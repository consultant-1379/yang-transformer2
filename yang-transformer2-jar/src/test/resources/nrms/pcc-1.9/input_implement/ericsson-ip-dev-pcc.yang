module ericsson-ip-dev-pcc {
  yang-version 1.1;
  namespace "urn:rdns:com:ericsson:oammodel:ericsson-ip-dev-pcc";
  prefix ipdpcc;

  import ietf-interfaces {
    prefix if;
  }
  import ietf-ip {
    prefix ip;
  }
  import ericsson-yang-extensions {
    prefix yexte;
  }

  organization
    "Ericsson AB";
  contact
    "Web:   <http://www.ericsson.com>";
  description
    "This model deviate IETF IP Management.
     Copyright (c) 2020 Ericsson AB.
     All rights reserved";

  revision 2020-08-09 {
    description
      "Change interface type";
    reference
      "EN/LZN 704 0249";
    yexte:version "1";
    yexte:release "1";
    yexte:correction "0";
  }

  revision 2019-07-15 {
    description
      "Deviation on IETF IP Management YANG";
    reference
      "rfc7950";
    yexte:version "1";
    yexte:release "0";
    yexte:correction "0";
  }

  deviation "/if:interfaces/if:interface/ip:ipv4/ip:mtu" {
    deviate not-supported;
  }

  deviation "/if:interfaces/if:interface/ip:ipv6/ip:mtu" {
    deviate not-supported;
  }
}
