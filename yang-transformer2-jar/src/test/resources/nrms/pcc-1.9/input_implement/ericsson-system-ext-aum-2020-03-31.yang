module ericsson-system-ext-aum {
    yang-version 1.1;
    namespace urn:rdns:com:ericsson:oammodel:ericsson-system-ext-aum;
    prefix sysxeaum;

    import ericsson-yang-extensions {
        prefix yexte;
    }
    import ericsson-system-ext {
      prefix sysxe;
    }
    import ietf-system {
      prefix sys;
    }

    organization "Ericsson AB";
    contact "Ericsson first line support via email";
    description "The module extends and deviates ericsson-system-ext-aum.

     Copyright (c) 2020 Ericsson AB. All rights reserved.";

    revision 2020-03-31 {
        // erdrjxx
        description "Enabling some LDAP paths for central authentication
            Features unlocked:
                - ericsson-system-ext:ldap
                - ericsson-system-ext:ldap-authentication
                - ericsson-system-ext:ldap-clear";
        yexte:version 1;
        yexte:release 1;
        yexte:correction 0;
    }

    revision 2020-03-04 {
        // erdrjxx
        description "First version";
        yexte:version 1;
        yexte:release 0;
        yexte:correction 0;
    }

    // #################################################################################
    // ############################## VERSION 1.0.0 ####################################
    // #################################################################################

    deviation /sys:set-current-datetime {
      description "not-supported.";
      deviate not-supported;
    }

    deviation /sys:system-restart {
      description "not-supported.";
      deviate not-supported;
    }

    deviation /sys:system/sys:clock {
      description "not-supported.";
      deviate not-supported;
    }

    deviation /sys:system/sys:contact {
      description "not-supported.";
      deviate not-supported;
    }

    deviation /sys:system/sys:dns-resolver {
      description "not-supported.";
      deviate not-supported;
    }

    deviation /sys:system/sys:hostname {
      description "not-supported.";
      deviate not-supported;
    }

    deviation /sys:system/sys:location {
      description "not-supported.";
      deviate not-supported;
    }

    deviation /sys:system/sysxe:user-label {
      description "not-supported.";
      deviate not-supported;
    }

    deviation /sys:system/sysxe:ldap-checks {
      description "not-supported.";
      deviate not-supported;
    }

    // @TODO deviate to config false (ready-only)
    deviation /sys:system/sys:authentication/sys:user-authentication-order {
      description "not-supported.";
      deviate not-supported;
    }

    deviation /sys:system/sys:authentication/sysxe:change-password {
      description "not-supported.";
      deviate not-supported;
    }

    deviation /sys:system/sys:authentication/sysxe:legal-notice {
      description "not-supported.";
      deviate not-supported;
    }

    deviation /sys:system/sys:authentication/sysxe:privacy-notice {
      description "not-supported.";
      deviate not-supported;
    }

    deviation /sys:system/sys:authentication/sysxe:authentication-failure-delay {
      description "not-supported.";
      deviate not-supported;
    }

    deviation /sys:system/sys:authentication/sys:user/sysxe:unlock-operational-lock {
      description "not-supported.";
      deviate not-supported;
    }

    deviation /sys:system/sys:authentication/sysxe:password-quality {
      description "not-supported.";
      deviate not-supported;
    }

    deviation /sys:system/sys:authentication/sysxe:default-password-policy/sysxe:password-quality {
      description "not-supported.";
      deviate not-supported;
    }

    deviation /sys:system/sys:authentication/sysxe:password-policy/sysxe:password-quality {
      description "not-supported.";
      deviate not-supported;
    }

    deviation /sys:system/sys:authentication/sysxe:admin-user/sysxe:admin-password-policy {
      description "not-supported.";
      deviate not-supported;
    }

    deviation /sys:system-state/sys:platform {
      description "not-supported.";
      deviate not-supported;
    }

    deviation /sys:system-state/sys:clock {
      description "not-supported.";
      deviate not-supported;
    }

    deviation /sys:system-state/sysxe:release {
      description "not-supported.";
      deviate not-supported;
    }

    deviation /sys:system-state/sysxe:managed-element-type {
      description "not-supported.";
      deviate not-supported;
    }

    deviation /sys:system-state/sysxe:authentication/sysxe:user {
      description "not-supported.";
      deviate not-supported;
    }

    deviation /sys:system-state/sysxe:authentication/sysxe:admin-user/sysxe:admin-password-policy {
      description "not-supported.";
      deviate not-supported;
    }

    deviation /sys:system-state/sysxe:authentication/sysxe:admin-user/sysxe:last-login-time {
      description "not-supported.";
      deviate not-supported;
    }

    deviation /sys:system-state/sysxe:authentication/sysxe:admin-user/sysxe:password-changed-time {
      description "not-supported.";
      deviate not-supported;
    }

    deviation /sys:system-state/sysxe:authentication/sysxe:admin-user/sysxe:password-failure-times {
      description "not-supported.";
      deviate not-supported;
    }

    deviation /sys:system/sys:authentication/sys:user/sys:name {
      description
	"Deviate with proper type definition.";

      deviate replace {
	type string {
	  length 1..32;
	  pattern '[a-zA-Z_][a-zA-Z0-9_.-]*' {
	    error-message
	      "A string of alphanumeric US-ASCII characters, optionally containing
    '-', '_', or '.'. For example: 'user_1'";
	  }
	}
      }
    }

    // #################################################################################
    // ############################## VERSION 1.1.0 ####################################
    // #################################################################################

    // DON'T REMOVE until confd issue has been solved (ietf-truststore)
    deviation /sys:system/sysxe:ldap/sysxe:security/sysxe:transport-security/sysxe:tls/sysxe:tls/sysxe:client-identity {
      description "not-supported.";
      deviate not-supported;
    }

    // DON'T REMOVE until confd issue has been solved (ietf-truststore)
    deviation /sys:system/sysxe:ldap/sysxe:security/sysxe:transport-security/sysxe:tls/sysxe:tls/sysxe:server-authentication {
      description "not-supported.";
      deviate not-supported;
    }

    // DON'T REMOVE until confd issue has been solved (ietf-truststore)
    deviation /sys:system/sysxe:ldap/sysxe:security/sysxe:transport-security/sysxe:tls/sysxe:tls/sysxe:hello-params {
      description "not-supported.";
      deviate not-supported;
    }

    // DON'T REMOVE until confd issue has been solved (ietf-truststore)
    deviation /sys:system/sysxe:ldap/sysxe:security/sysxe:transport-security/sysxe:tls/sysxe:tls/sysxe:keepalives {
      description "not-supported.";
      deviate not-supported;
    }

    deviation /sys:system/sysxe:ldap/sysxe:options/sysxe:group-filter {
      description "not-supported.";
      deviate not-supported;
    }

    deviation /sys:system/sysxe:ldap/sysxe:security/sysxe:authentication-type/sysxe:simple-anonymous/sysxe:simple-anonymous {
       description "not-supported.";
       deviate not-supported;
    }

    deviation /sys:system/sysxe:ldap/sysxe:security/sysxe:authentication-type/sysxe:simple-unauthenticated/sysxe:simple-unauthenticated {
       description "not-supported.";
       deviate not-supported;
    }
}
