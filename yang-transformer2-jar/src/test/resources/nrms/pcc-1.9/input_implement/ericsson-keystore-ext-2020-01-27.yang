module ericsson-keystore-ext {
  yang-version 1.1;
  namespace "urn:rdns:com:ericsson:oammodel:ericsson-keystore-ext";
  prefix ksxe;

  import ericsson-yang-extensions {
    prefix yexte;
  }
  import ericsson-yang-types {
    prefix typese;
  }
  import ietf-inet-types {
    prefix inet;
  }
  import ietf-yang-types {
    prefix yang;
  }
  import ietf-keystore {
    prefix ks;
    revision-date 2019-11-20;
    description
      "Based on draft";
  }
  import ietf-truststore {
    prefix ts;
    revision-date 2019-11-20;
    description
      "Based on draft";
    reference "ietf-truststore@2019-11-20";
  }
  import iana-asymmetric-algs {
    prefix iasa;
    reference "RFC XXXX: Common YANG Data Types for Cryptography";
  }

  organization
    "Ericsson AB";
  contact
    "Ericsson first line support via email.";
  description
    "The module extends and deviates ietf-keystore.

     Keystore supports three private key types: cleartext, hidden, and encrypted.
     It is important, that all cases must be encrypted at rest, and cleartext
     is clear only from NBI perspective where authentication and authorization still
     applies. Hidden is used primarily for hardware security cases when the key
     is stored in the HW security module and it is not possible to read as
     configuration neither in clear nor in encrypted way. However, hidden behavior
     can be implemented also with SW keys, keys residing in file system or a KMS. Encrypted
     keys were invented in IETF for a special case, to support copy-config and
     edit-config way of moving configuration between devices, and still supporting
     keys that are generated by the device and not exposed to the client. Encrypted
     keys can be moved with copy-config and edit-config, if the encryption key is shared
     between the devices. The encryption key is then either in clear in NBI, or encrypted
     by a device specific hidden key, but in all cases the encryption key is shared
     between source and target devices.

     In this module, the decision was to not use encrypted keys (and NBI based
     migration as a consequence), but use only the cleartext or the hidden keys.
     Cleartext is used in config false mode and requires a pkcs12 or pkcs8 installation
     action to support common installation format and the atomic configuratiopn of the
     algorithm, public key, and private key. Cleartext NBI representation is considered
     ok for these installations since the private key is coming from operator. Hidden key
     is supposed to be used in cases when the private key is generated by the device
     coming from HW security module, or stored in file system, or in a KMS. Migration
     of SW based hidden keys can be supported through the backup procedure.

     --- ---

     Copyright (c) 2020 Ericsson AB. All rights reserved.";

  revision 2020-01-27 {
    description
      "CMPv2 online enrollment included.
       Aligned to ietf drafts from 2019-11-20.

       Hidden private key type added for keys generated
       for CMPv2 enrollments.
       Symmetric keys added back as supported due to typedef dependency";
    yexte:version "1";
    yexte:release "1";
    yexte:correction "0";
  }
  revision 2019-05-24 {
    description
      "First version.";
    yexte:version "1";
    yexte:release "0";
    yexte:correction "0";
  }

  feature pkcs12 {
    description
      "Indicates that the system supports installing pkcs12 binaries.";
    reference "RFC 7292: PKCS #12: Personal Information Exchange Syntax v1.1";
  }

  feature pkcs8 {
    description
      "Indicates that the system supports installing pkcs8 binaries.";
    reference
      "RFC5208: Public-Key Cryptography Standards (PKCS) #8:
                Private-Key Information Syntax Specification Version 1.2";
  }

  feature cmp {
    description
      "Indicates that the system supports online enrollment by CMPv2.";
    reference
      "RFC 6712: Internet X.509 Public Key Infrastructure
                 HTTP Transfer for the Certificate Management Protocol (CMP)";
  }

  feature manual-renewal {
    if-feature "cmp";
    description
      "Indicates that the system supports manually triggered renewal by CMPv2.";
  }

  deviation "/ks:keystore/ks:asymmetric-keys/ks:asymmetric-key/ks:private-key-type/ks:private-key/ks:private-key" {
    description
      "Binary configuration of private-key is not supported in this revision.
       Where key import is necessary, install-asymmetric-key-pkcs8
       or install-asymmetric-key-pkcs12 actions should be used.";
    deviate replace {
      config false;
    }
    deviate add {
      yexte:is-passphrase;
    }
  }
  deviation "/ks:keystore/ks:asymmetric-keys/ks:asymmetric-key/ks:private-key-format" {
    description
      "Binary configuration of private-key is not supported in this revision.
       Where key import is necessary, install-asymmetric-key-pkcs8
       or install-asymmetric-key-pkcs12 actions should be used.";
    deviate replace {
      config false;
    }
  }
  deviation "/ks:keystore/ks:asymmetric-keys/ks:asymmetric-key/ks:private-key-type/ks:hidden-private-key/ks:hidden-private-key" {
    description
      "Creation of hidden key is not supported in this revision.
       Where key generation is necessary, use start-cmp instead.";
    deviate replace {
      config false;
    }
  }
  deviation "/ks:keystore/ks:asymmetric-keys/ks:asymmetric-key/ks:public-key" {
    description
      "This leaf is not possible to configure as private-key is not configurable, and
       both must be set and form a key pair. Use install-asymmetric-key-pkcs8, or
       install-asymmetric-key-pkcs12, or start-cmp.";
    deviate replace {
      config false;
    }
  }
  deviation "/ks:keystore/ks:asymmetric-keys/ks:asymmetric-key/ks:public-key-format" {
    description
      "This leaf is not possible to configure as private-key is not configurable, and
       both must be set and form a key pair. Use install-asymmetric-key-pkcs8, or
       install-asymmetric-key-pkcs12, or start-cmp.";
    deviate replace {
      config false;
    }
  }
  deviation "/ks:keystore/ks:asymmetric-keys/ks:asymmetric-key/ks:algorithm" {
    description
      "This leaf is not possible to configure as private-key is not configurable, and
       it must represent the algorithm of the private key. Use install-asymmetric-key-pkcs8, or
       install-asymmetric-key-pkcs12, or start-cmp.";
    deviate replace {
      config false;
    }
  }
  deviation "/ks:keystore/ks:asymmetric-keys/ks:generate-asymmetric-key" {
    description
      "Generation of asymmetric keys not supported. Use PKCS12 or CMPv2 instead.";
    deviate not-supported;
  }
  deviation "/ks:keystore/ks:asymmetric-keys/ks:asymmetric-key/ks:certificates/ks:certificate/ks:certificate-expiration" {
    description
      "Instead of certificate expiration notification, Fault Management alarms are sent.";
    deviate not-supported;
  }
  augment "/ks:keystore/ks:asymmetric-keys" {
    description
      "Adds an action to install a pkcs8 container file
       with an asymmetric private key. Especially needed
       for the use case of installing an SSH key for user
       authentication toward external SFTP server.";
    action install-asymmetric-key-pkcs8 {
      if-feature "pkcs8";
      description
        "Installs a pkcs8 binary with an asymmetric private key.
         The resulting asymmetric key values are copied to <running>.

         The key may be password protected.";
      input {
        leaf name {
          type string;
          mandatory true;
          description
            "The name the asymmetric key should have when listed in
             /keystore/asymmetric-keys/asymmetric-key/";
        }
        leaf p8 {
          type binary;
          mandatory true;
          yexte:is-passphrase;
          description
            "A binary that contains the pkcs8 encoded value of the
             private key.";
          reference
            "RFC5208: Public-Key Cryptography Standards (PKCS) #8:
                      Private-Key Information Syntax Specification Version 1.2";
        }
        leaf p8-password {
          type string;
          yexte:is-passphrase;
          description
            "The password to decrypt an encrypted pkcs8 container.";
        }
      }
    }
  }
  augment "/ks:keystore/ks:asymmetric-keys" {
    description
      "Adds an action to install a pkcs12 binary with an asymmetric
       private key and a corresponding certificate chain.";
    action install-asymmetric-key-pkcs12 {
      if-feature "pkcs12";
      description
        "Installs a pkcs12 binary with an asymmetric private key
         and a corresponding certificate chain. The resulting asymmetric
         key values are copied to <running>.

         The pkcs12 binary may be password protected.";
      input {
        leaf name {
          type string;
          mandatory true;
          description
            "The name the asymmetric key should have when listed in
             /keystore/asymmetric-keys/asymmetric-key/";
        }
        leaf certificate-name {
          type string;
          mandatory true;
          description
            "The name the certificate chain should have when listed in
             /keystore/asymmetric-keys/asymmetric-key/certificates/certificate";
        }
        leaf p12 {
          type binary;
          mandatory true;
          yexte:is-passphrase;
          description
            "A binary that contains the pkcs12 encoded value of the
             private key and the corresponding certificate chain.";
          reference "RFC7292: PKCS #12: Personal Information Exchange Syntax v1.1";
        }
        leaf p12-password {
          type string;
          yexte:is-passphrase;
          description
            "The password to decrypt an encrypted pkcs12 container.";
        }
      }
    }
  }
  augment "/ks:keystore/ks:asymmetric-keys/ks:asymmetric-key/ks:certificates" {
    description
      "Adds an action to install a PEM certificate chain.";
    action install-certificate-pem {
      description
        "Installs a PEM file with the end-entity and intermediate certificates.";
      input {
        leaf name {
          type string;
          mandatory true;
          description
            "The name the certificate chain should have when listed in
             /keystore/asymmetric-keys/asymmetric-key/certificates/certificate";
        }
        leaf pem {
          type binary;
          mandatory true;
          description
            "A binary that contains the PEM encoded textual value of the end-entity
             and its intermediate certificates.";
          reference "RFC 7468: Textual Encodings of PKIX, PKCS, and CMS Structures";
        }
      }
    }
  }
  augment "/ks:keystore" {
    if-feature "cmp";
    description
      "Augments keystore with certificate authority and registration authority groups for
       CMPv2 enrollment option.";
    reference
      "RFC 6712: Internet X.509 Public Key Infrastructure
                 HTTP Transfer for the Certificate Management Protocol (CMP)";
    container cmp {
      description
        "Configuration of CMPv2 servers and authorities.";
      container certificate-authorities {
        description
          "A list of Certificate Authorities.";
        list certificate-authority {
          key "name";
          description
            "A Certificate Authority.";
          leaf name {
            type typese:distinguished-name;
            description
              "Specifies the name of the issuing CA.
               The X.501 distinguished name of the issuing CA
               used for addressing and reference identity.";
          }
        }
      }
      container cmp-server-groups {
        description
          "A list of CMPv2 server groups.";
        list cmp-server-group {
          key "name";
          description
            "A CMPv2 server group.";
          leaf name {
            type string;
            mandatory true;
            description
              "The name of the CMPv2 server group.";
          }
          list cmp-server {
            key "name";
            min-elements 1;
            description
              "A CMPv2 server, which can be implemented by either
               a Registration Authority or a Certificate Authority.";
            leaf name {
              type string;
              mandatory true;
              description
                "The name of the CMPv2 server.";
            }
            leaf uri {
              type inet:uri;
              mandatory true;
              description
                "The URI of the CMPv2 server.

                 Example: http://192.168.33.27:8080 or cmp://192.168.33.27";
            }
            leaf ca-certs {
              type ts:certificates-ref;
              mandatory true;
              description
                "A reference to a list of certificate authority (CA)
                 certificates used by the CMPv2 client to authenticate
                 the CMPv2 server certificates.  A CMPv2 server
                 certificate is authenticated if it has a valid chain of trust to
                 a configured CA certificate.";
            }
            leaf certificate-authority {
              type leafref {
                path "/ks:keystore/ksxe:cmp/ksxe:certificate-authorities/ksxe:certificate-authority/ksxe:name";
              }
              mandatory true;
              description
                "The Certificate Authority used by this CMPv2 server.";
            }
            leaf priority {
              type uint8 {
                range "1..max";
              }
              default "1";
              description
                "A priority assigned to a CMPv2 server. A smaller number
                 signifies higher priority. A server with a lower priority is chosen
                 when servers with higher priority are not accessible. In the case when
                 CMPv2 servers have the same priority, then the server is chosen
                 with round robin.";
            }
          }
        }
      }
    }
  }
  augment "/ks:keystore/ks:asymmetric-keys" {
    if-feature "cmp";
    description
      "Augments asymmetric keys in keystore to perform initial CMPv2 enrollment";
    reference
      "RFC 6712: Internet X.509 Public Key Infrastructure
                 HTTP Transfer for the Certificate Management Protocol (CMP)";
    container cmp {
      action start-cmp {
        description
          "Starts a CMPv2 initial enrollment.";
        input {
          leaf name {
            type string;
            mandatory true;
            description
              "The name the asymmetric key should have when listed in
               /keystore/asymmetric-keys/asymmetric-key/";
          }
          leaf certificate-name {
            type string;
            mandatory true;
            description
              "The name the certificate chain should have when listed in
               /keystore/asymmetric-keys/asymmetric-key/certificates/certificate";
          }
          leaf algorithm {
            type iasa:asymmetric-algorithm-type;
            mandatory true;
            description
              "The algorithm to be used when generating the
               asymmetric key.";
            must
              "(. = 'rsa2048' or . = 'rsa3072' or . = 'rsa4096' or
                . = 'secp256r1' or . = 'secp384r1' or . = 'secp521r1')";
          }
          leaf subject {
            type typese:distinguished-name;
            mandatory true;
            description
              "The X.501 DN to be used in the subject field of the requested certificate.
                  For instance: 'C=SE,O=Ericsson,CN=someserialnumber.ericsson.com'";
          }
          leaf-list subject-alternative-names {
            type string;
            description
              "The subjectAltName can be specified either as an IP address or a FQDN.

               Format is <type>:<value>, where <type> is either 'IP' (for IP address) or 'DNS' (for FQDN).
               For 'IP' type the <value> is an IPv4 address in dotted decimal notation, or an IPv6 address
               in colon decimal notation. For 'DNS' type the <value> is an FQDN.

               Examples:
                  DNS:someserialnumber.ericsson.com
                  IP:145.34.23.123
                  IP:2001:DB8::8:800:200C:417A";
          }
          leaf password {
            yexte:is-passphrase;
            type string;
            mandatory true;
            description
              "The CMPv2 challenge password.";
          }
          leaf cmp-server-group {
            mandatory true;
            type leafref {
              path "/ks:keystore/ksxe:cmp/ksxe:cmp-server-groups/ksxe:cmp-server-group/ksxe:name";
            }
            description
              "A CMPv2 server group used for CMPv2 enrollment.";
          }
          leaf trusted-certs {
            type ts:certificates-ref {
              require-instance false;
            }
            description
              "A reference to a list of certificate authority (CA)
               certificates updated by the CMPv2 client after completing
               the CMPv2 enrollment if the CMPv2 server provided
               CA certificates.";
          }
        }
      }
    }
  }
  augment "/ks:keystore/ks:asymmetric-keys/ks:asymmetric-key" {
    if-feature "cmp";
    description
      "Augments asymmetric keys in keystore with CMPv2 server
       configuration, action to perform CMPv2 renewal, and configuration
       for automated renewal.";
    reference
      "RFC 6712: Internet X.509 Public Key Infrastructure
                 HTTP Transfer for the Certificate Management Protocol (CMP)";
    container cmp {
      presence "true";
      description
        "CMPv2 configuration and actions for an asymmetric key.";
      leaf cmp-server-group {
        mandatory true;
        type leafref {
          path "/ks:keystore/ksxe:cmp/ksxe:cmp-server-groups/ksxe:cmp-server-group/ksxe:name";
        }
        description
          "A CMPv2 server group used for CMPv2 enrollment.";
      }
      leaf renewal-time {
        type yang:date-and-time;
        config false;
        description
          "The planned renewal time of the asymmetric key and its certificate when automatic
           renewal is enabled.";
      }
      leaf trusted-certs {
        type ts:certificates-ref {
          require-instance false;
        }
        config false;
        description
          "A reference to a list of certificate authority (CA)
           certificates updated by the CMPv2 client after completing
           the CMPv2 enrollment if the CMPv2 server provided
           CA certificates. Updated by start-cmp.";
      }
      leaf renewal-mode {
        if-feature "manual-renewal";
        type enumeration {
          enum manual {
            value 0;
            description
              "Manual renewal.";
          }
          enum automatic {
            value 1;
            description
              "Automatic renewal.";
          }
        }
        default "manual";
        description
          "Sets renewal mode to manual or automatic. In automatic case the device
           attempts to renew the certificate before expiration by authenticating to the
           CMPv2 server with the current certificate and keeping the current key
           algorithm for the new certificate. If a change in the algorithm or subject alternative name
           is needed then renew-cmp action can be used.";
        must '(. = "manual" or (/ks:keystore/ks:asymmetric-keys/ks:asymmetric-key/ks:certificates/ks:certificate))' {
          error-message
            "Must be either manual or a valid certificate
             must exist for CMPv2 automated renewal.";
        }
      }
      action renew-cmp {
        description
          "Renews a certificate by CMPv2.";
        input {
          leaf algorithm {
            type iasa:asymmetric-algorithm-type;
            description
              "The algorithm to be used when generating the
               asymmetric key.";
            must
              "(. = 'rsa2048' or . = 'rsa3072' or . = 'rsa4096' or
                . = 'secp256r1' or . = 'secp384r1' or . = 'secp521r1')";
          }
          leaf-list subject-alternative-names {
            type string;
            description
              "The subjectAltName can be specified either as an IP address or a FQDN.

               Format is <type>:<value>, where <type> is either 'IP' (for IP address) or 'DNS' (for FQDN).
               For 'IP' type the <value> is an IPv4 address in dotted decimal notation, or an IPv6 address
               in colon decimal notation. For 'DNS' type the <value> is an FQDN.

               Examples:
                  DNS:someserialnumber.ericsson.com
                  IP:145.34.23.123
                  IP:2001:DB8::8:800:200C:417A";
          }
          must '(/ks:keystore/ks:asymmetric-keys/ks:asymmetric-key/ks:certificates/ks:certificate)' {
            error-message "A valid certificate must exist for CMPv2 renewal.";
          }
        }
      }
    }
  }
}
