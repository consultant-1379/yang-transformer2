module ericsson-brm-ext-adp {
  yang-version 1.1;
  namespace "urn:rdns:com:ericsson:oammodel:ericsson-brm-ext-adp";
  prefix brmxe;

  import ericsson-yang-extensions { prefix yexte; }
  import ericsson-brm { prefix brme; }


  organization
    "Ericsson AB";
  contact
    "Ericsson first line support via email";
  description
    "The module deviates ericsson-brm.

     Copyright (c) 2020 Ericsson AB. All rights reserved.";

  revision "2020-02-02" {
    // eeistn
    description
          "First version of the extension file. This extension removes
           the unsupported features from ericsson-brm. These features
           will be implemented in future releases of the
           ADP Backup and Restore Orchestrator.";
    yexte:version 1;
    yexte:release 0;
    yexte:correction 0;
  }

  deviation "/brme:brm/brme:backup-manager/brme:housekeeping" {
    description
      "housekeeping is not yet supported";
        deviate not-supported;
  }

  deviation "/brme:brm/brme:backup-manager/brme:scheduler" {
    description
      "scheduling is not yet supported";
        deviate not-supported;
  }

  deviation "/brme:brm/brme:backup-manager/brme:label-store" {
    description
      "label-store is not yet supported";
        deviate not-supported;
  }

  deviation "/brme:brm/brme:backup-manager/brme:failsafe-backup" {
    description
      "failsafe-backup is not yet supported";
        deviate not-supported;
  }

  deviation "/brme:brm/brme:rollback-at-restore" {
    description
      "rollback-at-restore is not yet supported";
        deviate not-supported;
  }

  deviation "/brme:brm/brme:backup-manager/brme:auto-export" {
     description
      "auto-export is not yet supported";
        deviate not-supported;
  }

  deviation "/brme:brm/brme:backup-manager/brme:auto-export-password" {
     description
      "auto-export is not yet supported";
        deviate not-supported;
  }

  deviation "/brme:brm/brme:backup-manager/brme:auto-export-uri" {
     description
      "auto-export is not yet supported";
        deviate not-supported;
  }

  deviation "/brme:brm/brme:export-package-label-prefix" {
     description
      "The export package label prefix is not supported";
        deviate not-supported;
  }

  deviation "/brme:brm/brme:backup-manager/brme:cancel-current-action" {
     description
      "cancel-current-action on brm level is not supported";
        deviate not-supported;
  }

  deviation "/brme:brm/brme:backup-manager/brme:backup/brme:cancel-current-action" {
     description
      "cancel-current-action on backup level is not supported";
        deviate not-supported;
  }

  deviation "/brme:brm/brme:backup-manager/brme:backup/brme:user-label" {
     description
      "user-label on backups is not supported";
        deviate not-supported;
  }

}
