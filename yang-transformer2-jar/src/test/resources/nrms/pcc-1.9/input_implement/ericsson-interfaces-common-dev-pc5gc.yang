module ericsson-interfaces-common-dev-pc5gc {
  yang-version 1.1;
  namespace "urn:rdns:com:ericsson:oammodel:ericsson-interfaces-common-dev-pc5gc";
  prefix "ifcmndpc5gc";

  import ietf-interfaces {
    prefix "if";
  }

  import ietf-interfaces-common {
    prefix "if-cmn";
  }

  import ericsson-yang-extensions {
    prefix "yexte";
  }

  import ericsson-if-types-pc5gc {
    prefix pcift;
  }

  import ericsson-inet-types-pc5gc {
    prefix inetpc5gc;
  }

  organization
    "Ericsson AB";
  contact
    "Web:   <http://www.ericsson.com>";
  description
    "This model deviate IETF interfaces common.
     Copyright (c) 2019 Ericsson AB.
     All rights reserved";

  revision 2020-08-09 {
    description
      "Change interface type";
    reference
      "EN/LZN 704 0249";
    yexte:version "2";
    yexte:release "0";
    yexte:correction "0";
  }

  revision "2019-09-27" {
    description
      "Deviation on IETF interface common YANG";
    reference
      "rfc7950";
    yexte:version "1";
    yexte:release "0";
    yexte:correction "0";
  }

  deviation "/if:interfaces/if:interface/if-cmn:parent-interface" {
    deviate add {
      must "(/if:interfaces/if:interface[if:name=current()]/if:type = 'pcift:ethernetCsmacd')
                or (/if:interfaces/if:interface[if:name=current()]/if:type = 'pcift:activeBackupBonding')" {
        error-message
          "parent-interface is supported for ethernetCsmacd or activeBackupBonding type interface";
        description
          "parent-interface is supported for ethernetCsmacd or activeBackupBonding type interface";
      }
   }
  }

  deviation "/if:interfaces/if:interface/if-cmn:l2-mtu" {
    deviate add {
      must "../if:type != 'pcift:softwareLoopback'" {
        error-message
          "l2-mtu is not supported for softwareLoopback interface";
        description
          "l2-mtu is not supported for softwareLoopback interface";
      }
    }
  }
}
