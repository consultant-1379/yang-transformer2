module  ericsson-base-if-type-pc5gc {
  yang-version 1.1;
  namespace "urn:rdns:com:ericsson:oammodel:ericsson-base-if-type-pc5gc";

  prefix pcbift;

  import ericsson-yang-extensions {
    prefix yexte;
  }

  organization "Ericsson AB";
  contact
    "Web:   <http://www.ericsson.com>";

  description
    "This YANG module defines base Ericsson packet core
     interface types.
     Copyright (c) 2020 Ericsson AB.
     All rights reserved";

  revision 2020-08-09 {
    description
      "Initial version";
    reference
      "";
    yexte:version "1";
    yexte:release "0";
    yexte:correction "0";
  }

  identity pc-interface-type {
    description
      "Base identity from which packet core specific interface types are
       derived.";
  }

}
