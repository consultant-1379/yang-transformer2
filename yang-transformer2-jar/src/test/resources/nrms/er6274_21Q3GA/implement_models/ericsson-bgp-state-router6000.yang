module ericsson-bgp-state-router6000 {

  /*** NAMESPACE / PREFIX DEFINITION ***/

  namespace "urn:rdns:com:ericsson:oammodel:ericsson-bgp-state-router6000";
  prefix "bgpstrouter6000";

  /*** LINKAGE (IMPORTS / INCLUDES) ***/

  import ietf-inet-types { prefix "inet"; }
  import ietf-yang-types { prefix "yang"; }
  import ericsson-contexts-router6000 { prefix "ctxsr6k"; }
  import ericsson-context-state-router6000   { prefix "ctxstrouter6000"; }
  import ericsson-yang-extensions { prefix "yexte"; }

  /*** META INFORMATION ***/

  organization
   "Ericsson AB";

  contact
   "Web:   <http://www.ericsson.com>";

  description
   "IPOS BGP-STATE model, based on yang file from BGP4-MIB,
    Copyright (c) 2015 Ericsson AB.
    All rights reserved.";

  revision "2018-06-05" {
    description "Change model namespace";
    reference "rfc6020.txt.";
    yexte:version "2";
    yexte:release "0";
    yexte:correction "0";
  }

  revision "2015-12-07" {
    description "Initial revision";
    reference "rfc6020.txt.";
    yexte:version "1";
    yexte:release "0";
    yexte:correction "0";
  }

  augment "/ctxsr6k:contexts-state/ctxstrouter6000:context/ctxstrouter6000:router"
  {
    description "bgp-state";
    container bgp {
      description "bgp-state";

      leaf bgp-version {
        type binary {
          length "1..255";
        }
        description
         "Vector of supported BGP protocol version
          numbers.  Each peer negotiates the version
          from this vector.  Versions are identified
          via the string of bits contained within this
          object.  The first octet contains bits 0 to
          7, the second octet contains bits 8 to 15,
          and so on, with the most significant bit
          referring to the lowest bit number in the
          octet (e.g., the MSB of the first octet
          refers to bit 0).  If a bit, i, is present
          and set, then the version (i+1) of the BGP
          is supported.";
        reference
         "RFC 4271, Section 4.2.";
      }

      leaf bgp-local-as {
        type int32 {
          range "0..65535";
        }
        description
         "The local autonomous system number.";
        reference
         "RFC 4271, Section 4.2, 'My Autonomous System'.";
      }

      leaf bgp-identifier {
        type inet:ipv4-address;

        description
         "The BGP Identifier of the local system.";
        reference
         "RFC 4271, Section 4.2.";
      }

      /* XXX table comments here XXX */

      list bgp-peer-entry {

        key "bgp-peer-remote-addr";
        description
         "Entry containing information about the
          connection with a BGP peer.";


        leaf bgp-peer-identifier {
          type inet:ipv4-address;
          description
           "The BGP Identifier of this entry's BGP peer.
            This entry MUST be 0.0.0.0 unless the
            bgpPeerState is in the openconfirm or the
            established state.";
          reference
           "RFC 4271, Section 4.2, 'BGP Identifier'.";
        }

        leaf bgp-peer-state {
          type enumeration {
            enum idle        {
                value 1;
                description "idel";
            }
            enum connect     {
                value 2;
                description "connect";
            }
            enum active      {
                value 3;
                description "active";
            }
            enum opensent    {
                value 4;
                description "opensent";
            }
            enum openconfirm {
                value 5;
                description "openconfirm";
            }
            enum established {
                value 6;
                description "established";
            }
          }
          description
           "The BGP peer connection state.";
          reference
           "RFC 4271, Section 8.2.2.";
        }

        leaf bgp-peer-negotiated-version {
          type int32;
          description
           "The negotiated version of BGP running between
            the two peers.

            This entry MUST be zero (0) unless the
            bgpPeerState is in the openconfirm or the
            established state.

            Note that legal values for this object are
            between 0 and 255.";
          reference
           "RFC 4271, Section 4.2.
            RFC 4271, Section 7.";
        }

        leaf bgp-peer-local-addr {
          type inet:ipv4-address;
          description
           "The local IP address of this entry's BGP
            connection.";
        }

        leaf bgp-peer-local-port {
          type int32 {
            range "0..65535";
          }

          description
           "The local port for the TCP connection between
            the BGP peers.";
        }

        leaf bgp-peer-remote-addr {
          type inet:ipv4-address;

          description
           "The remote IP address of this entry's BGP
            peer.";
        }

        leaf bgp-peer-remote-port {
          type int32 {
            range "0..65535";
          }

          description
           "The remote port for the TCP connection
            between the BGP peers.  Note that the
            objects bgpPeerLocalAddr,
            bgpPeerLocalPort, bgpPeerRemoteAddr, and
            bgpPeerRemotePort provide the appropriate
            reference to the standard MIB TCP
            connection table.";
        }

        leaf bgp-peer-remote-as {
          type int32 {
            range "0..65535";
          }

          description
           "The remote autonomous system number received in
            the BGP OPEN message.";
          reference
           "RFC 4271, Section 4.2.";
        }

        leaf bgp-peer-in-updates {
          type yang:counter32;

          description
           "The number of BGP UPDATE messages
            received on this connection.";
          reference
           "RFC 4271, Section 4.3.";
        }

        leaf bgp-peer-out-updates {
          type yang:counter32;

          description
           "The number of BGP UPDATE messages
            transmitted on this connection.";
          reference
           "RFC 4271, Section 4.3.";
        }

        leaf bgp-peer-in-total-messages {
          type yang:counter32;

          description
           "The total number of messages received
            from the remote peer on this connection.";
          reference
           "RFC 4271, Section 4.";
        }

        leaf bgp-peer-out-total-messages {
          type yang:counter32;

          description
           "The total number of messages transmitted to
            the remote peer on this connection.";
          reference
           "RFC 4271, Section 4.";
        }

        leaf bgp-peer-last-error {
          type binary {
            length "2";
          }

          description
           "The last error code and subcode seen by this
            peer on this connection.  If no error has
            occurred, this field is zero.  Otherwise, the
            first byte of this two byte OCTET STRING
            contains the error code, and the second byte
            contains the subcode.";
          reference
           "RFC 4271, Section 4.5.";
        }

        leaf bgp-peer-fsm-established-transitions {
          type yang:counter32;

          description
           "The total number of times the BGP FSM
            transitioned into the established state
            for this peer.";
          reference
           "RFC 4271, Section 8.";
        }

        leaf bgp-peer-fsm-established-time {
          type yang:gauge32;
          units "seconds";

          description
           "This timer indicates how long (in
            seconds) this peer has been in the
            established state or how long
            since this peer was last in the
            established state.  It is set to zero when
            a new peer is configured or when the router is
            booted.";
          reference
           "RFC 4271, Section 8.";
        }

        leaf bgp-peer-hold-time {
          type int32 {
            range "0 | 3..65535";
          }
          units "seconds";

          description
           "Time interval (in seconds) for the Hold
            Timer established with the peer.  The
            value of this object is calculated by this
            BGP speaker, using the smaller of the
            values in bgpPeerHoldTimeConfigured and the
            Hold Time received in the OPEN message.

            This value must be at least three seconds
            if it is not zero (0).

            If the Hold Timer has not been established
            with the peer this object MUST have a value
            of zero (0).

            If the bgpPeerHoldTimeConfigured object has
            a value of (0), then this object MUST have a
            value of (0).";
          reference
           "RFC 4271, Section 4.2.";
        }

        leaf bgp-peer-keep-alive {
          type int32 {
            range "0..21845";
          }
          units "seconds";

          description
           "Time interval (in seconds) for the KeepAlive
            timer established with the peer.  The value
            of this object is calculated by this BGP
            speaker such that, when compared with
            bgpPeerHoldTime, it has the same proportion
            that bgpPeerKeepAliveConfigured has,
            compared with bgpPeerHoldTimeConfigured.

            If the KeepAlive timer has not been established
            with the peer, this object MUST have a value
            of zero (0).

            If the of bgpPeerKeepAliveConfigured object
            has a value of (0), then this object MUST have
            a value of (0).";
          reference
           "RFC 4271, Section 4.4.";
        }

        leaf bgp-peer-in-update-elapsed-time {
          type yang:gauge32;
          units "seconds";

          description
           "Elapsed time (in seconds) since the last BGP
            UPDATE message was received from the peer.
            Each time bgpPeerInUpdates is incremented,
            the value of this object is set to zero (0).";
          reference
           "RFC 4271, Section 4.3.
            RFC 4271, Section 8.2.2, Established state.";
        }
      }

      /* XXX table comments here XXX */
      list bgp4-path-attr-entry {

        key "bgp4-path-attr-ip-addr-prefix bgp4-path-attr-ip-addr-prefix-len  bgp4-path-attr-peer";
        description
         "Information about a path to a network.";


        leaf bgp4-path-attr-peer {
          type inet:ipv4-address;

          description
           "The IP address of the peer where the path
            information was learned.";
        }

        leaf bgp4-path-attr-ip-addr-prefix-len {
          type int32 {
            range "0..32";
          }

          description
           "Length in bits of the IP address prefix in
            the Network Layer Reachability
            Information field.";
        }

        leaf bgp4-path-attr-ip-addr-prefix {
          type inet:ipv4-address;

          description
           "An IP address prefix in the Network Layer
            Reachability Information field.  This object
            is an IP address containing the prefix with
            length specified by
            bgp4PathAttrIpAddrPrefixLen.
            Any bits beyond the length specified by
            bgp4PathAttrIpAddrPrefixLen are zeroed.";
          reference
           "RFC 4271, Section 4.3.";
        }

        leaf bgp4-path-attr-origin {
          type enumeration {
            enum igp        {
                value 1;
                description "igp";
            }
            enum egp        {
                value 2;
                description "egp";
            }
            enum incomplete {
                value 3;
                description "incomplete";
            }
          }

          description
           "The ultimate origin of the path
            information.";
          reference
           "RFC 4271, Section 4.3.
            RFC 4271, Section 5.1.1.";
        }

        leaf bgp4-path-attr-aspath-segment {
          type binary {
            length "2..255";
          }

          description
           "The sequence of AS path segments.  Each AS
            path segment is represented by a triple
            <type, length, value>.

            The type is a 1-octet field that has two
            possible values:
                1      AS_SET: unordered set of ASes that a
                            route in the UPDATE message
                            has traversed

                2      AS_SEQUENCE: ordered set of ASes that
                            a route in the UPDATE message
                            has traversed.

            The length is a 1-octet field containing the
            number of ASes in the value field.

            The value field contains one or more AS
            numbers.  Each AS is represented in the octet
            string as a pair of octets according to the
            following algorithm:

               first-byte-of-pair = ASNumber / 256;
               second-byte-of-pair = ASNumber & 255;

            Known Issues:
            o BGP Confederations will result in
              a type of either 3 or 4.
            o An AS Path may be longer than 255 octets.
              This may result in this object containing
              a truncated AS Path.";
          reference
           "RFC 4271, Section 4.3.
            RFC 4271, Section 5.1.2.";
        }

        leaf bgp4-path-attr-next-hop {
          type inet:ipv4-address;

          description
           "The address of the border router that
            should be used for the destination
            network.  This address is the NEXT_HOP
            address received in the UPDATE packet.";
          reference
           "RFC 4271, Section 4.3.
            RFC 4271, Section 5.1.3.";
        }

        leaf bgp4-path-attr-multi-exit-disc {
          type int32 {
            range "-1..2147483647";
          }

          description
           "This metric is used to discriminate
            between multiple exit points to an
            adjacent autonomous system.  A value of -1
            indicates the absence of this attribute.

            Known Issues:
            o The BGP-4 specification uses an
              unsigned 32 bit number.  Thus, this
              object cannot represent the full
              range of the protocol.";
          reference
           "RFC 4271, Section 4.3.
            RFC 4271, Section 5.1.4.";
        }

        leaf bgp4-path-attr-local-pref {
          type int32 {
            range "-1..2147483647";
          }

          description
           "The originating BGP4 speaker's degree of
            preference for an advertised route.  A
            value of -1 indicates the absence of this
            attribute.

            Known Issues:
            o The BGP-4 specification uses an
              unsigned 32 bit number and thus this
              object cannot represent the full
              range of the protocol.";
          reference
           "RFC 4271, Section 4.3.
            RFC 4271, Section 5.1.5.";
        }

        leaf bgp4-path-attr-atomic-aggregate {
          type enumeration {
            enum lessSpecificRouteNotSelected {
                value 1;
                description "lessSpecificRouteNotSelected";
            }
            enum lessSpecificRouteSelected    {
                value 2;
                description "lessSpecificRouteSelected";
            }
          }

          description
           "If the ATOMIC_AGGREGATE attribute is present
            in the Path Attributes then this object MUST
            have a value of 'lessSpecificRouteNotSelected'.

            If the ATOMIC_AGGREGATE attribute is missing
            in the Path Attributes then this object MUST
            have a value of 'lessSpecificRouteSelected'.

            Note that ATOMIC_AGGREGATE is now a primarily
            informational attribute.";
          reference
           "RFC 4271, Sections 5.1.6 and 9.1.4.";
        }

        leaf bgp4-path-attr-aggregator-as {
          type int32 {
            range "0..65535";
          }

          description
           "The AS number of the last BGP4 speaker that
            performed route aggregation.  A value of
            zero (0) indicates the absence of this
            attribute.

            Note that propagation of AS of zero is illegal
            in the Internet.";
          reference
           "RFC 4271, Section 5.1.7.
            RFC 4271, Section 9.2.2.2.";
        }

        leaf bgp4-path-attr-aggregator-addr {
          type inet:ipv4-address;

          description
           "The IP address of the last BGP4 speaker
            that performed route aggregation.  A
            value of 0.0.0.0 indicates the absence
            of this attribute.";
          reference
           "RFC 4271, Section 5.1.7.
            RFC 4271, Section 9.2.2.2.";
        }

        leaf bgp4-path-attr-calc-local-pref {
          type int32 {
            range "-1..2147483647";
          }
          description
           "The degree of preference calculated by the
            receiving BGP4 speaker for an advertised
            route.  A value of -1 indicates the
            absence of this attribute.

            Known Issues:
            o The BGP-4 specification uses an
              unsigned 32 bit number and thus this
              object cannot represent the full
              range of the protocol.";
          reference
           "RFC 4271, Section 9.1.1.";
        }

        leaf bgp4-path-attr-best {
          type enumeration {
            enum false {
                value 1;
                description "false";
            }
            enum true  {
                value 2;
                description "true";
            }
          }
          description
           "An indication of whether this route
            was chosen as the best BGP4 route for this
            destination.";
          reference
           "RFC 4271, Section 9.1.2.";
        }

        leaf bgp4-path-attr-unknown {
          type binary {
            length "0..255";
          }
          description
           "One or more path attributes not understood by
            this BGP4 speaker.

            Path attributes are recorded in the Update Path
            attribute format of type, length, value.

            Size zero (0) indicates the absence of such
            attributes.

            Octets beyond the maximum size, if any, are not
            recorded by this object.

            Known Issues:
            o Attributes understood by this speaker, but not
              represented in this MIB, are unavailable to
              the agent.";
          reference
           "RFC 4271, Section 5.";
        }
      }
    }
  }
} /* end of module bgp-state */
