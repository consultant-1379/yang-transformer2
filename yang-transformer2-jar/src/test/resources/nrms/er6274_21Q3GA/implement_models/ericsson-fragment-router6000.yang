module ericsson-fragment-router6000 {
  yang-version "1";

  namespace "urn:rdns:com:ericsson:oammodel:ericsson-fragment-router6000";

  prefix "fragmentrouter6000";

  import ietf-inet-types {
    prefix "inet";
  }

  import ericsson-types-router6000 {
    prefix "typesrouter6000";
  }

  import ericsson-contexts-router6000 {
    prefix "ctxsr6k";
  }

  import ietf-yang-types {
    prefix "yang";
  }

  import ericsson-yang-extensions {
    prefix "yexte";
  }

  organization
    "Ericsson AB";

  contact
    "Web:   <http://www.ericsson.com>";

  description
    "ericsson-fragment-router6000
     Copyright (c) 2018 Ericsson AB.
     All rights reserved";

  revision "2018-08-20" {
    description
      "initial revision";
    reference
      "rfc6020";
    yexte:version "1";
    yexte:release "0";
    yexte:correction "0";
  }

  augment "/ctxsr6k:contexts" {
    description
      "ericsson-fragment";
    /*
    ipv4 enable-fragment
    */
    leaf ipv4-enable-fragment {
      type empty;
      description
        "Enable IPv4 unicast fragment";
    }
  }

}
