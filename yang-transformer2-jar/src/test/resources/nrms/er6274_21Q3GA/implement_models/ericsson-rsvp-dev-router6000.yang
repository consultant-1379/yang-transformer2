module ericsson-rsvp-dev-router6000 {
  yang-version "1";

  namespace "urn:rdns:com:ericsson:oammodel:ericsson-rsvp-dev-router6000";

  prefix "rsvprouter6000";

  import ericsson-rsvp-router6000 {
   prefix "rsvpr6k";
  }

  import ericsson-contexts-router6000 {
   prefix "ctxsr6k";
  }

  import ericsson-context-router6000 {
   prefix "ctxr6k";
  }
  
   import ericsson-yang-extensions {
    prefix "yexte";
  }

  organization
    "Ericsson";

  contact
    "Web:   <http://www.ericsson.com>";

  description
    "ericsson-rsvp-dev-router6000
     Copyright (c) 2017 Ericsson AB.
     All rights reserved";

  revision "2018-06-05" {
    description
      "Change the module namespace";
    reference
      "rfc6020";
    yexte:version "2";
    yexte:release "0";
    yexte:correction "0";
  }

  revision "2017-06-16" {
    description
      "deviation for ericsson-rsvp-ipos.yang file";
    reference
      "rfc6020";
      yexte:version "1";
      yexte:release "0";
      yexte:correction "0";
  }

  deviation "/ctxsr6k:contexts/ctxr6k:context/ctxr6k:router/rsvpr6k:rsvp/rsvpr6k:lsp/rsvpr6k:tunnel-shortcut" {
    deviate not-supported;
  }
  deviation "/ctxsr6k:contexts/ctxr6k:context/ctxr6k:router/rsvpr6k:rsvp/rsvpr6k:lsp/rsvpr6k:fast-reroute" {
    deviate not-supported;
  }
  deviation "/ctxsr6k:contexts/ctxr6k:context/ctxr6k:router/rsvpr6k:rsvp/rsvpr6k:tunnel-shortcut" {
    deviate not-supported;
  } 
  }
