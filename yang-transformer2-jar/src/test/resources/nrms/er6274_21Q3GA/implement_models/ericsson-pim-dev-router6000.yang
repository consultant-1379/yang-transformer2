module ericsson-pim-dev-router6000 {
  yang-version "1";

  namespace "urn:rdns:com:ericsson:oammodel:ericsson-pim-dev-router6000";

  prefix "pimrouter6000";

  import ericsson-pim-router6000 {
   prefix "pimr6k";
  }

  import ericsson-contexts-router6000 {
   prefix "ctxsr6k";
  }

  import ericsson-context-router6000 {
   prefix "ctxr6k";
  }
  
    import ericsson-yang-extensions {
    prefix "yexte";
  }

  organization
    "Ericsson";

  contact
    "Web:   <http://www.ericsson.com>";

  description
    "ericsson-pim-dev-router6000
     Copyright (c) 2017 Ericsson AB.
     All rights reserved";

  revision "2018-06-05" {
    description
      "Change the module namespace";
    reference
      "rfc6020";
    yexte:version "2";
    yexte:release "0";
    yexte:correction "0";
  }

  revision "2017-06-13" {
    description
      "deviation for ericsson-pim-router6000.yang file";
    reference
      "rfc6020";
      yexte:version "1";
      yexte:release "0";
      yexte:correction "0";
  }

  deviation "/ctxsr6k:contexts/ctxr6k:context/ctxr6k:router/pimr6k:pim/pimr6k:address-family/pimr6k:ipv4/pimr6k:interface/pimr6k:state-refresh-origination-interval" {
    deviate not-supported;
  }
  deviation "/ctxsr6k:contexts/ctxr6k:context/ctxr6k:router/pimr6k:pim/pimr6k:address-family/pimr6k:ipv4/pimr6k:interface/pimr6k:dense-mode" {
    deviate not-supported;
  } 
  deviation "/ctxsr6k:contexts/ctxr6k:context/ctxr6k:router/pimr6k:pim/pimr6k:address-family/pimr6k:ipv4/pimr6k:interface/pimr6k:boundary" {
    deviate not-supported;
  }
  deviation "/ctxsr6k:contexts/ctxr6k:context/ctxr6k:router/pimr6k:pim/pimr6k:address-family/pimr6k:ipv4/pimr6k:interface/pimr6k:mdt-encapsulation-gre" {
    deviate not-supported;
  }
  deviation "/ctxsr6k:contexts/ctxr6k:context/ctxr6k:router/pimr6k:pim/pimr6k:operation-mode" {
    deviate not-supported;
  }
  deviation "/ctxsr6k:contexts/ctxr6k:context/ctxr6k:router/pimr6k:pim/pimr6k:address-family/pimr6k:ipv6/pimr6k:ssm" {
    deviate not-supported;
  }
  deviation "/ctxsr6k:contexts/ctxr6k:context/ctxr6k:router/pimr6k:pim/pimr6k:address-family/pimr6k:ipv6/pimr6k:interface/pimr6k:boundary" {
    deviate not-supported;
  }
  }
