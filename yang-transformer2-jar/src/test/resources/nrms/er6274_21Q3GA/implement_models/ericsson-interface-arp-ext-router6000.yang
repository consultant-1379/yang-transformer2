module ericsson-interface-arp-ext-router6000 {
  yang-version "1";

  namespace "urn:rdns:com:ericsson:oammodel:ericsson-interface-arp-ext-router6000";

  prefix "ifarpxrouter6000";

  import ietf-interfaces {
    prefix "if";
  }

  import ericsson-interfaces-ext-router6000 {
    prefix "ifxrouter6000";
  }

  import ericsson-yang-extensions {
    prefix "yexte";
  }

  organization
    "Ericsson AB";

  contact
    "Web:   <http://www.ericsson.com>";

  description
    "ericsson-interface-arp-ext-router6000
     Copyright (c) 2021 Ericsson AB.
     All rights reserved";

  revision "2021-03-16" {
    description
      "For Disabling gratuitous-arp on interface";
    reference
      "rfc6020";
    yexte:version "2";
    yexte:release "1";
    yexte:correction "1";
  }

  revision "2020-12-17" {
    description
      "For Disabling gratuitous-arp on interface";
    reference
      "rfc6020";
    yexte:version "2";
    yexte:release "1";
    yexte:correction "0";
  }

  revision "2018-11-27" {
    description
      "remove ipos choice description";
    reference
      "rfc6020";
    yexte:version "2";
    yexte:release "0";
    yexte:correction "1";
  }

  revision "2018-06-05" {
    description
      "Change model namespace";
    reference
      "rfc6020";
    yexte:version "2";
    yexte:release "0";
    yexte:correction "0";
  }

  revision "2018-03-19" {
    description
      "Replace container proxy-arp/secured-arp with choice
       case.";
    reference
      "rfc6020";
    yexte:version "1";
    yexte:release "0";
    yexte:correction "1";
  }

  revision "2016-03-29" {
    description
      "For CLI2Yang models data node sequence change.";
    reference
      "rfc6020";
    yexte:version "1";
    yexte:release "0";
    yexte:correction "0";
  }

  revision "2015-12-07" {
    description
      "initial revision";
    reference
      "rfc6020";
  }

  augment "/if:interfaces/if:interface/ifxrouter6000:l3-interfac"
  + "e/ifxrouter6000:ip" {
    description
      "ericsson-arp-interface";
    /*
    arp { arpa | timeout (timeo-val) | {proxy-arp [ always ] |
     secured-arp [ always ]} | delete-expired | sync icr [ choice
     (peer-intf) [ (peer-ctx) ] ] | { gratuitous-arp  [disable-
     send-receive | disable-receive] } }
    */
    container arp {
      description
        "ARP interface configuration";
      leaf arpa {
        type boolean;
        default "true";
        description
          "Enable/Disable arpa";
      }
      leaf timeout {
        type uint32 {
          range "30..4294967";
        }
        default "3600";
        description
          "Set ARP cache timeout";
      }
      choice arp-choice {
        case proxy-arp {
          container proxy-arp {
            presence "";
            description
              "Enable proxy ARP on the interface";
            leaf always {
              type empty;
              description
                "Enable proxy-arp for multiple hosts behind the
                 same circuit";
            }
          }
        }
        case secured-arp {
          container secured-arp {
            presence "";
            description
              "Enable secured-arp on the interface";
            leaf always {
              type empty;
              description
                "Enable secured-arp for multiple hosts behind
                 the same circuit";
            }
          }
        }
      }
      leaf delete-expired {
        type empty;
        description
          "Delete dynamic ARP entries when expired";
      }
      container sync-icr {
        presence "";
        description
          "ARP sync over ICR link";
        container choice {
          presence "";
          description
            "container choice.";
          leaf peer-intf {
            type string;
            mandatory true;
            description
              "peer interface name";
          }
          leaf peer-ctx {
            type string;
            description
              "peer context name";
          }
        }
      }
      container gratuitous-arp {
        description
          "gratuitous-arp config on the interface";
        choice gratuitous-arp-opt {
          case disable-send-receive {
            leaf disable-send-receive {
              type empty;
              description
                "Disable gratuitous-arp on the interface";
            }
          }
          case disable-receive {
            leaf disable-receive {
              type empty;
              description
                "Disable gratuitous-arp receive only";
            }
          }
        }
      }
    }
  }

}
