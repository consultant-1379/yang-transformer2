module ericsson-igmp-dev-router6000 {
  yang-version "1";

  namespace "urn:rdns:com:ericsson:oammodel:ericsson-igmp-dev-router6000";

  prefix "igmprouter6000";

  import ericsson-igmp-router6000 {
   prefix "igmpr6k";
  }

  import ericsson-contexts-router6000 {
   prefix "ctxsr6k";
  }

  import ericsson-context-router6000 {
   prefix "ctxr6k";
  }
  
  import ericsson-yang-extensions {
    prefix "yexte";
  }

  organization
    "Ericsson";

  contact
    "Web:   <http://www.ericsson.com>";

  description
    "ericsson-igmp-dev-router6000
     Copyright (c) 2017 Ericsson AB.
     All rights reserved";

  revision "2018-06-05" {
    description
      "Change the module namespace";
    reference
      "rfc6020";
    yexte:version "2";
    yexte:release "0";
    yexte:correction "0";
  }

  revision "2017-06-13" {
    description
      "deviation for ericsson-igmp-router6000.yang file";
    reference
      "rfc6020";
      yexte:version "1";
      yexte:release "0";
      yexte:correction "0";
  }

  deviation "/ctxsr6k:contexts/ctxr6k:context/igmpr6k:igmp/igmpr6k:service-profile/igmpr6k:multicast" {
    deviate not-supported;
  }
  deviation "/ctxsr6k:contexts/ctxr6k:context/igmpr6k:igmp/igmpr6k:service-profile/igmpr6k:bulkstats" {
    deviate not-supported;
  } 
  }
