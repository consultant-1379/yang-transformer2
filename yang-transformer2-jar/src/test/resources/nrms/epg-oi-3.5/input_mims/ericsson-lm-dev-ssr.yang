module ericsson-lm-dev-ssr {
  yang-version "1.1";

  namespace "urn:rdns:com:ericsson:oammodel:ericsson-lm-dev-ssr";

  prefix "lmdevssr";

  import ericsson-yang-extensions {
    prefix "yexte";
  }

  import ietf-yang-types {
    prefix yang;
  }

  import ericsson-lm {
    prefix lme;
  }

  organization
    "Ericsson AB";

  contact
    "Web:   <http://www.ericsson.com>";

  description
    "ericsson-lm-dev-ssr
     Copyright (c) 2018-2019 Ericsson AB.
     All rights reserved";

  revision "2019-09-09" {
    description
      "Deviating host as mandatory false";
    reference
      "rfc7950";
    yexte:version "1";
    yexte:release "0";
    yexte:correction "3";
  }

  revision "2019-08-21" {
    description
      "Remove deviation expiration and valid-from";
    reference
      "rfc7950";
    yexte:version "1";
    yexte:release "0";
    yexte:correction "2";
  }

  revision "2019-01-10" {
    description
      "Deviating host as not supported";
    reference
      "rfc7950";
    yexte:version "1";
    yexte:release "0";
    yexte:correction "1";
  }

  revision "2018-10-30" {
    description
      "Deviating data type of expiration and valid-from";
    reference
      "rfc6020";
    yexte:version "1";
    yexte:release "0";
    yexte:correction "0";
  }

  deviation "/lme:lm" {
    deviate add {
      yexte:is-system-created;
    }
  }
  deviation "/lme:lm/lme:nels-configuration" {
    deviate add {
      yexte:is-system-created;
    }
  }
  deviation "/lme:lm/lme:nels-configuration/lme:host" {
    deviate replace {
      mandatory false;
    }
  }
  deviation "/lme:lm/lme:nels-configuration/lme:port" {
    deviate replace {
      mandatory false;
    }
  }
}
