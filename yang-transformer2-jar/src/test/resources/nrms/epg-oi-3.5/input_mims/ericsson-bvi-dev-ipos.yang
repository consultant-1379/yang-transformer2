module ericsson-bvi-dev-ipos {
  yang-version 1.1;
  namespace "urn:rdns:com:ericsson:oammodel:ericsson-bvi-dev-ipos";
  prefix iposbvi;

  import ericsson-bvi-ext-ipos {
    prefix bvixipos;
  }

  import ietf-interfaces {
    prefix "if";
  }

  import ericsson-yang-extensions {
    prefix "yexte";
  }

  organization
    "Ericsson AB";
  contact
    "Ericsson first line support via email";
  description
    "Copyright (c) 2018 Ericsson AB. All rights reserved";

  revision "2019-07-04" {
    description
      "Update yang version 1.0 to 1.1";
    reference
      "rfc7950";
    yexte:version "1";
    yexte:release "0";
    yexte:correction "2";
  }

  revision "2018-06-01" {
    description "change yang version";
    reference "rfc6020";
    yexte:version "1";
    yexte:release "0";
    yexte:correction "1";
  }

  revision "2018-01-25" {
    description "initial revision";
    reference "rfc6020";
    yexte:version "1";
    yexte:release "0";
    yexte:correction "0";
  }

  deviation "/if:interfaces/if:interface/bvixipos:bvi/bvixipos:subscribe-micro-bfd" {
    deviate not-supported;
  }
}
