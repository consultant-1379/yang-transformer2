module ericsson-epg {
  yang-version 1.1;
  prefix epg;
  namespace "urn:rdns:com:ericsson:oammodel:ericsson-epg";

  include ericsson-types-epg;

  import ericsson-contexts-ipos { prefix ctxsipos; }
  import ericsson-context-ipos { prefix ctxipos; }
  import ericsson-pm {
    prefix pme;
  }
  import tailf-common {
    prefix tailf;
  }
  import ericsson-yang-extensions {
    prefix yexte;
  }
  import ietf-inet-types {
    prefix inet;
  }

  organization
    "Ericsson AB";
  contact
    "Ericsson AB first line support by email";
  description
    "Epg model.
     Copyright (c) 2017 Ericsson AB. All rights reserved.";

  revision 2020-02-12 {
    description
      "hour:minute:second=12:21:04";
    yexte:version "3";
    yexte:release "5";
    yexte:correction "0";
    reference "rfc6020";
  }

  typedef rule-failure-code-number-choice {
    type string {
      pattern '0|[1-9][0-9]{0,9}' {
        error-message "";
      }
    }
    description
      "number";
    tailf:info "0|[1-9][0-9]{0,9}";
  }

  typedef routing-instance-type {
    type leafref {
      path "/epg:epg/epg:node/epg:direct-io/epg:routing-instance/epg:name";
    }
    description
      "used by data models that need to reference epg node direct-io routing-instance.";
  }

  typedef application-id-application-identifier-choice {
    type string {
      pattern '[0-9]+(:[0-9]+)?' {
        error-message "Must be of form <number> or <number>:<number>";
      }
    }
    description
      "Application identity <application> or vendor application identity <vendor>:<application>";
    tailf:info "[0-9]+(:[0-9]+)?";
  }

  typedef protocol-number-number-choice {
    type string {
      pattern '([1-9])|([1-9][0-9])|(1[0-9][0-9])|(2[0-4][0-9])|(25[0-5])' {
        error-message "Must be a number from 0 to 255";
      }
    }
    description
      "A protocol number";
    tailf:info "([1-9])|([1-9][0-9])|(1[0-9][0-9])|(2[0-4][0-9])|(25[0-5])";
  }

  typedef acl-type {
    type identityref {
      base acl-base;
    }
    description
      "This type is used to refer to an Access Control List
       (ACL) type";
  }

   typedef priority_type {
     type uint16 {
        range "1..512" {
         error-message "Invalid value for attribute. Valid values are in range:[1,512]";
       }
     }
   }

    typedef rate-control-time-unit {
      description
        "Time unit for rate control configuration";
      type enumeration {
        enum unrestricted {
          description
            "Unrestricted";
        }
        enum minute {
          description
            "Minute";
        }
        enum hour {
          description
            "Hour";
        }
        enum day {
          description
            "Day";
        }
        enum week {
          description
            "Week";
        }
      }
    }

            typedef log-level {
              type enumeration {
                enum default {
                  value 9;
                  description
                    "default log level";
                }
                enum debug {
                  value 7;
                  description
                    "debug log level";
                }
                enum info {
                  value 6;
                  description
                    "info log level";
                }
                enum error {
                  value 3;
                  description
                    "error log level";
                }
                enum off {
                  value 0;
                  description
                    "turn off logging";
                }
              }
              description
                "log-level";
            }

  typedef service-context-id-id-choice {
    type string {
      pattern '[A-Za-z. 0-9@-]*' {
        error-message "Must contain only letters, digits, periods, spaces, dashes, and '@'";
      }
    }
    description
      "Provider specific DCCA service specification";
    tailf:info "[A-Za-z. 0-9@-]*";
  }

  typedef operator {
    type enumeration {
      enum lte {
        description
          "Less than or equal.";
      }
      enum gte {
        description
          "Greater than or equal.";
      }
      enum eq {
        description
          "Equal to.";
      }
      enum neq {
        description
          "Not equal to.";
      }
    }
    description
      "The source and destination port range definitions
       can be further qualified using an operator. An
       operator is needed only if lower-port is specified
       and upper-port is not specified. The operator
       therefore further qualifies lower-port only.";
  }

  grouping cp-block-allocation-type {
    leaf node {
      description
        "Block on node level";
      type empty;
    }
  }

  grouping dynamic-src-port-type {
    leaf port {
      description
        "Port range (default 49152-65535)";
      type string {
        pattern '[0-9]{1,5}[-][0-9]{1,5}' {
          error-message "Must be in the range 1 .. 65535";
        }
        length "1..11";
      }
    }
  }

  grouping locationarea-type {
    leaf name {
      description
        "Location area name";
      type string {
        pattern '[.0-9A-Za-z_-]*' {
          error-message "Must contain only letters, numbers, underscores or dashes";
        }
        length "1..64";
      }
    }
    list mcc-mnc {
      key "name";
      uses mccmnc-type;
    }
  }

  grouping mccmnc-type {
    leaf name {
      description
        "MccMnc value";
      type string {
        pattern '[0-9]{5,6}' {
          error-message "Mcc-Mnc is a string of 5 or 6 digits";
        }
      }
    }
    leaf-list tac {
      description
        "TAC value or TAC list";
      type uint16;
      max-elements 64;
    }
    leaf-list lac {
      description
        "LAC value or LAC list";
      type uint16;
      max-elements 64;
    }
  }

  grouping session-management-type {
    leaf dedicated-signaling-pdp {
      description
        "Enable session management for dedicated signaling PDP context";
      type empty;
    }
    leaf modify-delete-cause {
      description
        "Add proprietary delete-cause to delete request message and modify its value in the CDR";
      type empty;
    }
    leaf cause-code-in-manual-deletion {
      description
        "Include the Cause code(Reactivation requested) in Delete Bearer Request/Delete PDP Context Request message when a PDN connection is manually terminated";
      type empty;
    }
    leaf specific-action-in-pco {
      description
        "Add the container identifier indicates operator specific use (0xFF00) in Delete Bearer Request message";
      type empty;
    }
    container late-request-handling {
      description
        "Enable handling of late arriving GTPv2 Create Session Requests";
      presence "late-request-handling need presence";
      leaf no-timed-out-request-handling {
        description
          "Do not check upstream requests or downstream responses for Max Wait Time expiry (timed out)";
        type empty;
      }
      leaf maximum-wait-time {
        description
          "Set a default Maximum Wait Time value in milliseconds which will be used if the PGW doesn't receive both Maximum Wait Time and Origination Time Stamp";
        type uint16 {
          range "100..65535" {
            error-message "Invalid value for attribute 'maximum-wait-time'. Valid values are in range:[100,65535]";
          }
        }
      }
    }
    list pdp-type-control {
      description
        "PDP type control";
      key "name";
      leaf name {
        description
          "Name of PDP type control";
        type string {
          pattern '[0-9A-Za-z]{1,64}' {
            error-message "PDP type control name may consist of up to 64 letters and must contain only letters and numbers";
          }
        }
      }
      container plmn {
        description
          "IPv6 PLMN ID lists";
        presence "plmn need presence";
        choice ipv6_plmn {
          container ipv6-blacklist {
            description
              "All PLMN IDs in the blacklist will be blocked for IPv6 roaming";
            presence "ipv6-blacklist need presence";
            leaf-list plmn-id {
              description
                "Public Land Mobile Network identifier";
              type string {
                pattern '(([0-9]{5,6})|([*]))' {
                  error-message "PLMN identifier is a string of 5 or 6 digits or a wildchar '*'";
                }
              }
              ordered-by user;
            }
          }
          container ipv6-whitelist {
            description
              "All PLMN IDs in the whitelist will not be blocked for IPv6 roaming";
            presence "ipv6-whitelist need presence";
            leaf-list plmn-id {
              description
                "Public Land Mobile Network identifier";
              type string {
                pattern '[0-9]{5,6}' {
                  error-message "PLMN identifier is a string of 5 or 6 digits";
                }
              }
            }
          }
        }
      }
    }
  }

  grouping pdp-context-type {
    leaf limit {
      description
        "Maximum sum of active pgw-only bearers, combined PGW/SGW bearers, and PDP contexts";
      type uint32 {
        range "1..4294967295" {
          error-message "Invalid value for attribute 'limit'. Valid values are in range:[1,4294967295]";
        }
      }
      default "150000";
    }
    leaf emps-limit-percentage {
      description
        "emps limit in percentage";
      type uint8 {
        range "1..15" {
          error-message "Invalid value for attribute 'emps-limit-percentage'. Valid values are in range:[1,15]";
        }
      }
    }
    leaf update-through-create {
      description
        "Enables update of PDP context through create";
      type empty;
    }
    container failover-back-off-timer {
      description
        "Enable send Create Session Response message with cause code APN Congestion(113) during GSC failover";
      leaf value {
        description
          "Set value of the timer between 0 and 31.";
        type uint8 {
          range "0..31" {
            error-message "Invalid value for attribute 'value'. Valid values are in range:[0,31]";
          }
        }
      }
      leaf unit {
        description
          "Set incremental factor of the timer\\. Timer value is incremented in multiple of the configured unit.";
        type enumeration {
          enum 2-seconds {
            description
              "2 seconds";
          }
          enum minute {
            description
              "Minute";
          }
          enum 10-minutes {
            description
              "10 minutes";
          }
          enum hour {
            description
              "Hour";
          }
          enum 10-hours {
            description
              "10 hours";
          }
          enum infinite {
            description
              "Infinite";
          }
        }
      }
    }
    leaf host-route-limit {
      description
        "Limitation on number of host routes when address range is received from Radius";
      type uint32 {
        range "0..1000000" {
          error-message "Invalid value for attribute 'host-route-limit'. Valid values are in range:[0,1000000]";
        }
      }
      default "100000";
    }
    container icr {
      description
        "Enable ICR for SGi interface";
      presence "icr need presence";
      leaf tracked {
        description
          "Toggle to enable that an ICR switchover is triggered when the user plane routes of the SGi interface can't be detected";
        type empty;
      }
    }
    leaf tft-ratio {
      description
        "Number of PDP contexts subject to TFT handling";
      type uint8 {
        range "0..100" {
          error-message "Invalid value for attribute 'tft-ratio'. Valid values are in range:[0,100]";
        }
      }
    }
    leaf reserved-secondary-capacity {
      description
        "Reserved secondary PDP context capacity";
      type uint8 {
        range "0..5" {
          error-message "Invalid value for attribute 'reserved-secondary-capacity'. Valid values are in range:[0,5]";
        }
      }
    }
    leaf allow-secondary {
      description
        "Allow secondary contexts";
      type empty;
    }
    leaf no-same-ipv4v6-fallback-cause {
      description
        "Enable different ipv4v6 fallback cause on bearer";
      type empty;
    }
    leaf reject-request-without-valid-ue-id {
      description
        "Reject session request without valid IMSI or MSISDN value";
      type empty;
    }
    leaf identify-sender-by-plmn {
      description
        "Reject Modify Bearer Request & Update Pdp Context Request with invalid PLMN ID";
      type empty;
    }
    container handover-without-indication {
      description
        "Process Create Session Request without handover bit as Handover";
      presence "handover-without-indication need presence";
      leaf handover-timeout {
        description
          "Timer(in milliseconds) for switching user tunnel during wifi to lte handover";
        type uint16 {
          range "10..3000" {
            error-message "Invalid value for attribute 'handover-timeout'. Valid values are in range:[10,3000]";
          }
        }
        default "1000";
      }
    }
    container network-initiated {
      description
        "Network requested secondary PDP context configuration";
      leaf delay-secondary {
        description
          "Delay network initiated secondary PDP context request";
        type uint8 {
          range "0..10" {
            error-message "Invalid value for attribute 'delay-secondary'. Valid values are in range:[0,10]";
          }
        }
      }
      leaf ran-ready-timer {
        description
          "Timer for RAN procedure ready";
        type uint8 {
          range "1..5" {
            error-message "Invalid value for attribute 'ran-ready-timer'. Valid values are in range:[1,5]";
          }
        }
      }
    }
    container session-control {
      description
        "Session control settings";
      uses session-management-type;
    }
    container signaling {
      description
        "PDP context signaling settings";
      leaf session-creation-rate {
        description
          "Maximum number of session creation requests not related to handover, received on any interface, accepted per second\\. Session creation requests received when above the limit are rejected\\. The value states the total number handled by the node";
        type uint32 {
          range "50..500000" {
            error-message "Invalid value for attribute 'session-creation-rate'. Valid values are in range:[50,500000]";
          }
        }
      }
      leaf locally-initiated-delete-rate {
        description
          "Maximum number of locally initiated deletions per second\\. The value states the total number of deletes by the node\\. Overload protection in the node may lower the actual rate";
        type uint32 {
          range "50..500000" {
            error-message "Invalid value for attribute 'locally-initiated-delete-rate'. Valid values are in range:[50,500000]";
          }
        }
        default "40000";
      }
      leaf sgsn-create-request-window-size {
        description
          "Maximum number of outstanding create requests from SGSN";
        type uint16 {
          range "0..5000" {
            error-message "Invalid value for attribute 'sgsn-create-request-window-size'. Valid values are in range:[0,5000]";
          }
        }
      }
      leaf sgw-create-request-window-size {
        description
          "Maximum number of outstanding create requests from SGW";
        type uint16 {
          range "0..5000" {
            error-message "Invalid value for attribute 'sgw-create-request-window-size'. Valid values are in range:[0,5000]";
          }
        }
      }
      leaf sgw-create-sessions-per-second {
        description
          "Maximum SGW create session requests per second per session controller on the node";
        type uint16 {
          range "50..5000" {
            error-message "Invalid value for attribute 'sgw-create-sessions-per-second'. Valid values are in range:[50,5000]";
          }
        }
      }
      leaf sgw-modify-bearers-per-second {
        description
          "Maximum SGW modify bearer requests per second per session controller on the node";
        type uint32 {
          range "0..80000" {
            error-message "Invalid value for attribute 'sgw-modify-bearers-per-second'. Valid values are in range:[0,80000]";
          }
        }
      }
      leaf pfcp-modify-rate {
        description
          "Maximum pfcp modify requests per second on the node";
        type uint32 {
          range "50..100000" {
            error-message "Invalid value for attribute 'pfcp-modify-rate'. Valid values are in range:[50,100000]";
          }
        }
        default "4000";
      }
      list serving-node {
        description
          "Serving node to be throttled";
        max-elements 64;
        key "name";
        leaf name {
          description
            "IPv4 or IPv6 address of a serving node";
          type inet:ip-address;
        }
        leaf sgw-create-sessions-per-second {
          description
            "Maximum SGW create session requests per second per session controller on a specified SGW";
          type uint16 {
            range "50..5000" {
              error-message "Invalid value for attribute 'sgw-create-sessions-per-second'. Valid values are in range:[50,5000]";
            }
          }
        }
        leaf sgw-modify-bearers-per-second {
          description
            "Maximum SGW modify bearer requests per second per session controller on a specified SGW";
          type uint32 {
            range "0..80000" {
              error-message "Invalid value for attribute 'sgw-modify-bearers-per-second'. Valid values are in range:[0,80000]";
            }
          }
        }
      }
    }
    action terminate {
      yexte:user-group "ericsson-support,epg-admin";
      description
        "Terminate all PDP contexts on the node";
      output {
        leaf result {
          type string;
          mandatory true;
        }
      }
    }
    action terminate-stop {
      yexte:user-group "ericsson-support,epg-admin";
      description
        "Stop PDP contexts deletion process";
      status current {
        yexte:preliminary;
      }
      output {
        leaf result {
          type string;
          mandatory true;
        }
      }
    }
    action terminate-imsi {
      yexte:user-group "ericsson-support,epg-admin";
      description
        "Identifier for International Mobile Subscriber Identity";
      input {
        leaf imsi {
          description
            "Identifier for International Mobile Subscriber Identity";
          type string {
            pattern '([0-9]{5,15})|([0-9]{1,14}\*)' {
              error-message "ERROR: Invalid value for parameter imsi. Valid values are strings in a specified format. Type: imsi? for more information on the format to use.";
            }
            length "2..15";
          }
          mandatory true;
        }
      }
      output {
        leaf result {
          type string;
          mandatory true;
        }
      }
    }
    action terminate-imsi-nsapi {
      yexte:user-group "ericsson-support,epg-admin";
      description
        "Network layer service access point identifier";
      input {
        leaf imsi {
          description
            "Identifier for International Mobile Subscriber Identity";
          type string {
            pattern '([0-9]{5,15})|([0-9]{1,14}\*)' {
              error-message "ERROR: Invalid value for parameter imsi. Valid values are strings in a specified format. Type: imsi? for more information on the format to use.";
            }
            length "2..15";
          }
          mandatory true;
        }
        leaf nsapi {
          description
            "Network layer service access point identifier";
          type uint8 {
            range "0..15" {
              error-message "Invalid value for attribute 'nsapi'. Valid values are in range:[0,15]";
            }
          }
          mandatory true;
        }
      }
      output {
        leaf result {
          type string;
          mandatory true;
        }
      }
    }
    action terminate-msisdn {
      yexte:user-group "ericsson-support,epg-admin";
      description
        "Terminate context for Mobile Station Integrated Services Digital Network";
      input {
        leaf msisdn {
          description
            "Identifier for MSISDN";
          type string {
            pattern '[0-9]*' {
              error-message "ERROR: Invalid value for parameter msisdn. Valid values are strings in a specified format. Type: msisdn? for more information on the format to use.";
            }
            length "1..18";
          }
          mandatory true;
        }
      }
      output {
        leaf result {
          type string;
          mandatory true;
        }
      }
    }
  }

  grouping secm-type {
    container certm {
      description
        "Certificate management encompasses management of node credentials and trusted certificates";
      list node-credential {
        description
          "Represents the node credential and contains information about the corresponding certificate";
        key "name";
        leaf name {
          description
            "Node credential name";
          type string;
        }
        leaf subject-name {
          description
            "The X501 Distinguished Name that is used for the next enrollment";
          type string;
          mandatory true;
        }
        leaf expiry-alarm-threshold {
          description
            "Threshold value to calculate the date of the alarm indicating the coming expiry of the certificate";
          type uint16 {
            range "1..365" {
              error-message "Invalid value for attribute 'expiry-alarm-threshold'. Valid values are in range:[1,365]";
            }
          }
          default "30";
        }
        leaf key-info {
          description
            "Specifies the key type and length that is used for the next enrollment";
          type enumeration {
            enum rsa-1024 {
              description
                "RSA key length 1024";
            }
            enum rsa-2048 {
              description
                "RSA key length 2048";
            }
            enum rsa-3072 {
              description
                "RSA key length 3072";
            }
            enum rsa-4096 {
              description
                "RSA key length 4096";
            }
          }
          default "rsa-2048";
        }
        action install-credential-from-uri {
          description
            "Installs a node credential or certificate from the specified Uniform Resource Identifier (URI)";
          input {
            leaf uri {
              description
                "Uniform Resource Identifier";
              type string;
              mandatory true;
            }
          }
          output {
            leaf result {
              type string;
              mandatory true;
            }
          }
        }
        action start-offline-csr-enrollment {
          description
            "Starts a manual enrollment procedure";
          input {
            leaf uri {
              description
                "Uniform Resource Identifier";
              type string;
              mandatory true;
            }
          }
          output {
            leaf result {
              type string;
              mandatory true;
            }
          }
        }
        action certificate-content {
          description
            "The X.509 content of the certificate";
          output {
            leaf result {
              type string;
              mandatory true;
            }
          }
        }
      }
      list trust-category {
        description
          "Represents a trusted category";
        key "name";
        leaf name {
          description
            "The Trusted Category ID";
          type string;
        }
        leaf-list trusted-certificates {
          description
            "The list of Trusted Certificates that belongs to this trust category";
          type leafref {
            path "/epg/node/secm/certm/trusted-certificate/name";
          }
          max-elements 20;
        }
      }
      list trusted-certificate {
        description
          "Represents a trusted certificate";
        action install-trusted-cert-from-uri {
          description
            "Installs a trusted certificate from the specified Uniform Resource Identifier (URI)";
          input {
            leaf uri {
              description
                "Uniform Resource Identifier";
              type string;
              mandatory true;
            }
          }
          output {
            leaf result {
              type string;
              mandatory true;
            }
          }
        }
        action certificate-content {
          description
            "The X.509 content of the certificate";
          output {
            leaf result {
              type string;
              mandatory true;
            }
          }
        }
        key "name";
        leaf name {
          description
            "The Trusted Certificate ID";
          type string;
        }
      }
    }
  }

  grouping pcscfippool-type {
    leaf name {
      description
        "p-cscf IP pool name";
      type string {
        pattern '[._0-9A-Za-z-]{1,102}' {
          error-message "Must be a string of 102 or fewer characters and may contain letters, numbers, decimals and dashes.";
        }
      }
    }
    list server {
      description
        "IPv4 or IPv6 p-cscf server";
      max-elements 100;
      leaf priority {
        description
          "Priority specifying which of multiple configured servers is to be used first\\. A value from 1 to 999999, where a lower value takes precedence.";
        type string {
          pattern '[1-9][0-9]*' {
            error-message "String must match: ^[1-9][0-9]*$'";
          }
          length "1..6";
        }
        default "999999";
      }
      key "name";
      leaf name {
        description
          "IPv4 or IPv6 p-cscf server address";
        type inet:ip-address;
      }
      leaf weight {
        description
          "Enable configure weight-factors for one p-cscf server";
        type uint8 {
          range "1..10" {
            error-message "Invalid value for attribute 'weight'. Valid values are in range:[1,10]";
          }
        }
        default "1";
      }
    }
  }

  grouping rat-type-for-timeout-object {
    leaf name {
      description
        "Radio access technology (RAT) identifier";
      type enumeration {
        enum eutran {
          description
            "LTE/Evolved UMTS terrestrial radio access network";
        }
      }
    }
    leaf timeout {
      description
        "Maximum consecutive idle seconds for a context";
      type uint32 {
        range "0..4294920" {
          error-message "Invalid value for attribute 'timeout'. Valid values are in range:[0,4294920]";
        }
      }
      mandatory true;
    }
  }

  grouping sgsn-plmn-id-idle-timeout-type {
    leaf name {
      description
        "Public land mobile network name";
      type leafref {
        path "/epg/pgw/plmn/name";
      }
    }
    list plmn-id {
      description
        "PLMN ID of the SGSN";
      key "name";
      leaf name {
        description
          "SGSN public land mobile network identifier";
        type leafref {
          path "/epg/pgw/plmn[name=current()/../../name]/plmn-id/name";
        }
      }
      leaf timeout {
        description
          "Maximum consecutive idle seconds for a context";
        type uint32 {
          range "0..4294920" {
            error-message "Invalid value for attribute 'timeout'. Valid values are in range:[0,4294920]";
          }
        }
        mandatory true;
      }
      list rat-type {
        key "name";
        uses rat-type-for-timeout-object;
      }
    }
  }

  grouping sgsn-plmn-id-session-timeout-type {
    leaf name {
      description
        "Public land mobile network name";
      type leafref {
        path "/epg/pgw/plmn/name";
      }
    }
    list plmn-id {
      description
        "PLMN ID of the SGSN";
      key "name";
      leaf name {
        description
          "SGSN public land mobile network identifier";
        type leafref {
          path "/epg/pgw/plmn[name=current()/../../name]/plmn-id/name";
        }
      }
      leaf timeout {
        description
          "Maximum session duration seconds since creation. 0 means no-supervision";
        type uint32 {
          range "0..4294920" {
            error-message "Invalid value for attribute 'timeout'. Valid values are in range:[0,4294920]";
          }
        }
        mandatory true;
      }
    }
  }

  grouping flow-filter-type {
    leaf name {
      description
        "Filter id";
      type uint8 {
        range "1..16" {
          error-message "Invalid value for attribute 'filter-name'. Valid values are in range:[1,16]";
        }
      }
    }
    leaf remote-address {
      description
        "IPv4 or IPv6 address of the server, with an optional prefix";
      type eip-prefix-optional;
    }
    leaf remote-port {
      description
        "A port or a range of ports on the server";
      type string {
        pattern '((([1-9](([0-9]){0,3}))|([1-5](([0-9]){0,4}))|(6[0-4]([0-9]{3}))|(65[0-4]([0-9]{2}))|(655[0-2][0-9])|6553[0-5])(-((([1-9](([0-9]){0,3}))|([1-5](([0-9]){0,4}))|(6[0-4]([0-9]{3}))|(65[0-4]([0-9]{2}))|(655[0-2][0-9])|6553[0-5])))?)' {
          error-message "Value must be a number from 1 to 65535 or a range";
        }
      }
    }
    leaf local-port {
      description
        "A port or a range of ports on the UE";
      type string {
        pattern '((([1-9](([0-9]){0,3}))|([1-5](([0-9]){0,4}))|(6[0-4]([0-9]{3}))|(65[0-4]([0-9]{2}))|(655[0-2][0-9])|6553[0-5])(-((([1-9](([0-9]){0,3}))|([1-5](([0-9]){0,4}))|(6[0-4]([0-9]{3}))|(65[0-4]([0-9]{2}))|(655[0-2][0-9])|6553[0-5])))?)' {
          error-message "Value must be a number from 1 to 65535 or a range";
        }
      }
    }
    leaf protocol-number {
      description
        "Protocol to match";
      type union {
        type enumeration {
          enum tcp {
            description
              "Transmission Control Protocol";
          }
          enum udp {
            description
              "User Datagram Protocol";
          }
          enum gre {
            description
              "Generic routing encapsulation";
          }
          enum esp {
            description
              "IPSec Encapsulating Security Payload";
          }
          enum ah {
            description
              "IP Security authentication header";
          }
          enum sctp {
            description
              "Stream Control Transmission Protocol";
          }
        }
        type protocol-number-number-choice;
      }
    }
    leaf dscp {
      description
        "DSCP";
      type enumeration {
        enum af11 {
          description
            "Assured forwarding class 1, low drop precedence";
        }
        enum af12 {
          description
            "Assured forwarding class 1, medium drop precedence";
        }
        enum af13 {
          description
            "Assured forwarding class 1, high drop precedence";
        }
        enum af21 {
          description
            "Assured forwarding class 2, low drop precedence";
        }
        enum af22 {
          description
            "Assured forwarding class 2, medium drop precedence";
        }
        enum af23 {
          description
            "Assured forwarding class 2, high drop precedence";
        }
        enum af31 {
          description
            "Assured forwarding class 3, low drop precedence";
        }
        enum af32 {
          description
            "Assured forwarding class 3, medium drop precedence";
        }
        enum af33 {
          description
            "Assured forwarding class 3, high drop precedence";
        }
        enum af41 {
          description
            "Assured forwarding class 4, low drop precedence";
        }
        enum af42 {
          description
            "Assured forwarding class 4, medium drop precedence";
        }
        enum af43 {
          description
            "Assured forwarding class 4, high drop precedence";
        }
        enum ef {
          description
            "Expedited forwarding";
        }
        enum be {
          description
            "Best effort forwarding";
        }
        enum cs1 {
          description
            "Class selector 1";
        }
        enum cs2 {
          description
            "Class selector 2";
        }
        enum cs3 {
          description
            "Class selector 3";
        }
        enum cs4 {
          description
            "Class selector 4";
        }
        enum cs5 {
          description
            "Class selector 5";
        }
        enum cs6 {
          description
            "Class selector 6";
        }
        enum cs7 {
          description
            "Class selector 7";
        }
      }
    }
  }

  grouping selection-condition-data-network-type {
    leaf name {
      description
        "Data network name";
      type string {
        pattern '[.0-9A-Za-z_-]*' {
          error-message "Must contain only letters, numbers, underscores or dashes";
        }
        length "1..64";
      }
    }
  }

  grouping selection-condition-area-id-type {
    leaf name {
      description
        "Area Id";
      type string {
        pattern '[.0-9A-Za-z_-]*' {
          error-message "Must contain only letters, numbers, underscores or dashes";
        }
        length "1..64";
      }
    }
  }

  grouping redirect-set-type {
    leaf name {
      description
        "Original destination address";
      type inet:ipv4-address;
    }
    leaf destination-address {
      description
        "Redirection destination address";
      type inet:ipv4-address;
      mandatory true;
    }
  }

  grouping session-management-apn-type {
    leaf exclude-dedicated-signaling {
      description
        "Exclude dedicated signaling from session management handling";
      type empty;
    }
    leaf cause-code-in-pdn-deletion {
      description
        "Include the Cause code(Reactivation Requested) in Delete Bearer Request message when PGW trigger LTE PDN connection deletion.";
      type empty;
    }
    leaf suppress-update-at-handover {
      description
        "Do not send an Update Bearer Request with authorized QoS after a handover to SGW from SGSN or from SGW";
      type empty;
    }
    container idle-timeout {
      description
        "Idle timeout settings";
      presence "idle-timeout need presence";
      container dedicated-bearer {
        description
          "Dedicated bearer timeout settings";
        presence "dedicated-bearer need presence";
        leaf timeout {
          description
            "Maximum consecutive idle seconds for a dedicated-bearer";
          type uint32 {
            range "0..4294920" {
              error-message "Invalid value for attribute 'timeout'. Valid values are in range:[0,4294920]";
            }
          }
        }
        list qci {
          description
            "qci for dedicated bearer settings";
          key "name";
          leaf name {
            description
              "Qci index for dedicated bearer ";
            type uint8 {
              range "1..254" {
                error-message "Invalid value for attribute 'qci-index'. Valid values are in range:[1,254]";
              }
            }
          }
          leaf timeout {
            description
              "Maximum consecutive idle seconds for a qci";
            type uint32 {
              range "0..4294920" {
                error-message "Invalid value for attribute 'timeout'. Valid values are in range:[0,4294920]";
              }
            }
          }
        }
      }
      container radius {
        description
          "Timeout settings based on RADIUS";
        presence "radius need presence";
        leaf use-timeout {
          description
            "Use idle timeout received from RADIUS";
          type empty;
        }
      }
      container aaa {
        description
          "Timeout settings based on AAA";
        presence "aaa need presence";
        leaf use-timeout {
          description
            "Use idle timeout received from AAA";
          type empty;
        }
      }
      container sgsn-plmn-id {
        description
          "Timeout settings based on SGSN PLMN IDs";
        presence "sgsn-plmn-id need presence";
        list plmn {
          key "name";
          uses sgsn-plmn-id-idle-timeout-type;
        }
      }
      container roaming {
        description
          "Timeout settings based on roaming";
        presence "roaming need presence";
        leaf timeout {
          description
            "Maximum consecutive idle seconds for a context";
          type uint32 {
            range "0..4294920" {
              error-message "Invalid value for attribute 'timeout'. Valid values are in range:[0,4294920]";
            }
          }
        }
        list rat-type {
          must '/epg/pgw/apn[name=current()/../../../../../name]/pdp-context/session-control/idle-timeout/roaming/timeout' {
            error-message "Timeout settings without Rat-Type must be configured";
          }
          key "name";
          uses rat-type-for-timeout-object;
        }
      }
      container default {
        description
          "Default timeout settings";
        presence "default need presence";
        leaf timeout {
          description
            "Maximum consecutive idle seconds for a context";
          type uint32 {
            range "0..4294920" {
              error-message "Invalid value for attribute 'timeout'. Valid values are in range:[0,4294920]";
            }
          }
        }
        list rat-type {
          must '/epg/pgw/apn[name=current()/../../../../../name]/pdp-context/session-control/idle-timeout/default/timeout' {
            error-message "Timeout settings without Rat-Type must be configured";
          }
          key "name";
          uses rat-type-for-timeout-object;
        }
      }
    }
    container session-timeout {
      description
        "Session timeout settings";
      presence "session-timeout need presence";
      leaf idle-check {
        description
          "Idle session check setting for long session deletion";
        type enumeration {
          enum no-dedicated-bearer {
            description
              "Recognize as an idle session if there's no dedicated bearer for a session";
          }
          enum preservation-information {
            description
              "Recognize as an idle session if PreservationInformation from SGSN or ECM_Idle from SGW is received";
          }
        }
      }
      container radius {
        description
          "Timeout settings based on RADIUS";
        presence "radius need presence";
        leaf use-timeout {
          description
            "Use session timeout received from RADIUS";
          type empty;
        }
      }
      container aaa {
        description
          "Timeout settings based on AAA";
        presence "aaa need presence";
        leaf use-timeout {
          description
            "Use session timeout received from AAA";
          type empty;
        }
      }
      container sgsn-plmn-id {
        description
          "Timeout settings based on SGSN PLMN IDs";
        presence "sgsn-plmn-id need presence";
        list plmn {
          key "name";
          uses sgsn-plmn-id-session-timeout-type;
        }
      }
      container roaming {
        description
          "Timeout settings based on roaming";
        presence "roaming need presence";
        leaf timeout {
          description
            "Maximum session duration seconds since creation. 0 means no-supervision";
          type uint32 {
            range "0..4294920" {
              error-message "Invalid value for attribute 'timeout'. Valid values are in range:[0,4294920]";
            }
          }
        }
      }
      container default {
        description
          "Default timeout settings";
        presence "default need presence";
        leaf timeout {
          description
            "Maximum session duration seconds since creation. 0 means no-supervision";
          type uint32 {
            range "0..4294920" {
              error-message "Invalid value for attribute 'timeout'. Valid values are in range:[0,4294920]";
            }
          }
        }
      }
    }
    leaf pdp-type-control {
      description
        "Name of PDP type control";
      type leafref {
        path "/epg/pgw/pdp-context/session-control/pdp-type-control/name";
      }
    }
  }

  grouping lns-server-type {
    leaf priority {
      description
        "Priority specifying which of multiple configured servers is to be used first\\. A value from 1 to 999999, where a lower value takes precedence.";
      type string {
        pattern '[1-9][0-9]*' {
          error-message "String must match: ^[1-9][0-9]*$'";
        }
        length "1..6";
      }
      default "999999";
    }
    leaf name {
      description
        "L2TP network server address";
      type inet:ipv4-address;
    }
    choice lns-port {
      leaf use-default-port {
        description
          "Use default port";
        type empty;
      }
      leaf port {
        description
          "L2TP network server destination port";
        type uint16;
      }
    }
    leaf max-ppp-sessions {
      description
        "Maximum number of simultaneous PPP sessions allowed";
      type uint16 {
        range "1..65000" {
          error-message "Invalid value for attribute 'max-ppp-sessions'. Valid values are in range:[1,65000]";
        }
      }
    }
  }

  grouping name-server-type {
    leaf priority {
      description
        "Priority specifying which of multiple configured name servers is to be used first\\. A value from 1 to 999999, where a lower value takes precedence.";
      type string {
        pattern '[1-9][0-9]*' {
          error-message "String must match: ^[1-9][0-9]*$'";
        }
        length "1..6";
      }
      default "999999";
    }
    leaf name {
      description
        "IPv4 DNS name server address";
      type inet:ipv4-address;
    }
  }

  grouping ipv6-name-server-type {
    leaf priority {
      description
        "Priority specifying which of multiple configured name servers is to be used first\\. A value from 1 to 999999, where a lower value takes precedence.";
      type string {
        pattern '[1-9][0-9]*' {
          error-message "String must match: ^[1-9][0-9]*$'";
        }
        length "1..6";
      }
      default "999999";
    }
    leaf name {
      description
        "IPv6 DNS name server address";
      type inet:ipv6-address;
    }
  }

  grouping netbios-name-server-type {
    leaf name {
      description
        "IPv4 netbios server address";
      type eipv4-prefix-optional;
    }
  }

  grouping rate-type-subscription-type {
    leaf name {
      description
        "Radio access technology (RAT) identifier";
      type common-rat-type;
    }
    leaf-list subscription-id {
      description
        "Subscription identifier";
      type enumeration {
        enum msisdn {
          description
            "Use MSISDN as subscription identifier";
        }
        enum nai {
          description
            "Use NAI as subscription identifier";
        }
        enum imsi {
          description
            "Use IMSI as subscription identifier";
        }
      }
    }
  }

  grouping gx-profile-type {
    leaf name {
      description
        "Profile identifier";
      type string {
        pattern '[.0-9A-Za-z_-]*' {
          error-message "Must contain only letters, numbers, underscores or dashes";
        }
        length "1..256";
      }
    }
    leaf diameter-application-system {
      description
        "Diameter application system";
      type leafref {
        path "/epg/pgw/diameter/diameter-application-system/name";
      }
      mandatory true;
    }
    leaf-list subscription-id {
      description
        "Subscription identifier";
      type enumeration {
        enum msisdn {
          description
            "Use MSISDN as subscription identifier";
        }
        enum nai {
          description
            "Use NAI as subscription identifier";
        }
        enum imsi {
          description
            "Use IMSI as subscription identifier";
        }
      }
    }
    list rat-type {
      key "name";
      uses rate-type-subscription-type;
    }
    leaf add-leading-digit {
      description
        "Add leading digit in user name of CCR messages";
      type empty;
    }
    leaf always-include-ms-timezone {
      description
        "Include 3gpp-MS-Timezone in all CCR messages";
      type empty;
    }
    leaf always-include-plmn {
      description
        "Include 3gpp-SGSN-MCC-MNC in all CCR messages";
      type empty;
    }
    leaf always-include-subscription-id {
      description
        "Include subscription-id in all CCR messages";
      type empty;
    }
    leaf always-include-user-location-info {
      description
        "Include 3gpp-user-location-information in all CCR messages";
      type empty;
    }
    leaf always-include-called-station-id {
      description
        "Include called-station-id in all CCR messages";
      type empty;
    }
    leaf always-include-rat-type {
      description
        "Include rat-type in all CCR messages";
      type empty;
    }
    leaf include-bearer-usage-on-wlan {
      description
        "Include 3GPP Bearer Usage AVP in ccr-i for WLAN";
      type empty;
    }
    leaf qos-change-provisioning-required {
      description
        "Require event trigger provisioning for reporting qos-change";
      type empty;
    }
    leaf extend-apn-with-domain {
      description
        "Prepend domain extracted from PAP/CHAP in PCO to the called-station-id";
      type empty;
    }
    leaf p-cscf-restoration-enhancement {
      description
        "Indicate support of pcrf-based p-cscf restoration";
      type empty;
    }
    leaf suppress-update-at-handover {
      description
        "Do not send an Update Bearer Request with authorized QoS after a handover to SGW from SGSN or from SGW";
      type empty;
      status deprecated;
    }
    leaf disable-bitrate-optimization {
      description
        "Always reserve bitrates for dynamic PCC rules even when flow-status is set to DISABLED";
      type empty;
    }
    leaf pcc-imei-encoding {
      description
        "pcc-imei-encoding";
      type enumeration {
        enum 3gpp-rel6 {
          description
            "3GPP-rel6 output format BCD";
        }
      }
    }
    container charging-control {
      description
        "Enable/disable charging control";
      presence "charging-control need presence";
      leaf online {
        description
          "Enable/Disable online charging";
        type enumeration {
          enum enable {
            description
              "Enable online charging";
          }
          enum disable {
            description
              "Disable online charging";
          }
        }
      }
    }
    container charging-characteristics {
      description
        "Include 3GPP charging-characteristics AVP in CCR";
      must 'not (../disable-gx-extensions)' {
        error-message "Incompatible with disable-gx-extensions";
      }
      presence "charging-characteristics need presence";
      leaf initial {
        description
          "Include 3GPP charging-characteristics in ccr-i";
        type empty;
      }
      leaf update {
        description
          "Include 3GPP charging-characteristics in ccr-u";
        type empty;
      }
    }
    leaf late-request-handling {
      description
        "Include origination-time-stamp and maximum-wait-time AVPs in ccr-i";
      type empty;
    }
    leaf location-change-reporting {
      description
        "Enable Location Change Reporting feature on the Gx profile";
      type empty;
    }
    leaf u-wlan-user-equipment-info {
      description
        "user-equipment-info type for untrusted WLAN access";
      type enumeration {
        enum imeisv {
          description
            "Use IMEISV as user-equipment-info type";
        }
        enum mac {
          description
            "Use MAC as user-equipment-info type to carry MAC address info of wifi access point in ccr-i/u";
        }
      }
    }
    leaf user-equipment-info-in-ccru {
      description
        "Include user-equipment-info in ccr-u";
      type empty;
    }
    leaf allow-rules-with-missing-bitrates {
      description
        "Allow installation of dynamic rules missing one or more bitrates";
      type empty;
    }
    leaf disable-gx-extensions {
      description
        "Do not allow use of Gx+ extensions";
      type empty;
      must 'not (../charging-characteristics)' {
        error-message "Incompatible with charging-characteristics";
      }
    }
    leaf disable-supported-features-id-2 {
      description
        "Only send one instance of the Supported-Features AVP";
      type empty;
      status deprecated;
    }
    leaf netloc {
      description
        "Enable NetLoc";
      type empty;
    }
    container monitoring-key {
      description
        "Control the handing of the Monitoring-Key AVP";
      leaf encoding {
        type enumeration {
          enum "ascii" {
            description
              "The Monitoring Key is encoded as an ASCII string";
          }
          enum "binary" {
            description
              "The Monitoring Key is encoded as an unsigned 32-bit integer";
          }
        }
        default "ascii";
      }
    }
    leaf csg-reporting {
      description
        "Enable CSG information reporting to PCRF";
      type empty;
    }
    leaf netlocuwan {
      description
        "Enable netloc-untrusted-wlan";
      type empty;
      must '../netloc' {
        error-message "NetLoc feature must be supported first";
      }
    }
    leaf extended-usage-monitoring {
      description
        "Enable usage monitoring at interim update";
      type empty;
      must "not (../pcc-release[text()='7'])" {
        error-message "Can not configure both extended-usage-monitoring and pcc-release 7 at the same time";
        tailf:dependency "../pcc-release";
      }
    }
    leaf pcc-release {
      description
        "Configure the PCC release to use";
      type enumeration {
        enum 8 {
          description
            "Gx PCC release 8";
        }
        enum 9 {
          description
            "Gx PCC release 9";
        }
        enum limited-10 {
          description
            "Gx PCC release 10 (limited)";
        }
      }
      must "not ((../pcc-release[text()='7']) and (../extended-usage-monitoring))" {
        error-message "Gx PCC Release 7 is not compatible with extended-usage-monitoring";
        tailf:dependency "../pcc-release";
      }
    }
    leaf disable-apn-ambr-mediation {
      description
        "Disables APN AMBR mediation in the PGW, allowing the SGSN to change APN AMBR.";
      type empty;
      must 'not (../no-override-authorized-qos)' {
        error-message "disable-apn-ambr-mediation is incompatible with no-override-authorized-qos";
      }
    }
    leaf rat-type-for-ehrpd {
      description
        "Define rat-type for eHRPD access";
      type enumeration {
        enum hrpd {
          description
            "Send HRPD as rat-type for eHRPD access";
        }
        enum ehrpd {
          description
            "Send eHRPD as rat-type for eHRPD access";
        }
      }
      status deprecated;
    }
    leaf ip-can-type-for-cdma {
      description
        "Define ip-can type for CDMA access";
      type enumeration {
        enum non-3gpp-eps {
          description
            "Non-3gpp eps";
        }
        enum 3gpp2 {
          description
            "3gpp2";
        }
      }
    }
    leaf no-override-authorized-qos {
      description
        "Disable the overriding of PCRF QoS setting";
      type empty;
      status deprecated;
    }
    leaf no-crr-in-raa {
      description
        "Disable sending of Charging-Rule-Reports in RAA messages";
      type empty;
    }
    leaf no-cdma-bsid {
      description
        "Do not include 3gpp2-bsid AVP in Credit Control Requests";
      type empty;
    }
    leaf no-cdma-user-equipment-info {
      description
        "Do not include user-equipment-info AVP in Credit Control Requests for PMIPv6 S2a access";
      type empty;
    }
    leaf select-requested-apn {
      description
        "Use requested APN name in Credit Control Requests";
      type empty;
      status deprecated;
      must 'not (../select-apn)' {
        error-message "Incompatible with 'select-apn'";
      }
    }
    leaf select-apn {
      description
        "Select Apn name sent in Credit Control Requests";
      must 'not (../select-requested-apn)' {
        error-message "Incompatible with 'select-requested-apn'";
      }
      type enumeration {
        enum logical {
          description
            "Logical APN name";
        }
        enum requested {
          description
            "Requested APN name";
        }
        enum used {
          description
            "Used APN name";
        }
        enum reported {
          description
            "Reported APN name";
        }
      }
    }
    leaf send-ccr-on-activate {
      description
        "Send CCR update on activate on the selected interface";
      type enumeration {
        enum s5 {
          description
            "S5 interface";
        }
        enum gn {
          description
            "Gn interface";
        }
        enum s5gn {
          description
            "S5 and Gn interface";
        }
      }
    }
    container cca-avp {
      description
        "Settings for optional attributes in Gx credit control responses";
      list custom-attribute {
        description
          "Custom attribute";
        max-elements 64;
        key "name";
        uses custom-attribute-type;
      }
      container rule-space-decision {
        description
          "Settings for rule-space decision avp";
        leaf custom-attribute {
          description
            "Name of rule-space-decision custom attribute";
          type string {
            length "1..64";
          }
        }
      }
    }
    container ccr-avp {
      description
        "Settings for optional attributes in Gx credit control requests";
      presence "ccr-avp need presence";
      leaf rule-space-suggestion {
        description
          "Send value of currently selected parameter as rule-space-suggestion to PCRF";
        must 'not (../rule-space-decision)' {
          error-message "Incompatible with 'rule-space-decision'";
        }
        type enumeration {
          enum policy-charging-rule-scope {
            description
              "Policy and Charging rule scope";
          }
        }
      }
      leaf rule-space-decision {
        description
          "Send value of currently selected parameter as rule-space-decision to PCRF";
        must 'not (../rule-space-suggestion)' {
          error-message "Incompatible with 'rule-space-suggestion'";
        }
        type enumeration {
          enum policy-charging-rule-scope {
            description
              "Policy and Charging rule scope";
          }
        }
      }
      container rat-type-map {
        description
          "Defines rat type mapping";
        list from {
          description
            "Original RAT type identifier to map from";
          key "name";
          uses rat-map-type;
        }
      }
    }
    container rar-avp {
      description
        "Settings for optional attributes in Gx reauthorization requests";
      list custom-attribute {
        description
          "Custom attribute";
        max-elements 64;
        key "name";
        uses custom-attribute-type;
      }
    }
    leaf failure-profile {
      description
        "Failure profile to use";
      type leafref {
        path "/epg/pgw/policy-control/gx-failure-profile/name";
      }
    }
    container dynamic-rule {
      leaf immediate-credit-control {
        description
          "Immediate credit control for dynamic charging rules";
        type empty;
      }
    }
    leaf disable-non-optimized-rar {
      description
        "Disables non-optimized RAR support.";
      type empty;
    }
  }

  grouping gy-profile-type {
    leaf name {
      description
        "Profile identifier";
      type string {
        pattern '[.0-9A-Za-z_-]*' {
          error-message "Must contain only letters, numbers, underscores or dashes";
        }
        length "1..256";
      }
    }
    leaf diameter-application-system {
      description
        "Diameter application system";
      type leafref {
        path "/epg/pgw/diameter/diameter-application-system/name";
      }
      mandatory true;
    }
    leaf-list additional-allowed-das {
      description
        "Additional diameter application systems within which the PCRF can select an OCS";
      type leafref {
        path "/epg/pgw/diameter/diameter-application-system/name";
      }
      max-elements 16;
    }
    leaf service-context-id {
      description
        "Credit control service specification";
      type union {
        type enumeration {
          enum 8.32251@3gpp.org {
            description
              "3GPP Gy release 8 service specification";
          }
          enum 12.32251@3gpp.org {
            description
              "3GPP Gy release 12 service specification";
          }
          enum 13.32251@3gpp.org {
            description
              "3GPP Gy release 13 service specification";
          }
          enum 15.32251@3gpp.org {
            description
              "3GPP Gy release 15 service specification";
          }
          enum v2.gy.ggsn@ericsson.com {
            description
              "Ericsson Gy version 2 service specification";
          }
          enum v3.gy.ggsn@ericsson.com {
            description
              "Ericsson Gy version 3 service specification";
          }
          enum v4.gy.ggsn@ericsson.com {
            description
              "Ericsson Gy version 4 service specification";
          }
          enum pgw.15.32251@ericsson.com {
            description
              "Ericsson Gy version 15 service specification";
          }
        }
        type service-context-id-id-choice;
      }
      mandatory true;
    }
    leaf ccr-context-id {
      description
        "Provider specific DCCA service-context-id AVP to include in credit control requests";
      type string {
        length "1..80";
      }
    }
    container ccr-avp {
      description
        "Settings for optional attributes in Gy credit control requests";
      presence "ccr-avp need presence";
      leaf no-user-plmn-id {
        description
          "Do not include 3GPP-IMSI-MCC-MNC AVP in credit control requests";
        type empty;
      }
      leaf no-ggsn-plmn-id {
        description
          "Do not include 3GPP-GGSN-MCC-MNC AVP in credit control requests";
        type empty;
      }
      leaf no-threegpp2-bsid {
        description
          "Do not include 3GPP2-BSID AVP in credit control requests for PMIPv6 S2a access";
        type empty;
      }
      leaf cdma-selection-mode {
        description
          "Include 3GPP-Selection-Mode AVP in credit control requests for PMIPv6 S2a access";
        type empty;
      }
      leaf no-cdma-user-equipment-info {
        description
          "Do not include user-equipment-info AVP in credit control requests for PMIPv6 S2a access";
        type empty;
      }
      leaf select-apn {
        description
          "Select APN name sent in Credit Control Requests";
        type enumeration {
          enum logical {
            description
              "Logical APN name";
          }
          enum requested {
            description
              "Requested APN name";
          }
          enum used {
            description
              "Used APN name";
          }
          enum reported {
            description
              "Reported APN name";
          }
        }
      }
      leaf no-pdp-context-type {
        description
          "Do not include pdp-context-type AVP within ps-information AVP in credit control requests";
        type empty;
      }
      leaf default-trigger-format {
        description
          "Type of default trigger format to include in credit control requests";
        type enumeration {
          enum trigger {
            description
              "Use Trigger AVP as trigger format";
          }
          enum trigger-type {
            description
              "Use trigger-type AVP as trigger format";
          }
        }
      }
      leaf ps-previous-information {
        description
          "Include ps-previous-information AVP in credit control requests";
        type empty;
      }
      leaf no-pdn-connection-id {
        description
          "Do not include pdn-connection-id AVP under ps-information AVP in credit control requests";
        type empty;
      }
      leaf no-ps-information-qos-information {
        description
          "Do not include qos-information AVP under ps-information AVP in credit control requests";
        type empty;
      }
      leaf no-ps-information-start-time {
        description
          "Do not include start-time AVP under ps-information AVP in credit control requests";
        type empty;
      }
      leaf no-ps-information-stop-time {
        description
          "Do not include stop-time AVP under ps-information AVP in credit control requests";
        type empty;
      }
      leaf mscc-qos-information {
        description
          "Include qos-information AVP within MSCC AVP in credit control requests";
        type empty;
      }
      container mscc-service-identifier {
        description
          "Options for including a preconfigured service identifier within MSCC AVP in credit control requests";
        leaf rating-group-id {
          description
            "Use the rating group identifier as the value of the service identifier";
          type empty;
          must 'not (../service-id)' {
            error-message "rating-group-id and service-id options are exclusive. Only one can be configured.";
          }
        }
        leaf service-id {
          description
            "Value used as the service identifier";
          type uint32;
          must 'not (../rating-group-id)' {
            error-message "rating-group-id and service-id options are exclusive. Only one can be configured.";
          }
        }
      }
      leaf win-service-type {
        status current {
          yexte:preliminary;
        }
        description
          "Include win-service-type AVP in credit control requests";
        type empty;
      }
      leaf u-wlan-user-equipment-info {
        description
          "Type of user-equipment-info AVP to include in credit control requests";
        type enumeration {
          enum imeisv {
            description
              "Use international mobile station equipment identity as user-equipment-info AVP";
          }
          enum mac {
            description
              "Use media access control address as user-equipment-info AVP";
          }
        }
      }
      leaf user-name {
        description
          "Type of user-name AVP to include in credit control requests";
        type enumeration {
          enum imsi {
            description
              "Use international mobile subscriber identity as user-name AVP";
          }
          enum nai {
            description
              "Use network access identifier as user-name AVP";
          }
        }
      }
      leaf subscription-id {
        description
          "Type of subscription-id AVP to include in credit control requests";
        type enumeration {
          enum imsi {
            description
              "Use international mobile subscriber identity as subscription-id AVP";
          }
          enum msisdn {
            description
              "Use mobile station international subscriber directory number as subscription-id AVP";
          }
          enum nai {
            description
              "Use network access identifier as subscription-id AVP";
          }
        }
      }
      leaf charging-rule-base-name {
        description
          "Include charging-rule-base-name AVP in credit control requests";
        type enumeration {
          enum pcc-rule-group {
            description
              "Use a pcc rule group as charging-rule-base-name AVP";
          }
          enum policy-charging-rule-scope {
            description
              "Use the selected policy charging rule scope as charging-rule-base-name AVP";
          }
        }
      }
      leaf sgsn-address {
        description
          "Include only preferred sgsn address types in sgsn-address AVP under ps-information AVP in credit control requests";
        type enumeration {
          enum ipv4 {
            description
              "Prefer to only include ipv4 address in sgsn-address AVP";
          }
          enum ipv6 {
            description
              "Prefer to only include ipv6 address in sgsn-address AVP";
          }
          enum ipv4v6 {
            description
              "Prefer to include both ipv4 and ipv6 address in sgsn-address AVP";
          }
        }
      }
      leaf ggsn-address {
        description
          "Include only preferred ggsn address types in ggsn-address AVP under ps-information AVP in credit control requests";
        type enumeration {
          enum ipv4 {
            description
              "Prefer to only include ipv4 address in ggsn-address AVP";
          }
          enum ipv6 {
            description
              "Prefer to only include ipv6 address in ggsn-address AVP";
          }
          enum ipv4v6 {
            description
              "Prefer to include both ipv4 and ipv6 address in ggsn-address AVP";
          }
        }
      }
      leaf no-presence-reporting-area {
        description
          "Do not include presence-reporting-area AVP under ps-information AVP in credit control requests";
        type empty;
      }
      leaf ps-information-uni-pdu-cp-only-flag {
        description
          "Include uni-pdu-cp-only-flag AVP under ps-information AVP in credit control requests";
        type empty;
      }
      leaf service-id-level-reporting {
        description
          "Include si-level reporting information.";
        type empty;
        must 'not ((../mscc-service-identifier/rating-group-id) or (../mscc-service-identifier/service-id))' {
          error-message "Incompatible with mscc-service-identifier options";
        }
      }
      leaf used-service-unit-time-usage {
        description
          "Include time-first-usage and time-last-usage AVPs under USU AVP in credit control requests when volume based charging is enabled";
        type empty;
      }
      leaf transaction-report {
        status current {
          yexte:preliminary;
        }
        description
          "Include transaction report information";
        type empty;
      }
      leaf rule-space-suggestion {
        description
          "Send value of currently selected parameter as rule-space-suggestion to OCS";
        must 'not (../rule-space-decision)' {
          error-message "Incompatible with 'rule-space-decision'";
        }
        type enumeration {
          enum policy-charging-rule-scope {
            description
              "Policy and Charging rule scope";
          }
        }
      }
      leaf rule-space-decision {
        description
          "Send value of currently selected parameter as rule-space-decision to OCS";
        must 'not (../rule-space-suggestion)' {
          error-message "Incompatible with 'rule-space-suggestion'";
        }
        type enumeration {
          enum policy-charging-rule-scope {
            description
              "Policy and Charging rule scope";
          }
        }
      }
      container rat-type-map {
        description
          "Defines rat type mapping";
        list from {
          description
            "Original RAT type identifier to map from";
          key "name";
          uses rat-map-type;
        }
      }
    }
    choice preemptive-reservation-choice {
      leaf preemptive-reservation {
        description
          "Accept preemptive, unsolicited quota reservation from the OCS";
        type empty;
      }
      leaf no-preemptive-reservation {
        description
          "Do not accept preemptive, unsolicited quota reservation from the OCS";
        type empty;
      }
    }
    container establish {
      leaf initial-attach {
        description
          "Establish a credit control session at initial attach";
        type empty;
      }
    }
    container cca-avp {
      description
        "Settings for optional attributes in Gy credit control responses";
      list custom-attribute {
        description
          "Custom attribute";
        max-elements 64;
        key "name";
        uses custom-attribute-type;
      }
      container rule-space-decision {
        description
          "Settings for rule-space decision avp";
        status current {
          yexte:preliminary;
        }
        leaf custom-attribute {
          description
            "Name of rule-space-decision custom attribute";
          type string {
            length "1..64";
          }
        }
      }
    }
    container rar-avp {
      description
        "Settings for optional attributes in Gy reauthorization requests";
      list custom-attribute {
        description
          "Custom attribute";
        max-elements 64;
        key "name";
        uses custom-attribute-type;
      }
    }
    leaf failure-profile {
      description
        "Failure profile to use";
      type leafref {
        path "../../gy-failure-profile/name";
      }
    }
  }

  grouping ue2ue-unblockedrange-type {
    leaf name {
      description
        "UE to UE Unblocked Range name";
      type string {
        pattern '[.0-9A-Za-z_-]*' {
          error-message "Ue to Ue unblocked range name, can consist of up to 100 characters of letters, digits or dashes";
        }
        length "1..100";
      }
    }
    leaf-list address {
      description
        "Ue to Ue filtering address range";
      type eipv4-prefix-optional;
      max-elements 32;
    }
  }

  grouping rat-map-type {
    leaf name {
      description
        "RAT type identifier to be mapped";
      type common-rat-type-extend;
    }
    leaf to {
      description
        "RAT type identifier to map to";
      type common-rat-type-extend;
      mandatory true;
    }
  }

  grouping apn-type {
    leaf name {
      description
        "Access point name";
      type string {
        pattern '[.0-9A-Za-z-]{1,100}' {
          error-message "Must be a string of 100 or fewer characters and may contain letters, numbers, decimals and dashes.";
        }
      }
    }
    leaf network-instance {
      description
        "Network instance for core interface";
      status current {
        yexte:preliminary;
      }
      type string;
    }
    container location {
      description
        "Location configuration";
      presence "location need presence";
      leaf location-based-ip-allocation {
        description
          "Enable location based IP address allocation on APN level";
        type empty;
        must "(/epg/pgw/apn[name=current()/../../name]/pdp-context/address-allocation[text()='shared-ip-pool']) or ((not (/epg/pgw/apn[name=current()/../../name]/pdp-context/pdp-type[text()='ipv4'])) and (not (/epg/pgw/apn[name=current()/../../name]/pdp-context/pdp-type[text()='ipv4v6'])) and (not (/epg/pgw/apn[name=current()/../../name]/pdp-context/pdp-type[text()='ipv4-ipv6'])))" {
          error-message "address-allocation should be shared-ip-pool while configuring location-based-ip-allocation.";
          tailf:dependency "/epg/pgw/apn/pdp-context/address-allocation";
          tailf:dependency "/epg/pgw/apn/pdp-context/pdp-type";
        }
        must "(/epg/pgw/apn[name=current()/../../name]/pdp-context/ipv6-address-allocation[text()='shared-ip-pool']) or ((not (/epg/pgw/apn[name=current()/../../name]/pdp-context/pdp-type[text()='ipv6'])) and (not (/epg/pgw/apn[name=current()/../../name]/pdp-context/pdp-type[text()='ipv4v6'])) and (not (/epg/pgw/apn[name=current()/../../name]/pdp-context/pdp-type[text()='ipv4-ipv6'])))" {
          error-message "ipv6-address-allocation should be shared-ip-pool while configuring location-based-ip-allocation.";
          tailf:dependency "/epg/pgw/apn/pdp-context/ipv6-address-allocation";
          tailf:dependency "/epg/pgw/apn/pdp-context/pdp-type";
        }
      }
    }
    list name-server {
      max-elements 2;
      key "name";
      uses name-server-type;
    }
    list ipv6-name-server {
      max-elements 2;
      key "name";
      uses ipv6-name-server-type;
    }
    list imei-class {
      description
        "IMEI class";
      key "name";
      leaf name {
        description
          "IMEI class identifier";
        type uint8 {
          range "1..24" {
            error-message "Invalid name for 'imei-class'. Valid values are in range:[1,24]";
          }
        }
      }
      leaf-list tac {
        description
          "Regular expression containing an 8 digits Type Allocation Code (TAC) or a 6 digits TAC followed by 2 digits Final Assembly Code (FAC)";
        type string {
          pattern '[.0-9]*' {
            error-message "ERROR: Invalid value for parameter 'tac'. Valid values are 8 decimal digits or dots.";
          }
          length "8";
        }
      }
    }
    container user-profile-selection {
      description
        "User profile selection settings";
      uses user-profile-selection-type;
    }
    action statistics {
      description
        "APN statistics information";
      output {
        leaf result {
          type string;
          mandatory true;
        }
      }
    }
    action user-info {
      yexte:user-group "ericsson-support,epg-tracing-admin,epg-admin";
      description
        "APN for which to show PDP Contexts";
      output {
        leaf result {
          type string;
          mandatory true;
        }
      }
    }
    leaf mtu {
      description
        "Maximum transmission unit (MTU) for end user IP packets downlink\\. Overrides PGW MTU configuration.";
      type uint16 {
        range "1280..2900" {
          error-message "Invalid value for attribute 'mtu'. Valid values are in range:[1280,2900]";
        }
      }
    }
    container access-restrictions {
      description
        "Settings for APN access restrictions";
      presence "access-restrictions need presence";
      leaf selection-mode {
        description
          "User access to the APN";
        type enumeration {
          enum public {
            description
              "User does not need to be subscribed for APN";
          }
          enum from-user {
            description
              "Can choose which APN to connect";
          }
          enum from-network {
            description
              "Can connect to default APN for the MME/SGW/SGSN";
          }
          enum restricted {
            description
              "Admit only users subscribed for APN";
          }
        }
      }
      container radius-assisted-apn-selection {
        description
          "Enable RADIUS assisted APN selection";
        presence "radius-assisted-apn-selection need presence";
        must 'not (../s6b-assisted-apn-selection)' {
          error-message "Can't Configure radius-assisted-apn-selection and s6b-assisted-apn-selection at the same time";
        }
        leaf default {
          description
            "Default APN name for radius assisted APN selection";
          type leafref {
            path "/epg/pgw/apn/name";
          }
        }
      }
      container s6b-assisted-apn-selection {
        description
          "Enable S6b assisted APN selection";
        presence "s6b-assisted-apn-selection need presence";
        must 'not (../radius-assisted-apn-selection)' {
          error-message "Can't Configure radius-assisted-apn-selection and s6b-assisted-apn-selection at the same time";
        }
        leaf default {
          description
            "Default APN name for s6b assisted APN selection";
          type leafref {
            path "/epg/pgw/apn/name";
          }
        }
      }
      leaf prevent-direct-access {
        description
          "Prevent from using a requested APN directly";
        type empty;
      }
      leaf restriction-value {
        description
          "Set APN Restriction Value on the APN";
        type uint8 {
          range "0..4" {
            error-message "Invalid value for attribute 'restriction-value'. Valid values are in range:[0,4]";
          }
        }
      }
    }
    leaf routing-instance {
      description
        "Routing instance for in-apn traffic";
      type string;
      must "(/ctxsipos:contexts/ctxipos:context[ctxipos:context-name=current()]) or (/epg/node/direct-io/routing-instance[name=current()])" {
        error-message "either ipos or direct-io routing instance should be configured";
      }
      default "local";
    }
    leaf gi-address-range {
      description
        "IPv4 address range to use in APN routing instance";
      type eipv4-prefix-optional;
    }
    choice ms-to-ms-handling {
      leaf ms-to-ms-unblocked {
        description
          "Disables MS2MS filtering";
        type empty;
      }
      leaf ue-to-ue-forwarding-address {
        description
          "IPv4 address to forward UE to UE traffic";
        type inet:ipv4-address;
      }
      list ue-to-ue-unblocked-range {
        max-elements 64;
        key "name";
        uses ue2ue-unblockedrange-type;
      }
    }
    container mmtel {
      description
        "Multimedia telephony configuration";
      presence "mmtel need presence";
      container emergency {
        description
          "Enable APN as an emergency APN";
        presence "emergency need presence";
        must '../../user-profile-selection/gx-profile' {
          error-message "user-profile-selection gx-profile must be configured for an emergency IMS APN";
        }
        leaf inactivity-timeout {
          description
            "Timeout for an inactive emergency session";
          type uint16 {
            range "5..7200" {
              error-message "Invalid value for attribute 'inactivity-timeout'. Valid values are in range:[5,7200]";
            }
          }
        }
        leaf imsi-for-unauthenticated {
          description
            "Configure the imsi number for unauthenticated users";
          type string {
            pattern '[0-9]*' {
              error-message "ERROR: Invalid value for parameter imsi-for-unauthenticated. Valid values are strings in a specified format. Type: imsi-for-unauthenticated? for more information on the format to use.";
            }
            length "5..15";
          }
        }
      }
    }
    container non-ip {
      description
        "non-ip application server configuration";
      presence "non-ip need presence";
      must "/epg/pgw/apn[name=current()/../name]/pdp-context/pdp-type[text()='non-ip']" {
        error-message "Must configure PdpType=non-ip when configuring non-ip application server";
        tailf:dependency "/epg/pgw/apn/pdp-context/pdp-type";
      }
      leaf application-server-address {
        description
          "Address to application server";
        type inet:ip-address;
        mandatory true;
      }
      leaf application-server-port {
        description
          "Port for application server";
        type uint16;
        mandatory true;
      }
      leaf local-port {
        description
          "Local port for UDP datagrams";
        type uint16;
      }
      leaf ipv6-mtu {
        description
          "IPv6 Maximum transmission unit";
        type uint16 {
          range "1280..2900" {
            error-message "Invalid value for attribute 'ipv6-mtu'. Valid values are in range:[1280,2900]";
          }
        }
      }
      leaf link-mtu {
        description
          "UE maximum transmission unit";
        type uint32;
      }
    }
    container pdp-context {
      description
        "apn-specific PDP context settings";
      presence "pdp-context need presence";
      uses apn-pdp-context-type;
    }
    container gtp {
      description
        "GTP configuration";
      presence "gtp need presence";
      leaf no-payload-compression {
        description
          "Prohibit SGSN payload compression";
        type empty;
      }
      leaf wlan {
        description
          "WLAN allowed for APN";
        type empty;
      }
      leaf disable-wlan-dedicated-bearer {
        description
          "Disable WLAN Dedicated Bearer for APN";
        type empty;
        must '/epg/pgw/apn[name=current()/../../name]/gtp/wlan' {
          error-message "Requires wlan";
        }
        must 'not (/epg/pgw/apn[name=current()/../../name]/pdp-context/disable-dedicated-bearer)' {
          error-message "pdp-context disable-dedicated-bearer is incompatible with disable-wlan-dedicated-bearer";
        }
      }
      leaf accept-handover-to-uwlan {
        description
          "Silently accept handover to untrusted WLAN when no context";
        type empty;
      }
    }
    container radius {
      description
        "RADIUS configuration";
      presence "radius need presence";
      leaf connect {
        description
          "Choose Radius connection type";
        type enumeration {
          enum direct {
            description
              "EPG connect to Radius server directly from PGW-C";
          }
          enum upf-forwarding {
            description
              "EPG connect to Radius server through upf forwarding";
          }
        }
      }
      uses radius-common-properties;
      container authentication {
        description
          "RADIUS authentication settings";
        presence "authentication need presence";
        list custom-attribute {
          key "name";
          leaf name {
            description
              "Custom attribute identifier";
            type string {
              length "1..64";
            }
          }
          leaf type {
            description
              "Radius attribute type";
            type uint8;
            must
              "(../type = '26' and ../vendor-id and ../vendor-type) or
               (../type != '26' and (not (../vendor-id)) and (not (../vendor-type)))" {
              error-message "vendor-id and vendor-type is reqiured for type 26";
            }
          }
          leaf vendor-id {
            description
              "Vendor ID for Vendor specific attribute";
            type uint32;
            tailf:display-when "../type = '26'";
          }
          leaf vendor-type {
            description
              "Type for Vendor specific attribute";
            type uint8;
            tailf:display-when "../type = '26'";
          }
        }
        container ericsson-primary-rulespace-name {
          description
            "Settings for ericsson-primary-rulespace-name";
          leaf custom-attribute {
            description
              "Name of ericsson-primary-rulespace-name custom attribute";
            type string {
              length "1..64";
            }
          }
        }
        leaf wpp-compatible-encoding {
          description
            "Encode RADIUS attributes in a format compatible with WPP GGSN";
          type empty;
        }
        container message-attributes {
          description
            "Attributes in RADIUS messages";
          presence "message-attributes need presence";
          uses radius-authentication-message-attributes-type;
        }
        choice auth_shared_or_inband_choice {
          list server {
            max-elements 10;
            key "name";
            uses radius-type;
          }
          leaf shared-server {
            description
              "Shared RADIUS server for authentication";
            type leafref {
              path "/epg/pgw/radius/server/name";
            }
          }
        }
        leaf use-domain-name {
          description
            "Use domain name as username in access request";
          type empty;
        }
        leaf user-name {
          description
            "User name for user authentication towards RADIUS";
          type enumeration {
            enum imsi {
              description
                "Use IMSI as username";
            }
            enum imsi-at-apn {
              description
                "Use IMSI@APN as username";
            }
            enum msisdn {
              description
                "Use MSISDN as username";
            }
            enum msisdn-at-apn {
              description
                "Use MSISDN@APN as username";
            }
          }
        }
      }
      container accounting {
        description
          "RADIUS accounting settings";
        presence "accounting need presence";
        uses radius-accounting-properties-type;
        container message-attributes {
          description
            "Attributes in RADIUS messages";
          presence "message-attributes need presence";
          uses radius-accounting-message-attributes-type;
        }
        choice acct_shared_or_inband_choice {
          list server {
            max-elements 10;
            key "name";
            uses radius-type-accounting-object;
          }
          leaf shared-server {
            description
              "Shared RADIUS server for accounting";
            type leafref {
              path "/epg/pgw/radius/server/name";
            }
          }
        }
      }
    }
    container dhcp {
      description
        "DHCP server configuration";
      presence "dhcp need presence";
      choice ob_or_ib_dhcp_choice {
        list server {
          max-elements 3;
          key "name";
          uses dhcp-server-type;
        }
        leaf-list shared-server {
          description
            "Shared DHCP server configuration";
          type leafref {
            path "/epg/pgw/dhcp/server/name";
          }
          max-elements 1;
        }
      }
      leaf subnet-select-option-check {
        description
          "Enable the consistency check of Subnet Select Option on DHCPOFFER and DHCPACK";
        type empty;
      }
      leaf no-hyphen-in-client-id {
        description
          "Remove hyphens from DHCP client id";
        type empty;
      }
      leaf sgi-address {
        description
          "Include SGi address in client ID parameter (Option 61)";
        type empty;
      }
      leaf imsi {
        description
          "Include IMSI in client ID parameter (Option 61)";
        type empty;
      }
      leaf nsapi {
        description
          "Include NSAPI in client ID parameter (Option 61)";
        type empty;
      }
      leaf msisdn {
        description
          "Include MSISDN in client ID parameter (Option 61)";
        type empty;
      }
    }
    list netbios-name-server {
      max-elements 10;
      key "name";
      uses netbios-name-server-type;
    }
    container charging {
      description
        "apn-specific charging configuration";
      presence "charging need presence";
      leaf no-enhanced-cdr {
        description
          "Disables record extensions and service data containers for CDRs";
        type empty;
      }
      container characteristics {
        description
          "apn-specific charging characteristics";
        presence "characteristics need presence";
        leaf ignore-profile-from-serving-node {
          description
            "Ignore profile received from serving node";
          type empty;
        }
        choice query-cc-as-choice {
          container query-ocs {
            description
              "OCS user query";
            presence "query-ocs need presence";
            container credit-control-user {
              description
                "Settings to use if OCS enables credit control for the user";
              presence "credit-control-user need presence";
              leaf cc {
                description
                  "Charging characteristics";
                type uint16 {
                  range "0..65535" {
                    error-message "Invalid value for attribute 'cc'. Valid values are in range:[0,65535]";
                  }
                }
                mandatory true;
              }
            }
            container no-credit-control-user {
              description
                "Settings to use if OCS disables credit control for the user";
              presence "no-credit-control-user need presence";
              leaf cc {
                description
                  "Charging characteristics";
                type uint16 {
                  range "0..65535" {
                    error-message "Invalid value for attribute 'cc'. Valid values are in range:[0,65535]";
                  }
                }
                mandatory true;
              }
            }
            container no-valid-answer {
              description
                "Settings to use if no valid answer is received from the OCS";
              presence "no-valid-answer need presence";
              leaf cc {
                description
                  "Charging characteristics";
                type uint16 {
                  range "0..65535" {
                    error-message "Invalid value for attribute 'cc'. Valid values are in range:[0,65535]";
                  }
                }
                mandatory true;
              }
            }
          }
        }
        container roaming-class-based {
          description
            "Charging characteristics based on roaming class";
          presence "roaming-class-based need presence";
          list complete-cc {
            description
              "Mapped charging characteristics value";
            max-elements 24;
            key "name";
            leaf name {
              description
                "Mapped charging characteristics value in 4 hexadecimal digits";
              type string {
                pattern '[0-9a-fA-F]*' {
                  error-message "Invalid value for attribute 'complete-cc'. Valid values are in range:[0000,FFFF]";
                }
                length "4";
              }
            }
            leaf value-description {
              description
                "Description of roaming-class-based-characteristics instance";
              type string;
            }
            leaf-list roaming-class {
              description
                "List of roaming classes assigned to this charging characteristics";
              type uint8 {
                range "1..24" {
                  error-message "Invalid value for attribute 'roaming-class'. Valid values are in range:[1,24]";
                }
              }
              max-elements 24;
            }
          }
        }
        container imsi-based {
          description
            "Charging characteristics based on IMSI";
          presence "imsi-based need presence";
          choice imsi-based-characteristics-choice {
            leaf disable {
              description
                "Disable imsi-based selection of charging characteristics";
              type empty;
            }
            leaf override {
              description
                "Force imsi-based selection of charging characteristics";
              type empty;
            }
          }
        }
        list charging-profile {
          description
            "Charging profile based on roaming-class and cc-value";
          key "name";
          leaf name {
            type uint8 {
              range "0..15" {
                error-message "Invalid value for attribute 'profile-id'. Valid values are in range:[0,15]";
              }
            }
          }
          leaf roaming-class {
            description
              "Mapped roaming class value";
            type uint8 {
              range "1..24" {
                error-message "Invalid value for attribute 'roaming-class'. Valid values are in range:[1,24]";
              }
            }
          }
          leaf cc-value {
            description
              "Mapped charging characteristics value";
            type uint16 {
              range "0..65535" {
                error-message "Invalid value for attribute 'cc-value'. Valid values are in range:[0,65535]";
              }
            }
          }
        }
        leaf roaming-profile {
          description
            "Charging profile for roaming users";
          type uint8 {
            range "0..15" {
              error-message "Invalid value for attribute 'roaming-profile'. Valid values are in range:[0,15]";
            }
          }
        }
        leaf apn-default-complete-cc {
          description
            "Mapped charging characteristics value in 4 hexadecimal digits";
          type string {
            pattern '[0-9a-fA-F]*' {
              error-message "Invalid value for attribute 'apn-default-complete-cc'. Valid values are in range:[0000,FFFF]";
            }
            length "4";
          }
        }
      }
      leaf select-requested-apn {
        description
          "Include requested APN in CDR and RF";
        type empty;
        status deprecated;
        must 'not (../select-apn)' {
          error-message "Incompatible with 'select-apn'";
        }
      }
      leaf select-apn {
        description
          "Select APN name sent in CDR and RF";
        must 'not (../select-requested-apn)' {
          error-message "Incompatible with 'select-requested-apn'";
        }
        type enumeration {
          enum logical {
            description
              "Logical APN name";
          }
          enum requested {
            description
              "Requested APN name";
          }
          enum used {
            description
              "Used APN name";
          }
          enum reported {
            description
              "Reported APN name";
          }
        }
      }
      leaf allow-cc-from-radius {
        description
          "Enable charging characteristics from RADIUS";
        type empty;
      }
    }
    container roaming {
      description
        "Roaming class settings";
      presence "roaming need presence";
      must '/epg/pgw/apn[name=current()/../name]/roaming/default' {
        error-message "default is mandatory";
      }
      uses roaming-type;
    }
    container qos-control {
      description
        "QoS control";
      presence "qos-control need presence";
      leaf maximum-bit-rate-uplink {
        description
          "Maximum bitrate uplink";
        type uint32 {
          range "64..1000000000" {
            error-message "Invalid value for attribute 'maximum-bit-rate-uplink'. Valid values are in range:[64,1000000000]";
          }
        }
      }
      leaf maximum-bit-rate-downlink {
        description
          "Maximum bitrate downlink";
        type uint32 {
          range "64..1000000000" {
            error-message "Invalid value for attribute 'maximum-bit-rate-downlink'. Valid values are in range:[64,1000000000]";
          }
        }
      }
      leaf enforce-only-licensed-bitrate {
        description
          "Enforce only licensed bitrate";
        type empty;
      }
      container dscp-map {
        description
          "Settings for DSCP marking based on QCI to DSCP map";
        presence "dscp-map need presence";
        leaf downlink {
          description
            "QCI to DSCP map for DSCP marking of downlink payload";
          type leafref {
            path "/epg/node/qos-control/dscp-map/name";
          }
        }
        leaf uplink {
          description
            "QCI to DSCP map for DSCP marking of uplink payload";
          type leafref {
            path "/epg/node/qos-control/dscp-map/name";
          }
          must 'not (/epg/pgw/apn[name=current()/../../../name]/qos-control/dscp-map/disable-uplink)' {
            error-message "Incompatible with 'disable-uplink'";
          }
        }
        leaf disable-uplink {
          description
            "Disable DSCP marking of uplink payload";
          type empty;
        }
      }
    }
    container p-cscf {
      description
        "p-cscf settings";
      presence "p-cscf need presence";
      uses p-cscf-apn-type;
    }

    container rate-control {
      description
        "Rate control configuration";
      presence "rate-control need presence";
      container apn-rate-control {
        description
          "Apn rate control configuration";
        presence "apn-rate-control need presence";
        leaf uplink-limit {
          description
            "Uplink rate limit";
          type uint16 {
            range "1..65535" {
              error-message "Invalid value for attribute 'uplink-limit'. Valid values are in range:[1,65535]";
            }
          }
        }
        leaf downlink-limit {
          description
            "Downlink rate limit";
          type uint16 {
            range "1..65535" {
              error-message "Invalid value for attribute 'downlink-limit'. Valid values are in range:[1,65535]";
            }
          }
        }
        leaf uplink-time-unit {
          description
            "Uplink time unit";
          type rate-control-time-unit;
        }
        leaf downlink-time-unit {
          description
            "downlink time unit";
          type rate-control-time-unit;
        }
      }
      container mo-exception-data {
        description
          "Mo exception data configuration";
        presence "mo-exception-data need presence";
        leaf uplink-limit {
          description
            "Uplink rate limit";
          type uint16 {
            range "1..65535" {
              error-message "Invalid value for attribute 'uplink-limit'. Valid values are in range:[1,65535]";
            }
          }
        }
        leaf uplink-time-unit {
          description
            "Uplink time unit";
          type rate-control-time-unit;
        }
      }
    }
    container pause-charging {
      description
        "apn-specific Pause Charging support configuration";
      presence "pause-charging need presence";
      action force-stop {
        description
          "Force unpaused PDN connection in this APN";
        input {
          leaf identifier-type {
            type enumeration {
              enum imsi {
                description
                  "International Mobile Subscriber Identity";
              }
              enum msisdn {
                description
                  "Mobile Station Integrated Services Digital Network";
              }
              enum imei {
                description
                  "International Mobile Equipment Identity";
              }
            }
            mandatory true;
          }
          leaf value {
            description
              "Identifier for IMSI , Identifier for MSISDN or Identifier for IMSI";
            type string {
              pattern '([0-9]{5,15})|([0-9]{1,18})' {
                error-message "ERROR: Invalid value for parameter value. Valid values are strings in a specified format. Type: value? for more information on the format to use.";
              }
            }
            mandatory true;
          }
          leaf end-user-address {
            description
              "end-user-address is an optional argument that specifies the IP of the PDN connetion to be forced to pass to unpasused status";
            type inet:ipv4-address;
          }
        }
        output {
          leaf result {
            type string;
            mandatory true;
          }
        }
      }
      leaf-list roaming-class {
        description
          "Roaming class identifier or set of roaming class identifiers";
        type string {
          pattern '([1-9]|1[0-9]|2[0-4])(-([1-9]|1[0-9]|2[0-4]))?' {
            error-message "ERROR: Invalid value for parameter roaming-class. Valid values are strings in a specified format. Type: roaming-class? for more information on the format to use.";
          }
          length "1..7";
        }
        max-elements 24;
      }
    }
  }

  grouping apn-address-type {
    leaf name {
      description
        "Address range for APN network";
      type eipv4-prefix-optional;
    }
  }

  grouping apn-ipv6-address-type {
    leaf name {
      description
        "Address range for APN network";
      type eipv6-prefix-optional;
    }
  }

  grouping user-profile-selection-type {

    grouping condition-type {
      leaf name {
        type string {
          pattern '[.0-9A-Za-z_-]*' {
            error-message "Must contain only letters, numbers, underscores or dashes";
          }
          length "1..64";
        }
        must '(../cc) or (../custom-attribute) or (../imei-class) or (../imsi) or (../msisdn) or (../roaming-class)' {
          error-message "A condition must have at least one match criterion configured.";
        }
      }
      leaf priority {
        description
          "Condition priority where lower value takes precedence";
        mandatory true;
        type uint8 {
          range "0..255" {
            error-message "Invalid value for attribute 'priority'. Valid values are in range:[0,255]";
          }
        }
      }
      container cc {
        description
          "Charging characteristics match criteria";
        presence "cc needs presence";
        leaf-list value {
          description
            "Charging characteristics value";
          type string {
            pattern '[0-9a-fA-F]*' {
              error-message "Must contain 4 hexadecimal digits";
            }
            length "4";
          }
          min-elements 1;
        }
        leaf mask {
          description
            "Charging characteristics mask";
          mandatory true;
          type string {
            pattern '[0-9a-fA-F]*' {
              error-message "Must contain 4 hexadecimal digits";
            }
            length "4";
          }
        }
      }
      list custom-attribute {
        description
          "Custom attribute match criteria";
        max-elements 1;
        key "name";
        leaf name {
          description
            "Custom attribute identifier";
          type string {
            length "1..64";
          }
        }
        choice matcher {
          mandatory true;
          leaf is {
            description
              "Custom attribute value equals";
            type string {
              length "1..255";
            }
          }
          leaf contains {
            description
              "Custom attribute value contains";
            type string {
              length "1..255";
            }
          }
          leaf any {
            description
              "Custom attribute is present";
            type empty;
          }
        }
      }
      leaf-list imei-class {
        description
          "IMEI class identifier";
        type leafref {
          path "/epg/pgw/apn/imei-class/name";
        }
      }
      leaf imsi {
        description
          "IMSI regular expression";
        type string;
      }
      leaf msisdn {
        description
          "MSISDN regular expression";
        type string;
      }
      leaf-list roaming-class {
        description
          "Roaming class identifier";
        type uint8 {
          range "1..24" {
            error-message "Invalid value for attribute 'roaming-class'. Valid values are in range:[1,24]";
          }
        }
      }
    }
    container gx-profile {
      description
        "Gx profile selection settings";
      must 'not(../../mmtel/emergency and not(default))' {
        error-message "'default' must be configured for an emergency IMS APN";
      }
      leaf default {
        description
          "The default Gx profile to use";
        type leafref {
          path "/epg/pgw/policy-control/gx-profile/name";
        }
      }
      list condition {
        key "name";
        uses condition-type;
        must 'not(../../../mmtel/emergency and not(profile))' {
          error-message "'profile' must be configured for an emergency IMS APN";
        }
        leaf profile {
          description
            "The Gx profile to use when this condition matches";
          type leafref {
            path "/epg/pgw/policy-control/gx-profile/name";
          }
        }
      }
    }
    container gy-profile {
      description
        "Gy profile selection settings";
      leaf default {
        description
          "The default Gy profile to use";
        type leafref {
          path "/epg/pgw/credit-control/gy-profile/name";
        }
      }
      list condition {
        key "name";
        uses condition-type;
        leaf profile {
          description
            "The Gy profile to use when this condition matches";
          type leafref {
            path "/epg/pgw/credit-control/gy-profile/name";
          }
        }
      }
    }
    choice s6b-or-s6b-auth-profile-choice {
      container s6b-profile {
        description
          "S6b profile selection settings";
        leaf default {
          description
            "The default S6b profile to use";
          type leafref {
            path "/epg/pgw/aaa/s6b-profile/name";
          }
        }
        list condition {
          key "name";
          uses condition-type;
          leaf profile {
            description
              "The S6b profile to use when this condition matches";
            type leafref {
              path "/epg/pgw/aaa/s6b-profile/name";
            }
          }
        }
      }
      container s6b-auth-profile {
        description
          "S6b auth profile selection settings";
        leaf default {
          description
            "The default S6b auth profile to use";
          type leafref {
            path "/epg/pgw/aaa/s6b-auth-profile/name";
          }
        }
        list condition {
          key "name";
          uses condition-type;
          leaf profile {
            description
              "The S6b auth profile to use when this condition matches";
            type leafref {
              path "/epg/pgw/aaa/s6b-auth-profile/name";
            }
          }
        }
      }
    }
    container service-chaining-profile {
      description
        "Service chaining profile selection settings";
      leaf default {
        description
          "The default service chaining profile to use";
        type leafref {
          path "/epg/pgw/packet-enforcement/service-chaining/profile/name";
        }
      }
      list condition {
        key "name";
        uses condition-type;
        leaf profile {
          description
            "The service chaining profile to use when this condition matches";
          type leafref {
            path "/epg/pgw/packet-enforcement/service-chaining/profile/name";
          }
        }
      }
    }
    container ga-bp-profile {
      description
        "Ga/Bp profile selection settings";
      leaf default {
        description
          "The default Ga/Bp profile to use";
        type leafref {
          path "/epg/pgw/charging/ga-bp-profile/name";
        }
      }
      list condition {
        key "name";
        uses condition-type;
        leaf profile {
          description
            "The Ga/Bp profile to use when this condition matches";
          type leafref {
            path "/epg/pgw/charging/ga-bp-profile/name";
          }
        }
      }
    }
    container rf-profile {
      description
        "Rf profile selection settings";
      leaf default {
        description
          "The default Rf profile to use";
        type leafref {
          path "/epg/pgw/charging/rf-profile/name";
        }
      }
      list condition {
        key "name";
        uses condition-type;
        leaf profile {
          description
            "The Rf profile to use when this condition matches";
          type leafref {
            path "/epg/pgw/charging/rf-profile/name";
          }
        }
      }
    }
    container local-policy-control-profile {
      description
        "Local policy control profile selection settings";
      leaf default {
        description
          "The default local policy control profile to use";
        type leafref {
          path "/epg/pgw/policy-control/local/profile/name";
        }
      }
      list condition {
        key "name";
        uses condition-type;
        leaf profile {
          description
            "The local policy control profile to use when this condition matches";
          type leafref {
            path "/epg/pgw/policy-control/local/profile/name";
          }
        }
      }
    }
    container local-qos-control-profile {
      description
        "Local QoS control profile selection settings";
      leaf default {
        description
          "The default local QoS control profile to use";
        type leafref {
          path "/epg/pgw/qos-control/local/profile/name";
        }
      }
      list condition {
        key "name";
        uses condition-type;
        leaf profile {
          description
            "The local QoS control profile to use when this condition matches";
          type leafref {
            path "/epg/pgw/qos-control/local/profile/name";
          }
        }
      }
    }
    container policy-charging-rule-scope {
      description
        "Policy and charging rule scope selection settings";
      leaf default {
        description
          "The default policy and charging rule scope to use";
        mandatory true;
        type leafref {
          path "/epg/pgw/policy-charging-rule-scope/name";
        }
      }
      list condition {
        key "name";
        uses condition-type;
        leaf profile {
          description
            "The policy and charging rule scope to use when this condition matches";
          mandatory true;
          type leafref {
            path "/epg/pgw/policy-charging-rule-scope/name";
          }
        }
      }
    }
  }

  grouping p-cscf-apn-type {
    list category {
      description
        "p-cscf Category";
      max-elements 63;
      key "name";
      leaf name {
        description
          "p-cscf category name";
        type string {
          pattern '[.0-9A-Za-z-]{1,64}' {
            error-message "Must be a string of 64 or fewer characters and may contain letters, numbers, decimals and dashes.";
          }
        }
      }
      leaf imsi {
        description
          "IMSI regular expression that selects this category";
        type string;
        mandatory true;
      }
      leaf serving-node-plmn-id {
        description
          "Serving Node PLMN ID";
        type string {
          pattern '[0-9]*' {
            error-message "PLMN identifier is a string of 5 or 6 digits";
          }
          length "5..6";
        }
      }
      leaf primary-p-cscf-pool {
        description
          "Primary p-cscf Pool name";
        type leafref {
          path "/epg/pgw/p-cscf-ip-pool/name";
        }
      }
      leaf secondary-p-cscf-pool {
        description
          "Secondary p-cscf Pool name";
        type leafref {
          path "/epg/pgw/p-cscf-ip-pool/name";
        }
        must '/epg/pgw/apn[name=current()/../../../name]/p-cscf/category[name=current()/../name]/primary-p-cscf-pool' {
          error-message "The primary pcscf pool name must be configured under [epg pgw apn p-cscf category primary-p-cscf-pool]";
        }
      }
    }
    leaf primary-p-cscf-pool {
      description
        "Default primary p-cscf Pool name";
      type leafref {
        path "/epg/pgw/p-cscf-ip-pool/name";
      }
    }
    leaf secondary-p-cscf-pool {
      description
        "Default secondary p-cscf Pool name";
      type leafref {
        path "/epg/pgw/p-cscf-ip-pool/name";
      }
      must '/epg/pgw/apn[name=current()/../../name]/p-cscf/primary-p-cscf-pool' {
        error-message "The primary pcscf pool name must be configured under [epg pgw apn p-cscf primary-p-cscf-pool]";
      }
    }
    leaf no-dedicated-signaling-access-ctrl {
      description
        "Disable access control for dedicated signaling contexts";
      type empty;
    }
    leaf no-general-purpose {
      description
        "No general purpose contexts allowed";
      type empty;
    }
    leaf no-dedicated-signaling {
      description
        "No dedicated signaling contexts allowed";
      type empty;
    }
    leaf no-general-signaling-indication {
      description
        "No signaling indication for general purpose contexts allowed";
      type empty;
    }
    leaf no-dedicated-signaling-indication {
      description
        "No signaling indication for dedicated signaling contexts allowed";
      type empty;
    }
    leaf no-reselection-support-check {
      description
        "No p-cscf reselection support  check for UE capability";
      type empty;
    }
    leaf address-format {
      description
        "Settings for address format in GTP response";
      type enumeration {
        enum no-ipv4 {
          description
            "Don't send ipv4 address";
        }
        enum no-ipv4-compatible-ipv6 {
          description
            "Don't send ipv4 address compatible ipv6 address";
        }
      }
    }
    leaf number-of-p-cscf {
      description
        "Number of p-cscf addresses in response";
      type uint8 {
        range "2..3" {
          error-message "Invalid value for attribute 'number-of-p-cscf'. Valid values are in range:[2,3]";
        }
      }
    }
  }

  grouping radius-common-properties {
    leaf same-nas-port-in-auth-acc {
      description
        "Use same generated value for NAS-PORT in Access and Accounting message per session when default nas-port value was not configured";
      type empty;
    }
    leaf retry-method {
      description
        "RADIUS retry scheme settings";
      type enumeration {
        enum single-server {
          description
            "Single server retry scheme";
        }
        enum multiple-server {
          description
            "Multiple server retry scheme";
        }
      }
    }
    leaf load-balancing {
      description
        "Use load balancing to distribute requests";
      type empty;
    }
    leaf quarantine-all {
      description
        "Allow all servers to be set into quarantine";
      type empty;
    }
    container rat-type-map {
      description
        "Defines rat type mapping";
      list from {
        description
          "Original RAT type identifier to map from";
        key "name";
        uses rat-map-type;
      }
    }
    leaf select-requested-apn {
      description
        "Use requested APN name as called-station-id attribute value";
      type empty;
      status deprecated;
      must 'not (../select-apn)' {
        error-message "Incompatible with 'select-apn'";
      }
    }
    leaf select-apn {
      description
        "Select APN name as Called-Station-Id attribute value";
      must 'not (../select-requested-apn)' {
        error-message "Incompatible with 'select-requested-apn'";
      }
      type enumeration {
        enum logical {
          description
            "Logical APN name";
        }
        enum requested {
          description
            "Requested APN name";
        }
        enum used {
          description
            "Used APN name";
        }
        enum reported {
          description
            "Reported APN name";
        }
      }
    }
    leaf timeout-cause-code {
      description
        "Cause code for server timeout, the value must be according to 3GPP TS 29.060";
      type uint8 {
        range "0..255" {
          error-message "Invalid value for attribute 'timeout-cause-code'. Valid values are in range:[0,255]";
        }
      }
    }
    leaf unavailable-cause-code {
      description
        "Cause code for unavailable server , the value must be according to 3GPP TS 29.060";
      type uint8 {
        range "0..255" {
          error-message "Invalid value for attribute 'unavailable-cause-code'. Valid values are in range:[0,255]";
        }
      }
    }
    leaf reuse-primary {
      description
        "Reuse the first primary server in the list when it is out of quarantine";
      type empty;
    }
    leaf force-switch-alarm {
      description
        "Force the RADIUS server switch alarm to be generated";
      type empty;
    }
    leaf accept-disconnect {
      description
        "Perform PDP context deletion on receiving a disconnect request from a RADIUS server";
      type empty;
    }
    leaf rulespace {
      description
        "Accept rulespace from RADIUS";
      type empty;
    }
  }

  grouping radius-accounting-properties-type {
    leaf wpp-compatible-encoding {
      description
        "Encode RADIUS attributes in a format compatible with WPP GGSN";
      type empty;
    }
    leaf message-for-every-context {
      description
        "Send start/interim/stop message for every PDP context";
      type empty;
    }
    leaf no-accounting-on {
      description
        "Do not send accounting on and off messages";
      type empty;
    }
    leaf no-accounting-on-resp-needed {
      description
        "Accounting on response not needed";
      type empty;
    }
    leaf accounting-on-retry {
      description
        "Accounting on request will be continuously sent until Accounting on response is received";
      type empty;
    }
    container accounting-on {
      description
        "Relates only to accounting-on";
      must 'not (./../no-accounting-on)' {
        error-message "no-accounting-on can not be set when using this configuration";
      }
      presence "accounting-on need presence";
      leaf no-short-timer {
        description
          "Will disable the short retry-timer for accounting-on";
        type empty;
      }
      leaf long-retry-timer {
        description
          "Define the long retry-timer for accounting-on, default: 60 seconds";
        type uint8 {
          range "5..90" {
            error-message "Invalid value for attribute 'long-retry-timer'. Valid values are in range:[5,90]";
          }
        }
      }
    }
    container interim-update {
      description
        "Send interim accounting requests";
      presence "interim-update need presence";
      leaf transfer-interval {
        description
          "Send RADIUS interim update periodically";
        type uint16 {
          range "1..1440" {
            error-message "Invalid value for attribute 'transfer-interval'. Valid values are in range:[1,1440]";
          }
        }
      }
      leaf transfer-on-update {
        description
          "Send RADIUS interim update when receiving PDP context update request";
        type empty;
      }
      container user-location-change-trigger {
        description
          "User location change trigger send RADIUS interim update";
        leaf rai {
          description
            "Rai change will trigger send RADIUS interim update";
          type empty;
        }
        leaf tai {
          description
            "Tai change will trigger send RADIUS interim update";
          type empty;
        }
      }
      leaf acknowledge {
        description
          "Delete PDP context when RADIUS interim response is not received";
        type empty;
      }
      container transfer-on-volume {
        description
          "Send RADIUS interim update on volume limit";
        presence "transfer-on-volume need presence";
        must './volume-threshold' {
          error-message "volume-threshold is mandatory";
        }
        container volume-threshold {
          description
            "Volume limit in kilobytes when RADIUS interim update is sent";
          presence "volume-threshold need presence";
          leaf gsm-wcdma {
            description
              "Allowed range for gsm-wcdma";
            type uint16 {
              range "512..10240" {
                error-message "Invalid value for attribute 'gsm-wcdma'. Valid values are in range:[512,10240]";
              }
            }
          }
          leaf lte {
            description
              "Allowed range for lte";
            type uint32 {
              range "512..1048576" {
                error-message "Invalid value for attribute 'lte'. Valid values are in range:[512,1048576]";
              }
            }
          }
        }
      }
      container service-detection {
        description
          "Send RADIUS interim update on service detection";
        must 'not (./../transfer-interval)' {
          error-message "service-detection can not be configured with transfer-interval";
        }
        must 'not (./../transfer-on-update)' {
          error-message "service-detection can not be configured with transfer-on-update";
        }
        must 'not (./../transfer-on-volume)' {
          error-message "service-detection can not be configured with transfer-on-volume";
        }
        presence "service-detection need presence";
        leaf-list access-control-rule {
          description
            "Access control rule identifier or set of access control rule identifiers for service detection";
          type string {
            pattern '[0-9]{1,10}([-][0-9]{1,10})?' {
              error-message "Must be an access control rule identifier or a range of access control rule identifiers";
            }
            length "1..21";
          }
          max-elements 16;
          must './../report-interval' {
            error-message "access-control-rule must be configured with report-interval";
          }
        }
        leaf report-interval {
          description
            "report internal for triggering interim";
          type uint16 {
            range "60..3600" {
              error-message "Invalid value for attribute 'report-interval'. Valid values are in range:[60,3600]";
            }
          }
          must './../access-control-rule' {
            error-message "report-interval must be configured with access-control-rule";
          }
        }
      }
    }
    leaf un-acknowledge {
      description
        "Run in un-acknowledge mode";
      type empty;
    }
    leaf force-multicast {
      description
        "Sends to multicast server(s) without waiting for the primary respone";
      type empty;
    }
    leaf force-retry {
      description
        "Continue with the next RADIUS server for the same pdp-context after max fail retries";
      type empty;
      must "(../un-acknowledge) or (not(../../retry-method[text()='multiple-server']))" {
        error-message "Forced-retry is only valid if retry-method is single-server and un-acknowledge is choosen";
      }
    }
    leaf restart-session-on-rat-change {
      description
        "Restart accounting session on RAT change";
      type empty;
    }
    leaf continue-session-on-id-overflow {
      description
        "Continue session on RADIUS ID overflow";
      type empty;
    }
  }

  grouping radius-authentication-message-attributes-type {
    leaf apn-identifier {
      description
        "Include APN name";
      type empty;
    }
    leaf apn-selection-mode {
      description
        "Include APN selection information";
      type empty;
    }
    leaf charging-gateway {
      description
        "Include charging gateway address";
      type empty;
    }
    leaf charging-characteristics {
      description
        "Include charging characteristics";
      type empty;
    }
    leaf framed-protocol {
      description
        "Framing to be used for access";
      type enumeration {
        enum ppp {
          description
            "PPP (1)";
        }
        enum gprs {
          description
            "gprs-pdp-context (7)";
        }
        enum no-framed-protocol {
          description
            "Do not send framed-protocol in RADIUS messages";
        }
      }
    }
    leaf ggsn-address {
      description
        "Include GGSN node address";
      type empty;
      must '(../pdp-type)' {
        error-message "Authentication ggsn-address attribute is enabled but pdp-type not set";
      }
    }
    leaf ggsn-address-ipv6 {
      description
        "Include GGSN node IPv6 address";
      type empty;
    }
    leaf eps-qos {
      description
        "Change the format of AVP qos-negotiation to new GTPv2 format.";
      type empty;
    }
    leaf imsi {
      description
        "Include IMSI";
      type empty;
    }
    leaf ms-timezone {
      description
        "Include MS timezone";
      type empty;
    }
    leaf nas-port-type {
      description
        "Type of physical port of the NAS";
      type enumeration {
        enum async {
          description
            "ASYNC (0)";
        }
        enum virtual {
          description
            "VIRTUAL (5)";
        }
        enum no-nas-port-type {
          description
            "Do not send nas-port-type in RADIUS messages";
        }
      }
    }
    leaf no-nas-identifier {
      description
        "Do not send nas-identifier in RADIUS messages";
      type empty;
    }
    leaf no-service-type {
      description
        "Do not send service-type in RADIUS messages";
      type empty;
    }
    leaf user-location-info {
      description
        "Include user location info";
      type empty;
    }
    choice user-plmn-mcc {
      leaf user-plmn-id {
        description
          "Include User Public Land Mobile Network identifier";
        type empty;
      }
    }
    choice msisdn_choice {
      container msisdn {
        description
          "Include MSISDN";
        presence "msisdn need presence";
        leaf numeric-prefix {
          description
            "A prefix that will be inserted in front of the MSISDN";
          type string {
            pattern '[0-9]{1,2}' {
              error-message "The prefix is a string up to 2 digits";
            }
          }
        }
      }
      leaf msisdn-value {
        description
          "MSISDN set to this value in RADIUS messages";
        type string {
          pattern '[0-9]{1,20}' {
            error-message "MSISDN is a string of up to 20 digits";
          }
        }
      }
    }
    leaf nsapi {
      description
        "Include NSAPI";
      type empty;
    }
    leaf pdp-type {
      description
        "Include PDP type";
      type empty;
    }
    leaf signaling-sgsn {
      description
        "Include signaling SGSN address";
      type empty;
    }
    leaf signaling-sgsn-ipv6 {
      description
        "Include signaling SGSN IPv6 address";
      type empty;
    }
    leaf user-value {
      description
        "User name set to this value in RADIUS messages";
      type string {
        pattern '[A-Za-z.0-9-]{1,40}' {
          error-message "User name may consist of up to 40 letters, numbers, periods and dashes";
        }
      }
    }
    choice nas_port_choice {
      leaf nas-port {
        description
          "Include NAS port attribute";
        type empty;
      }
      leaf nas-port-value {
        description
          "NAS port set to this value in RADIUS messages";
        type string {
          pattern '[0-9]{1,10}' {
            error-message "NAS port is a string of up to 10 digits";
          }
        }
      }
    }
    leaf nas-ip-address-value {
      description
        "NAS IP address set to this value in RADIUS messages";
      type inet:ipv4-address;
    }
    leaf sgsn-plmn-id {
      description
        "Include the SGSN Public Land Mobile Network identifier";
      type empty;
    }
    leaf ggsn-plmn-id {
      description
        "Include the GGSN Public Land Mobile Network identifier";
      type empty;
    }
    leaf rat-type {
      description
        "Include the radio access technology type in the request";
      type empty;
    }
    leaf acct-session-id {
      description
        "Include the acct-session-id attribute in RADIUS authentication messages";
      type empty;
    }
    leaf allocate-ip-type {
      description
        "Include allocate ip type";
      type empty;
    }
    leaf imei-sv {
      description
        "Include the imei-sv in the request";
      type empty;
    }
    leaf user-password-value {
      description
        "User password set to this value in messages";
      type tailf:aes-cfb-128-encrypted-string {
        pattern '($[1-9]$(.|\n)*)|(($0$)?.{1,128})' {
          error-message "User password may consist of up to 128 characters";
        }
      }
    }
    leaf override-user-info {
      description
        "Override username and password received in PCO";
      type empty;
    }
    leaf disable-chap-challenge-padding {
      description
        "Turn off the validation of the length and the padding with zeros of the chap challenge AVP.";
      type empty;
    }
  }

  grouping radius-accounting-message-attributes-type {
    leaf event-timestamp {
      description
        "Include the event-timestamp attribute in RADIUS accounting messages";
      type empty;
    }
    leaf apn-identifier {
      description
        "Include APN name";
      type empty;
    }
    leaf apn-selection-mode {
      description
        "Include APN selection information";
      type empty;
    }
    leaf charging-gateway {
      description
        "Include charging gateway address";
      type empty;
    }
    leaf charging-characteristics {
      description
        "Include charging characteristics";
      type empty;
    }
    leaf framed-protocol {
      description
        "Framing to be used for access";
      type enumeration {
        enum ppp {
          description
            "PPP (1)";
        }
        enum gprs {
          description
            "gprs-pdp-context (7)";
        }
        enum no-framed-protocol {
          description
            "Do not send framed-protocol in RADIUS messages";
        }
      }
    }
    leaf ggsn-address {
      description
        "Include GGSN node address";
      type empty;
      must '(../pdp-type)' {
        error-message "Accounting ggsn-address attribute is enabled but pdp-type not set";
      }
    }
    leaf ggsn-address-ipv6 {
      description
        "Include GGSN node IPv6 address";
      type empty;
    }
    leaf eps-qos {
      description
        "Change the format of AVP qos-negotiation to new GTPv2 format.";
      type empty;
    }
    leaf imsi {
      description
        "Include IMSI";
      type empty;
    }
    leaf ms-timezone {
      description
        "Include MS timezone";
      type empty;
    }
    leaf nas-port-type {
      description
        "Type of physical port of the NAS";
      type enumeration {
        enum async {
          description
            "ASYNC (0)";
        }
        enum virtual {
          description
            "VIRTUAL (5)";
        }
        enum no-nas-port-type {
          description
            "Do not send nas-port-type in RADIUS messages";
        }
      }
    }
    leaf no-nas-identifier {
      description
        "Do not send nas-identifier in RADIUS messages";
      type empty;
    }
    leaf no-service-type {
      description
        "Do not send service-type in RADIUS messages";
      type empty;
    }
    leaf user-location-info {
      description
        "Include user location info";
      type empty;
    }
    choice user-plmn-mcc {
      leaf user-plmn-id {
        description
          "Include User Public Land Mobile Network identifier";
        type empty;
      }
    }
    choice msisdn_choice {
      container msisdn {
        description
          "Include MSISDN";
        presence "msisdn need presence";
        leaf numeric-prefix {
          description
            "A prefix that will be inserted in front of the MSISDN";
          type string {
            pattern '[0-9]{1,2}' {
              error-message "The prefix is a string up to 2 digits";
            }
          }
        }
      }
      leaf msisdn-value {
        description
          "MSISDN set to this value in RADIUS messages";
        type string {
          pattern '[0-9]{1,20}' {
            error-message "MSISDN is a string of up to 20 digits";
          }
        }
      }
    }
    leaf nsapi {
      description
        "Include NSAPI";
      type empty;
    }
    leaf pdp-type {
      description
        "Include PDP type";
      type empty;
    }
    leaf signaling-sgsn {
      description
        "Include signaling SGSN address";
      type empty;
    }
    leaf signaling-sgsn-ipv6 {
      description
        "Include signaling SGSN IPv6 address";
      type empty;
    }
    leaf user-value {
      description
        "User name set to this value in RADIUS messages";
      type string {
        pattern '[A-Za-z.0-9-]{1,40}' {
          error-message "User name may consist of up to 40 letters, numbers, periods and dashes";
        }
      }
    }
    choice nas_port_choice {
      leaf nas-port {
        description
          "Include NAS port attribute";
        type empty;
      }
      leaf nas-port-value {
        description
          "NAS port set to this value in RADIUS messages";
        type string {
          pattern '[0-9]{1,10}' {
            error-message "NAS port is a string of up to 10 digits";
          }
        }
      }
    }
    leaf nas-ip-address-value {
      description
        "NAS IP address set to this value in RADIUS messages";
      type inet:ipv4-address;
    }
    leaf sgsn-plmn-id {
      description
        "Include the SGSN Public Land Mobile Network identifier";
      type empty;
    }
    leaf ggsn-plmn-id {
      description
        "Include the GGSN Public Land Mobile Network identifier";
      type empty;
    }
    leaf rat-type {
      description
        "Include the radio access technology type in the request";
      type empty;
    }
    leaf charging-identifier {
      description
        "Include user charging identifier";
      type empty;
    }
    leaf acct-input-octets {
      description
        "Include the number of octets sent";
      type empty;
    }
    leaf acct-input-gigawords {
      description
        "Include the number of times octets overflew";
      type empty;
      must '(../acct-input-octets)' {
        error-message "Accounting input-gigawords is not allowed without acct-input-octets";
      }
    }
    leaf acct-output-octets {
      description
        "Include the number of octets received";
      type empty;
    }
    leaf acct-output-gigawords {
      description
        "Include the number of times octets overflew";
      type empty;
      must '(../acct-output-octets)' {
        error-message "Accounting output-gigawords is not allowed without acct-input-octets";
      }
    }
    leaf acct-output-packets {
      description
        "Include the number of output packets";
      type empty;
    }
    leaf acct-input-packets {
      description
        "Include the number of input packets";
      type empty;
    }
    leaf imei-sv-stop {
      description
        "Include the imei-sv in accounting stop request";
      type empty;
    }
    leaf served-mdn {
      description
        "Include MSISDN in served-mdn attribute";
      type empty;
    }
    leaf no-acct-authentic {
      description
        "Do not send acct-authentic in RADIUS messages";
      type empty;
    }
    leaf negotiated-dscp {
      description
        "Include negotiated DSCP";
      type empty;
    }
    leaf acct-multisession-id {
      description
        "Include Multi Session Id and Link Count";
      type empty;
    }
    leaf packet-filter {
      description
        "Include packet filter";
      type empty;
    }
    leaf imei-sv {
      description
        "Include the imei-sv in accounting start and accounting interim-update request";
      type empty;
    }
    leaf imei-sv-start {
      description
        "Include the imei-sv in accounting start request";
      type empty;
      must 'not (./../imei-sv)' {
        error-message "Radius attributes have both imeiSv and imeiSvStart specified(mutually exclusive).";
      }
    }
    leaf session-stop {
      description
        "Send session stop message";
      type empty;
    }
    leaf include-session-time {
      description
        "Include session-time in accounting stop";
      type empty;
    }
    leaf include-session-time-in-all {
      description
        "Include session-time in all RADIUS accounting messages";
      type empty;
    }
    leaf prepaid-expired {
      description
        "Include prepaid-expired VSA in RADIUS accounting message";
      type empty;
    }
    leaf service-key {
      description
        "Include service-key VSA in RADIUS accounting message";
      type empty;
    }
    leaf preservation-indicator {
      description
        "Include preservation-indicator VSA in RADIUS accounting message";
      type empty;
    }
    leaf framed-interface-id {
      description
        "Include framed-interface-id RADIUS accounting message";
      type empty;
    }
    leaf low-access-priority {
      description
        "Include low-access-priority VSA in RADIUS accounting message";
      type empty;
    }
  }

  grouping radius-type {
    leaf priority {
      description
        "Priority specifying which of multiple configured servers is to be used first\\. A value from 1 to 999999, where a lower value takes precedence.";
      type string {
        pattern '[1-9][0-9]*' {
          error-message "String must match: ^[1-9][0-9]*$'";
        }
        length "1..6";
      }
      default "999999";
    }
    leaf name {
      description
        "RADIUS server address";
      type inet:ipv4-address;
    }
    leaf timeout {
      description
        "Request timeout period";
      type uint8 {
        range "1..90" {
          error-message "Invalid value for attribute 'timeout'. Valid values are in range:[1,90]";
        }
      }
    }
    leaf retry {
      description
        "Retry attempts";
      type uint8 {
        range "1..10" {
          error-message "Invalid value for attribute 'retry'. Valid values are in range:[1,10]";
        }
      }
    }
    leaf port {
      description
        "Port number for RADIUS messages";
      type uint16;
    }
    leaf secret {
      description
        "Shared secret with the RADIUS server";
      type tailf:aes-cfb-128-encrypted-string;
      mandatory true;
    }
    leaf serverdown-timeout {
      description
        "Time before retrying requests to a down server";
      type uint16 {
        range "0..1800" {
          error-message "Invalid value for attribute 'serverdown-timeout'. Valid values are in range:[0,1800]";
        }
      }
    }
    leaf multicast {
      description
        "Allow server to participate in RADIUS multicast";
      type empty;
    }
  }

  grouping radius-type-accounting-object {
    leaf priority {
      description
        "Priority specifying which of multiple configured servers is to be used first\\. A value from 1 to 999999, where a lower value takes precedence.";
      type string {
        pattern '[1-9][0-9]*' {
          error-message "String must match: ^[1-9][0-9]*$'";
        }
        length "1..6";
      }
      default "999999";
    }
    leaf name {
      description
        "RADIUS server address";
      type inet:ipv4-address;
    }
    leaf timeout {
      description
        "Request timeout period";
      type uint8 {
        range "1..90" {
          error-message "Invalid value for attribute 'timeout'. Valid values are in range:[1,90]";
        }
      }
    }
    leaf retry {
      description
        "Retry attempts";
      type uint8 {
        range "1..60" {
          error-message "Invalid value for attribute 'retry'. Valid values are in range:[1,60]";
        }
      }
    }
    leaf acct-interim-requests-per-second {
      description
        "Accounting interim update request per second";
      type uint16 {
        range "0..65535" {
          error-message "Invalid value for attribute 'acct-interim-requests-per-second'. Valid values are in range:[0,65535]";
        }
      }
    }
    leaf port {
      description
        "Port number for RADIUS messages";
      type uint16;
    }
    leaf secret {
      description
        "Shared secret with the RADIUS server";
      type tailf:aes-cfb-128-encrypted-string;
      mandatory true;
    }
    leaf serverdown-timeout {
      description
        "Time before retrying requests to a down server";
      type uint16 {
        range "0..1800" {
          error-message "Invalid value for attribute 'serverdown-timeout'. Valid values are in range:[0,1800]";
        }
      }
    }
    leaf multicast {
      description
        "Allow server to participate in RADIUS multicast";
      type empty;
    }
    leaf no-interim-update-multicast {
      description
        "Do not send interim multicast to this RADIUS server";
      type empty;
    }
  }

  grouping roaming-type {
    list roaming-class {
      must '/epg/pgw/apn[name=current()/../../name]/roaming/roaming-class[name=current()/name]/plmn' {
        error-message "plmn is mandatory";
      }
      key "name";
      uses roaming-class-type;
    }
    container default {
      description
        "Default roaming class";
      presence "default need presence";
      list rat-type {
        key "name";
        uses roaming-default-type;
      }
      leaf roaming-class {
        description
          "Roaming class for any radio access technology";
        type uint8 {
          range "1..24" {
            error-message "Invalid value for attribute 'roaming-class'. Valid values are in range:[1,24]";
          }
        }
        mandatory true;
      }
    }
  }

  grouping roaming-class-type {
    leaf name {
      description
        "Roaming class identifier";
      type uint8 {
        range "1..24" {
          error-message "Invalid value for attribute 'roaming-class-id'. Valid values are in range:[1,24]";
        }
      }
    }
    list plmn {
      description
        "Public land mobile network name";
      must '/epg/pgw/apn[name=current()/../../../name]/roaming/roaming-class[name=current()/../name]/plmn[name=current()/name]/plmn-id' {
        error-message "plmn-id is mandatory";
      }
      key "name";
      leaf name {
        description
          "Public land mobile network name";
        type leafref {
          path "/epg/pgw/plmn/name";
        }
      }
      list plmn-id {
        key "name";
        uses roaming-plmn-id-type;
      }
    }
  }

  grouping roaming-default-type {
    leaf name {
      description
        "Radio access technology (RAT) identifier";
      type common-rat-type-extend;
    }
    leaf roaming-class {
      description
        "Roaming class";
      type uint8 {
        range "1..24" {
          error-message "Invalid value for attribute 'roaming-class'. Valid values are in range:[1,24]";
        }
      }
      mandatory true;
    }
  }

  grouping roaming-plmn-id-type {
    leaf name {
      description
        "SGSN public land mobile network identifier";
      type leafref {
        path "/epg/pgw/plmn[name=current()/../../name]/plmn-id/name";
      }
    }
    leaf-list rat-types {
      description
        "Radio access technology (RAT) global defaults";
      type common-rat-type-extend;
    }
  }

  grouping dhcp-server-type {
    leaf priority {
      description
        "Priority specifying which of multiple configured servers is to be used first\\. A value from 1 to 999999, where a lower value takes precedence.";
      type string {
        pattern '[1-9][0-9]*' {
          error-message "String must match: ^[1-9][0-9]*$'";
        }
        length "1..6";
      }
      default "999999";
    }
    leaf name {
      description
        "DHCP server address";
      type inet:ipv4-address;
    }
    leaf timeout {
      description
        "Request timeout period";
      type uint8 {
        range "1..90" {
          error-message "Invalid value for attribute 'timeout'. Valid values are in range:[1,90]";
        }
      }
    }
    leaf retry {
      description
        "Retry attempts";
      type uint8 {
        range "1..10" {
          error-message "Invalid value for attribute 'retry'. Valid values are in range:[1,10]";
        }
      }
    }
  }

  grouping custom-attribute-type {
    leaf name {
      description
        "Custom attribute identifier";
      type string {
        length "1..64";
      }
    }
    leaf vendor-id {
      description
        "Custom attribute vendor identifier";
      type uint32;
      mandatory true;
    }
    leaf code {
      description
        "Custom attribute code";
      type uint32;
      mandatory true;
    }
    leaf type {
      description
        "Custom attribute type";
      type enumeration {
        enum octet-string {
          description
            "Type OctetString";
        }
      }
      default "octet-string";
    }
  }

  grouping apn-pdp-context-type {
    leaf creation {
      description
        "PDP context creation state";
      type enumeration {
        enum unblocked {
          description
            "No restrictions on PDP context creation";
        }
        enum blocked {
          description
            "New PDP context creation fully blocked";
        }
      }
    }
    leaf pdp-type {
      description
        "PDP context type";
      type enumeration {
        enum ipv4 {
          description
            "IPv4 PDP context type";
        }
        enum ipv6 {
          description
            "IPv6 PDP context type";
        }
        enum ipv4-ipv6 {
          description
            "IPv4 and IPv6 PDP contexts";
        }
        enum ipv4v6 {
          description
            "IPv4v6 PDP contexts";
        }
        enum non-ip {
          description
            "non-ip PDP context type";
        }
      }
      must "not ((/epg/pgw/apn[name=current()/../../name]/pdp-context/pdp-type[text()='non-ip']) and (not (/epg/pgw/apn[name=current()/../../name]/non-ip)))" {
        error-message "Must configure NonIp=1 when using pdp type non-IP";
        tailf:dependency "/epg/pgw/apn/pdp-context/pdp-type";
      }
    }
    leaf ipv4-address-saving {
      description
        "Only allocate one IPv6 address for dual stack UE";
      type empty;
    }
    leaf address-allocation {
      description
        "Method used to allocate IPv4 addresses to PDP contexts";
      type enumeration {
        enum static {
          description
            "Only static addresses accepted";
        }
        enum radius {
          description
            "RADIUS authentication assigns addresses";
        }
        enum dhcp-client {
          description
            "DHCP server assigns addresses";
        }
        enum l2tp {
          description
            "L2TP assigns addresses";
        }
        enum shared-ip-pool {
          description
            "GGSN assigns addresses from shared ip pool";
        }
        enum radius-shared-ip-pool {
          description
            "GGSN assigns addresses from either radius or shared ip pool";
        }
      }
    }
    leaf ipv6-address-allocation {
      description
        "Method used to allocate IPv6 addresses to PDP contexts";
      type enumeration {
        enum radius {
          description
            "RADIUS authentication assigns addresses";
        }
        enum shared-ip-pool {
          description
            "GGSN assigns addresses from shared ip pool";
        }
        enum static {
          description
            "HLR/HSS assigns addresses";
        }
        enum radius-shared-ip-pool {
          description
            "GGSN assigns addresses from either radius or shared ip pool";
        }
      }
    }
    leaf ipv6-prefix-delegate {
      description
        "Method used to allocate delegated IPv6 prefix to PDP contexts";
      type enumeration {
        enum radius {
          description
            "Radius authentication assigns delegated ipv6 prefix";
        }
        enum dhcpv6 {
          description
            "Dhcpv6 server assigns delegated ipv6 prefix";
        }
      }
      must '(/epg/pgw/apn[name=current()/../../name]/pdp-context/ipv6-address-allocation)' {
        error-message "ipv6-address-allocation should be configured.";
        tailf:dependency "/epg/pgw/apn/pdp-context/ipv6-address-allocation";
      }
    }
    list address {
      max-elements 99;
      key "name";
      uses apn-address-type;
      status obsolete;
    }
    list ipv6-address {
      max-elements 99;
      key "name";
      uses apn-ipv6-address-type;
      status obsolete;
    }
    leaf limit {
      description
        "Maximum sum of active pgw-only bearers, combined PGW/SGW bearers, and PDP contexts";
      type uint32 {
        range "1..4294967295" {
          error-message "Invalid value for attribute 'limit'. Valid values are in range:[1,4294967295]";
        }
      }
    }
    leaf emps-limit-percentage {
      description
        "emps limit in percentage";
      type uint8 {
        range "1..15" {
          error-message "Invalid value for attribute 'emps-limit-percentage'. Valid values are in range:[1,15]";
        }
      }
    }
    leaf reject-request-without-pco {
      description
        "Reject create pdp context requests if the pco field is missing or empty";
      type empty;
    }
    leaf disable-dedicated-bearer {
      description
        "Disable dedicated bearer support";
      type empty;
    }
    leaf flow-based-traffic-steering {
      description
        "Method used to enable flow based traffic steering";
      type empty;
    }
    leaf prioritized-ip-version {
      description
        "Prioritized IP version for Dual Stack";
      type enumeration {
        enum ipv4 {
          description
            "IPv4 address is assigned when fallback case happens for dual stack";
        }
        enum ipv6 {
          description
            "IPv6 address is assigned when fallback case happens for dual stack";
        }
      }
      must "(/epg/pgw/apn[name=current()/../../name]/pdp-context/pdp-type[text()='ipv4v6']) or (/epg/pgw/apn[name=current()/../../name]/pdp-context/pdp-type[text()='ipv4-ipv6'])" {
        error-message "prioritized-ip-version is configurable only when pdp-type is ipv4v6 or ipv4-ipv6";
        tailf:dependency "/epg/pgw/apn/pdp-context/pdp-type";
      }
    }
    container session-control {
      description
        "Session control settings";
      presence "session-control need presence";
      uses session-management-apn-type;
    }
    container load-distribution {
      description
        "PPB load distribution";
      presence "load-distribution need presence";
      leaf granularity {
        description
          "Granularity to use for PPB load distribution";
        type enumeration {
          enum 32 {
            description
              "Size of slice on PPB is 32";
          }
          enum 16 {
            description
              "Size of slice on PPB is 16";
          }
          enum 8 {
            description
              "Size of slice on PPB is 8";
          }
          enum 4 {
            description
              "Size of slice on PPB is 4";
          }
          enum 2 {
            description
              "Size of slice on PPB is 2";
          }
          enum 1 {
            description
              "Size of slice on PPB is 1";
          }
        }
      }
    }
    leaf alarm-limit {
      description
        "APN utilization limit at which to raise alarm";
      type uint8 {
        range "80..100" {
          error-message "Invalid value for attribute 'alarm-limit'. Valid values are in range:[80,100]";
        }
      }
    }
    container signaling {
      description
        "PDP context signaling settings";
      presence "signaling need presence";
      leaf session-creation-rate {
        description
          "Maximum number of session creation requests for the APN not related to handover, received on any interface, accepted per second\\. Session creation requests received when above the limit are rejected\\. The value states the total number for the APN handled by the node";
        type uint32 {
          range "7..100000" {
            error-message "Invalid value for attribute 'session-creation-rate'. Valid values are in range:[7,100000]";
          }
        }
      }
      leaf locally-initiated-delete-rate {
        description
          "Maximum number of locally initiated deletions for the APN per second\\. The value states the total number of deletions by the node";
        type uint32 {
          range "7..100000" {
            error-message "Invalid value for attribute 'locally-initiated-delete-rate'. Valid values are in range:[7,100000]";
          }
        }
      }
    }
    leaf allow-framed-ip-netmask {
      description
        "Allow framed-ip-netmask attribute from RADIUS";
      type empty;
      must "not (/epg/pgw/apn[name=current()/../../name]/pdp-context/address-allocation[text()='radius-shared-ip-pool'])" {
        error-message "Framed IP Netmask is not allowed when APN is configured for radius-shared-ip-pool address allocation method.";
        tailf:dependency "/epg/pgw/apn/pdp-context/address-allocation";
      }
      must 'not (/epg/pgw/pdp-context/icr)' {
        error-message "Framed IP Netmask is not allowed when ICR is configured.";
        tailf:dependency "/epg/pgw/pdp-context/icr";
      }
    }
    leaf use-framed-route {
      description
        "Use framed route received from RADIUS";
      type empty;
      must "not (/epg/pgw/apn[name=current()/../../name]/pdp-context/address-allocation[text()='radius-shared-ip-pool'])" {
        error-message "Framed Route is not allowed when APN is configured for radius-shared-ip-pool address allocation method.";
        tailf:dependency "/epg/pgw/apn/pdp-context/address-allocation";
      }
      must 'not (/epg/pgw/pdp-context/icr)' {
        error-message "Framed Route is not allowed when ICR is configured.";
        tailf:dependency "/epg/pgw/pdp-context/icr";
      }
    }
    container back-off-time {
      description
        "Set refraining time of subsequent PDN connection establishment to the congested APN";
      presence "back-off-time need presence";
      leaf timer-value {
        description
          "Set value of the timer between 0 and 31.";
        type uint8 {
          range "0..31" {
            error-message "Invalid value for attribute 'timer-value'. Valid values are in range:[0,31]";
          }
        }
      }
      leaf timer-unit {
        description
          "Set incremental factor of the timer\\. Timer value is incremented in multiple of the configured unit.";
        type enumeration {
          enum 2-seconds {
            description
              "2 seconds";
          }
          enum minute {
            description
              "Minute";
          }
          enum 10-minutes {
            description
              "10 minutes";
          }
          enum hour {
            description
              "Hour";
          }
          enum 10-hours {
            description
              "10 hours";
          }
          enum infinite {
            description
              "Infinite";
          }
        }
      }
    }
    action terminate {
      yexte:user-group "ericsson-support,epg-admin";
      description
        "Name of access point name";
      input {
        leaf delete-option {
          description
            "delete option";
          type enumeration {
            enum default-only {
              description
                "Delete session with default bearer only";
            }
            enum bearer-released {
              description
                "Delete session on last dedicated bearer release";
            }
          }
        }
      }
      output {
        leaf result {
          type string;
          mandatory true;
        }
      }
    }
    action terminate-stop {
      yexte:user-group "ericsson-support,epg-admin";
      description
        "Stop EPS session deletion process";
      status current {
        yexte:preliminary;
      }
      output {
        leaf result {
          type string;
          mandatory true;
        }
      }
    }
    action terminate-shared-ip-pool {
      yexte:user-group "ericsson-support,epg-admin";
      description
        "Name of shared ip pool";
      input {
        leaf shared-ip-pool {
          description
            "Name of shared ip pool";
          type leafref {
            path "/epg/pgw/shared-ip-pool/name";
          }
          mandatory true;
        }
        leaf address-range {
          description
            "IPv4 address range";
          type leafref {
            path "/epg/pgw/shared-ip-pool[name=current()/../shared-ip-pool]/address/name";
          }
          must 'not (../ipv6-address-range)' {
            error-message "Do not specify IPv4 and IPv6 address range at the same time";
          }
        }
        leaf ipv6-address-range {
          description
            "IPv6 address range";
          type leafref {
            path "/epg/pgw/shared-ip-pool[name=current()/../shared-ip-pool]/ipv6-address/name";
          }
          must 'not (../address-range)' {
            error-message "Do not specify IPv4 and IPv6 address range at the same time";
          }
        }
        leaf delete-option {
          description
            "delete option";
          type enumeration {
            enum default-only {
              description
                "Delete session with default bearer only";
            }
            enum bearer-released {
              description
                "Delete session on last dedicated bearer release";
            }
          }
        }
      }
      output {
        leaf result {
          type string;
          mandatory true;
        }
      }
    }
    action terminate-imsi {
      yexte:user-group "ericsson-support,epg-admin";
      description
        "Identifier for International Mobile Subscriber Identity";
      input {
        leaf imsi {
          description
            "Identifier for International Mobile Subscriber Identity";
          type string {
            pattern '([0-9]{5,15})|([0-9]{1,14}\*)' {
              error-message "ERROR: Invalid value for parameter imsi. Valid values are strings in a specified format. Type: imsi? for more information on the format to use.";
            }
            length "2..15";
          }
          mandatory true;
        }
      }
      output {
        leaf result {
          type string;
          mandatory true;
        }
      }
    }
    action terminate-idle-session-start {
      yexte:user-group "ericsson-support,epg-admin";
      description
        "start idle session deletion process";
      input {
        leaf idle-monitor-timer {
          description
            "The idleMonitorTimer is defined as the maximum time in seconds for which a session is allowed with no uplink payload";
          type uint16 {
            range "1..65535" {
              error-message "Invalid value for attribute 'idle-monitor-timer'. Valid values are in range:[1,65535]";
            }
          }
          mandatory true;
        }
        leaf delete-condition {
          type enumeration {
            enum shared-ip-pool {
              description
                "sharedIpPool";
            }
          }
        }
        leaf condition-parameter {
          description
            "Shared IP pool name";
          type string {
            pattern '[._0-9A-Za-z-]{1,121}' {
              error-message "Must be a string of 121 or fewer characters and may contain letters, numbers, decimals and dashes.";
            }
          }
        }
      }
      output {
        leaf result {
          type string;
          mandatory true;
        }
      }
    }
    action terminate-idle-session-stop {
      yexte:user-group "ericsson-support,epg-admin";
      description
        "stop idle session deletion process";
      input {
        leaf delete-condition {
          type enumeration {
            enum shared-ip-pool {
              description
                "sharedIpPool";
            }
          }
        }
        leaf condition-parameter {
          description
            "Shared IP pool name";
          type string {
            pattern '[._0-9A-Za-z-]{1,121}' {
              error-message "Must be a string of 121 or fewer characters and may contain letters, numbers, decimals and dashes.";
            }
          }
        }
      }
      output {
        leaf result {
          type string;
          mandatory true;
        }
      }
    }
    action terminate-idle-session-show {
      description
        "show idle session deletion process";
      input {
        leaf delete-condition {
          type enumeration {
            enum shared-ip-pool {
              description
                "sharedIpPool";
            }
          }
        }
      }
      output {
        leaf result {
          type string;
          mandatory true;
        }
      }
    }
  }

  grouping user-plane-type {
    container service-chaining {
      description
        "Service chaining settings";
      uses service-chaining-type;
    }
    container association {
      status current {
        yexte:preliminary;
      }
      description
        "Association settings";
      action info {
        status current {
          yexte:preliminary;
        }
        description
          "Show information related to a PFCP Association";
        input {
          choice node-id {
            leaf fqdn {
              description
                "Fully Qualified Domain Name (FQDN) of association to show";
              type string {
                pattern '[.0-9A-Za-z_-]*' {
                  error-message "Must contain only letters, numbers, underscores or dashes";
                }
                length "1..255";
              }
            }
            leaf ipv4 {
              description
                "IPv4 of association to show";
              type eipv4-prefix-optional;
            }
            leaf ipv6 {
              description
                "IPv6 of association to show";
              type eipv6-prefix-optional;
            }
          }
        }
        output {
          leaf result {
            type string;
            mandatory true;
          }
        }
      }
      container block {
        status current {
          yexte:preliminary;
        }
        yexte:user-group "ericsson-support,epg-admin";
        description
          "New PFCP associations blocked";
        leaf node {
          status current {
            yexte:preliminary;
          }
          description
            "Block on node level";
          type empty;
        }
      }
      action terminate {
        status current {
          yexte:preliminary;
        }
        yexte:user-group "ericsson-support,epg-admin";
        description
          "Terminate PFCP association";
        input {
          choice node-id {
            leaf fqdn {
              description
                "Fully Qualified Domain Name (FQDN) of association to terminate";
              type string {
                pattern '[.0-9A-Za-z_-]*' {
                  error-message "Must contain only letters, numbers, underscores or dashes";
                }
                length "1..255";
              }
            }
            leaf ipv4 {
              description
                "IPv4 of association to terminate";
              type eipv4-prefix-optional;
            }
            leaf ipv6 {
              description
                "IPv6 of association to terminate";
              type eipv6-prefix-optional;
            }
          }
        }
        output {
          leaf result {
            type string;
            mandatory true;
          }
        }
      }
    }
    container lawful-intercept {
      yexte:user-group "epg-lawful-intercept-admin";
      description
        "Configuration for lawful-interception in the user-plane";
      container transport-layer-security {
        description
          "To enable transport layer security";
        leaf node-credential {
          description
            "node-credential reference";
          type leafref {
            path "/epg/node/secm/certm/node-credential/name";
          }
        }
        leaf trust-category {
          description
            "trust-category reference";
          type leafref {
            path "/epg/node/secm/certm/trust-category/name";
          }
        }
      }
    }
    container session {
      status current {
        yexte:preliminary;
      }
      description
        "Session settings";
      container block {
        status current {
          yexte:preliminary;
        }
        yexte:user-group "ericsson-support,epg-admin";
        description
          "New PFCP sessions blocked";
        leaf node {
          status current {
            yexte:preliminary;
          }
          description
            "Block on node level";
          type empty;
        }
      }
      action terminate {
        status current {
          yexte:preliminary;
        }
        yexte:user-group "ericsson-support,epg-admin";
        description
          "Terminate existing PFCP Sessions";
        output {
          leaf result {
            type string;
            mandatory true;
          }
        }
      }
      action info {
        status current {
          yexte:preliminary;
        }
        yexte:user-group "ericsson-support,epg-tracing-admin,epg-admin";
        description
          "Show information related to a PFCP Session";
        input {
          leaf seid {
            description
              "Session Endpoint IDentifier (SEID), given as decimal uint64 or hexadecimal string of octets prefixed by '0x'";
            type union {
              type uint64;
              type string {
                pattern '0x[0-9a-fA-F]+' {
                  error-message "Invalid value for attribute 'seid'. Valid values are decimal uint64 or hexadecimal string of octets prefixed by '0x.'";
                }
              }
            }
          }
        }
        output {
          leaf result {
            type string;
            mandatory true;
          }
        }
      }
    }
    container stop {
      yexte:user-group "ericsson-support,epg-admin";
      description
        "Stop the UPF service";
      leaf node {
        description
          "Stop on node level";
        type empty;
      }
    }
    list network-instance {
      status current {
        yexte:preliminary;
      }
      key "name";
      leaf name {
        status current {
          yexte:preliminary;
        }
        description
          "Network instance name";
        type string {
          pattern '[.0-9A-Za-z_-]*' {
            error-message "Must be a string of 100 or fewer characters and may only contain letters, numbers, decimals, dashes and underscores";
          }
          length "1..100";
        }
      }
      leaf tcp-mss-ipv4 {
        description
          "Maximum TCP segment size (MSS) for end user IPv4 packets per network instance. This attribute overrides tcpMssIpv4 value if it is configured at interface level. This value is applied if TCP MSS feature is active";
        type uint16 {
          range "536..2860" {
            error-message "Invalid value for attribute. 'tcp-mss-ipv4'. Valid values are in range:[536,2860] bytes.";
          }
        }
      }
      leaf tcp-mss-ipv6 {
        description
          "Maximum TCP segment size (MSS) for end user IPv6 packets per network instance. This attribute overrides tcpMssIpv6 value if it is configured at interface level. This value is applied if TCP MSS feature is active";
        type uint16 {
          range "1220..2840" {
            error-message "Invalid value for attribute 'tcp-mss-ipv6'. Valid values are in range:[1220,2840] bytes.";
          }
        }
      }
      leaf routing-context {
        status current {
          yexte:preliminary;
        }
        description
          "Routing context";
        type string;
        must "(/ctxsipos:contexts/ctxipos:context[ctxipos:context-name=current()]) or (/epg/node/direct-io/routing-instance[name=current()])" {
          error-message "either ipos or direct-io routing instance should be configured";
        }
        mandatory true;
      }
      action statistics {
        description
          "Show UPF network-instance statistics";
        output {
          leaf result {
            type string;
            mandatory true;
          }
        }
      }
      container network-address-translation {
        status current {
          yexte:preliminary;
        }
        leaf-list nat-ip-pool {
          status current {
            yexte:preliminary;
          }
          description
            "Previously defined CGNAT pools";
          type leafref {
            path "../../../network-address-translation/nat-ip-pool/pool-name";
          }
        }
      }
      container interface {
        status current {
          yexte:preliminary;
        }
        container cp-function {
          status current {
            yexte:preliminary;
          }
          description
            "cp-function interface (Sx/N4) settings";
          leaf address {
            status current {
              yexte:preliminary;
            }
            description
              "Sx/N4 IPv4 address";
            type eipv4-prefix-optional;
          }
          leaf ipv6-address {
            status current {
              yexte:preliminary;
            }
            description
              "Sx/N4 IPv6 address";
            type eipv6-prefix-optional;
          }
          leaf heartbeat-interval {
            status current {
              yexte:preliminary;
            }
            description
              "Specifies the interval, in seconds, between Heartbeat procedures";
            type uint16 {
              range "1..600" {
                error-message "Invalid value for attribute 'heartbeat-interval'. Valid values are in range:[1,600]";
              }
            }
            default "60";
          }
          leaf ignore-path-failure {
            status current {
              yexte:preliminary;
            }
            description
              "Don't terminate sessions on path failure";
            type empty;
          }
          leaf disable-path-management {
            status current {
              yexte:preliminary;
            }
            description
              "Disable path management - no Heartbeat Requests are sent";
            type empty;
          }
          leaf n1-requests {
            status current {
              yexte:preliminary;
            }
            description
              "Specifies the max number of transmissions of PFCP Request";
            type uint16 {
              range "1..8" {
                error-message "Invalid value for attribute 'n1-requests'. Valid values are in range:[1,8]";
              }
            }
            default "3";
          }
          leaf t1-response-time {
            status current {
              yexte:preliminary;
            }
            description
              "Specifies how long time, in seconds, to wait for a response before considering the request lost";
            type string {
              pattern '((0.[3-9])|([1-9])|([1-9].[0-9])|([1-2][0-9])|([1-2][0-9].[0-9])|(30)|(30.0))' {
                error-message "Invalid value for attribute 't1-response-time'. Valid values are in range:[0.3,30.0]";
              }
            }
            default "3.0";
          }
          leaf heartbeat-n1-requests {
            status current {
              yexte:preliminary;
            }
            description
              "Specifies the max number of transmissions of Heartbeat Request";
            type uint16 {
              range "1..30" {
                error-message "Invalid value for attribute 'heartbeat-n1-requests'. Valid values are in range:[1,30]";
              }
            }
            default "10";
          }
          leaf heartbeat-t1-response-time {
            status current {
              yexte:preliminary;
            }
            description
              "Specifies how long time, in seconds, to wait for a Heartbeat Response before considering the Heartbeat Request lost";
            type string {
              pattern '((0.[3-9])|([1-9])|([1-9].[0-9])|([1-2][0-9])|([1-2][0-9].[0-9])|(30)|(30.0))' {
                error-message "Invalid value for attribute 't1-response-time'. Valid values are in range:[0.3,30.0]";
              }
            }
            default "3.0";
          }
          container li-t3 {
            yexte:user-group "epg-lawful-intercept-admin";
            status current {
              yexte:preliminary;
            }
            description
              "li-t3 interface";
            leaf shared-secret {
              status current {
                yexte:preliminary;
              }
              description
                "li-t3 shared secret key";
              type tailf:aes-cfb-128-encrypted-string;
            }
            leaf port {
              status current {
                yexte:preliminary;
              }
              description
                "li-t3 port number";
              type uint16;
              must '(/epg/user-plane/network-instance/interface/li-function/address) or (/epg/user-plane/network-instance/interface/li-function/ipv6-address)' {
                error-message "LI-T3 requires a network-instance with an li-function with at least one IPv4/IPv6 address";
              }
            }
          }
        }
        container access {
          status current {
            yexte:preliminary;
          }
          description
            "Access interface settings";
          leaf gtp-address {
            status current {
              yexte:preliminary;
            }
            description
              "GTP address or address range";
            type eipv4-prefix-optional;
          }
          leaf gtp-ipv6-address {
            status current {
              yexte:preliminary;
            }
            description
              "GTP IPv6 address or IPv6 address range";
            type eipv6-prefix-optional;
          }
          leaf gtp-ingress-optimization {
            status current {
              yexte:preliminary;
            }
            description
              "Enable ingress optimization for this GTP based interface";
            type empty;
          }
          leaf tcp-mss-ipv4 {
            description
              "Maximum TCP segment size (MSS) for end user IPv4 packets per network interface. This value is applied if TCP MSS feature is active.";
            type uint16 {
              range "536..2860" {
                error-message "Invalid value for attribute 'tcp-mss-ipv4'. Valid values are in range:[536,2860] bytes";
              }
            }
          }
          leaf tcp-mss-ipv6 {
            description
              "Maximum TCP segment size (MSS) for end user IPv6 packets per network interface. This value is applied if TCP MSS feature is active.";
            type uint16 {
              range "1220..2840" {
                error-message "Invalid value for attribute 'tcp-mss-ipv6'. Valid values are in range:[1220,2840] bytes";
              }
            }
          }
        }
        container core {
          status current {
            yexte:preliminary;
          }
          description
            "Core interface settings";
          presence "core need presence";
          leaf gtp-address {
            status current {
              yexte:preliminary;
            }
            description
              "GTP address or address range";
            type eipv4-prefix-optional;
          }
          leaf gtp-ipv6-address {
            status current {
              yexte:preliminary;
            }
            description
              "GTP IPv6 address or IPv6 address range";
            type eipv6-prefix-optional;
          }
          leaf gtp-ingress-optimization {
            status current {
              yexte:preliminary;
            }
            description
              "Enable ingress optimization for this GTP based interface";
            type empty;
          }
          leaf-list sgi-address-range {
            status current {
              yexte:preliminary;
            }
            description
              "IPv4 or IPv6 address ranges for SGi";
            max-elements 99;
            type eip-prefix;
          }
          leaf tcp-mss-ipv4 {
            description
              "Maximum TCP segment size (MSS) for end user IPv4 packets per network interface. This value is applied if TCP MSS feature is active.";
            type uint16 {
              range "536..2860" {
                error-message "Invalid value for attribute 'tcp-mss-ipv4'. Valid values are in range:[536,2860] bytes";
              }
            }
          }
          leaf tcp-mss-ipv6 {
            description
              "Maximum TCP segment size (MSS) for end user IPv6 packets per network interface. This value is applied if TCP MSS feature is active.";
            type uint16 {
              range "1220..2840" {
                error-message "Invalid value for attribute 'tcp-mss-ipv6'. Valid values are in range:[1220,2840] bytes";
              }
            }
          }
        }
        container li-function {
          yexte:user-group "epg-lawful-intercept-admin";
          status current {
            yexte:preliminary;
          }
          description
            "Li function interface settings";
          leaf address {
            status current {
              yexte:preliminary;
            }
            description
              "Li function address";
            type eipv4-address;
          }
          leaf ipv6-address {
            status current {
              yexte:preliminary;
            }
            description
              "Li function IPv6 address";
            type eipv6-address;
          }
          leaf dscp {
            status current {
              yexte:preliminary;
            }
            description
              "DSCP (DiffServ Code Point) for packets";
            type enumeration {
              enum af11 {
                description
                  "Assured forwarding class 1, low drop precedence";
              }
              enum af12 {
                description
                  "Assured forwarding class 1, medium drop precedence";
              }
              enum af13 {
                description
                  "Assured forwarding class 1, high drop precedence";
              }
              enum af21 {
                description
                  "Assured forwarding class 2, low drop precedence";
              }
              enum af22 {
                description
                  "Assured forwarding class 2, medium drop precedence";
              }
              enum af23 {
                description
                  "Assured forwarding class 2, high drop precedence";
              }
              enum af31 {
                description
                  "Assured forwarding class 3, low drop precedence";
              }
              enum af32 {
                description
                  "Assured forwarding class 3, medium drop precedence";
              }
              enum af33 {
                description
                  "Assured forwarding class 3, high drop precedence";
              }
              enum af41 {
                description
                  "Assured forwarding class 4, low drop precedence";
              }
              enum af42 {
                description
                  "Assured forwarding class 4, medium drop precedence";
              }
              enum af43 {
                description
                  "Assured forwarding class 4, high drop precedence";
              }
              enum ef {
                description
                  "Expedited forwarding";
              }
              enum be {
                description
                  "Best effort forwarding";
              }
              enum cs1 {
                description
                  "Class selector 1";
              }
              enum cs2 {
                description
                  "Class selector 2";
              }
              enum cs3 {
                description
                  "Class selector 3";
              }
              enum cs4 {
                description
                  "Class selector 4";
              }
              enum cs5 {
                description
                  "Class selector 5";
              }
              enum cs6 {
                description
                  "Class selector 6";
              }
              enum cs7 {
                description
                  "Class selector 7";
              }
            }
          }
        }
      }
      container icr {
        description
          "Enable ICR for this interface";
        presence "icr need presence";
        leaf tracked {
          description
            "Toggle to enable that this interface will trigger an ICR switchover in case of problem";
          type empty;
        }
      }
    }
    leaf default-cp-function-network-instance {
      status current {
        yexte:preliminary;
      }
      description
        "Default Network Instance for cp-function interface";
      type leafref {
        path "/epg/user-plane/network-instance/name";
      }
      mandatory true;
      must '(/epg/user-plane/network-instance[name=current()]/interface/cp-function/address) or (/epg/user-plane/network-instance[name=current()]/interface/cp-function/ipv6-address)' {
        error-message "The default cp-function network instance must at least have one IPv4/IPv6 address [epg user-plane network-instance]";
      }
    }
    leaf default-access-network-instance {
      status current {
        yexte:preliminary;
      }
      description
        "Default Network Instance for Access interface";
      type leafref {
        path "/epg/user-plane/network-instance/name";
      }
      mandatory true;
      must '(/epg/user-plane/network-instance[name=current()]/interface/access/gtp-address) or (/epg/user-plane/network-instance[name=current()]/interface/access/gtp-ipv6-address)' {
        error-message "The default access network instance must have an access interface with at least one IPv4/IPv6 gtp-address [epg user-plane network-instance]";
      }
    }
    leaf default-core-network-instance {
      status current {
        yexte:preliminary;
      }
      description
        "Default Network Instance for Core interface";
      type leafref {
        path "/epg/user-plane/network-instance/name";
      }
      mandatory true;
    }
    container internal-debug {
      yexte:user-group "ericsson-support";
      description
        "Commands for internal debugging";
      container packet-detection {
        description
          "Commands for packet detection debugging";
        container clear {
          description
            "Clear commands";
          action dynamic-rules {
            description
              "Clear IP addresses discovered through IP Domain matching";
            output {
              leaf result {
                type string;
                mandatory true;
              }
            }
          }
        }
      }
      container timer-wheel {
        description
          "timer-wheel";
        status current {
          yexte:preliminary;
        }
        container show {
          description
            "Show timer-wheel information";
          container detail {
            description
              "Show timer-wheel detailed information";
            action status {
              description
                "Show timer-wheel detailed status";
              output {
                leaf result {
                  type string;
                  mandatory true;
                }
              }
            }
            action statistics {
              description
                "show timer-wheel detailed statistics";
              output {
                leaf result {
                  type string;
                  mandatory true;
                }
              }
            }
          }
          action status {
            description
              "Show timer-wheel status";
            output {
              leaf result {
                type string;
                mandatory true;
              }
            }
          }
          action statistics {
            description
              "show timer-wheel statistics";
            output {
              leaf result {
                type string;
                mandatory true;
              }
            }
          }
          container dbproxy {
            description
              "timer-wheel show db-proxy";
            action statistics {
              description
                "Show timer-wheel db-proxy statistics";
              output {
                leaf result {
                  type string;
                  mandatory true;
                }
              }
            }
          }
          action log-level {
            description
              "Show timer-wheel log-level setting";
            output {
              leaf result {
                type string;
                mandatory true;
              }
            }
          }
        }
        container set {
          description
            "Change timer-wheel settings";
          action log-level {
            description
              "Set new timer-wheel log-level";

            input {
              leaf level {
                type log-level;
              }
            }
            output {
              leaf result {
                type string;
                mandatory true;
              }
            }
          }
        }
        container memtracker {
          description
            "timer-wheel memtracker";
          action start {
            description
              "Start memtracker for timer-wheel process";
            output {
              leaf result {
                type string;
                mandatory true;
              }
            }
          }
          action stop {
            description
              "Stop memtracker for timer-wheel process";
            output {
              leaf result {
                type string;
                mandatory true;
              }
            }
          }
          action report {
            description
              "Generate timer-wheel memtracker report";
            output {
              leaf result {
                type string;
                mandatory true;
              }
            }
          }
          action status {
            description
              "Show timer-wheel memtracker status";
            output {
              leaf result {
                type string;
                mandatory true;
              }
            }
          }
        }
      }
      container pfcp-endpoint {
        description
          "PFCP Endpoint";
        status current {
          yexte:preliminary;
        }
        container show {
          description
            "Display information";
          container association {
            description
              "Display information";
            action transactions {
              description
                "Show ongoing association transactions";
              input {
                leaf lifetime {
                  description
                    "Transaction lifetime limit, in milliseconds";
                  type uint32;
                }
              }
              output {
                leaf result {
                  type string;
                  mandatory true;
                }
              }
            }
            action info {
              description
                "Show Association and Path information";
              output {
                leaf result {
                  type string;
                  mandatory true;
                }
              }
            }
          }
          container path {
            description
              "Display information";
            action transactions {
              description
                "Show ongoing path transactions";
              input {
                leaf lifetime {
                  description
                    "Transaction lifetime limit, in milliseconds";
                  type uint32;
                }
              }
              output {
                leaf result {
                  type string;
                  mandatory true;
                }
              }
            }
          }
          action status {
            description
              "Show PFCP-Endpoint status";
            output {
              leaf result {
                type string;
                mandatory true;
              }
            }
          }
          action statistics {
            description
              "Show PFCP-Endpoint statistics";
            output {
              leaf result {
                type string;
                mandatory true;
              }
            }
          }
          action process {
            description
              "Show PFCP-Endpoint process information";
            output {
              leaf result {
                type string;
                mandatory true;
              }
            }
          }
          container dbproxy {
            description
              "Database Proxy";
            action statistics {
              description
                "Show db-proxy statistics";
              output {
                leaf result {
                  type string;
                  mandatory true;
                }
              }
            }
          }
          container twadapter {
            description
              "Timer Wheel Adapter";
            action statistics {
              description
                "Show tw-adapter statistics";
              output {
                leaf result {
                  type string;
                  mandatory true;
                }
              }
            }
          }
          action config {
            description
              "Show PFCP-Endpoint config";
            output {
              leaf result {
                type string;
                mandatory true;
              }
            }
          }
        }
        action logging {
          description
            "Logging";

          input {
            choice module {
              leaf all {
                type log-level;
              }
              leaf pfcp {
                type log-level;
              }
              leaf association {
                type log-level;
              }
              leaf session {
                type log-level;
              }
              leaf pathsupervisor {
                type log-level;
              }
              leaf dbmodule {
                type log-level;
              }
              leaf twmodule {
                type log-level;
              }
              leaf dpadapter {
                type log-level;
              }
            }
          }
          output {
            leaf result {
              type string;
              mandatory true;
            }
          }
        }
      }
      container data-plane {
        description
          "Internal data-plane commands";
        status current {
          yexte:preliminary;
        }
        container protocol {
          description
            "Protocol commands";
          status current {
            yexte:preliminary;
          }
          container bfd {
            status current {
              yexte:preliminary;
            }
            description
              "Bfd commands";
            action show {
              description
                "Print bfd statistics";
              input {
                leaf board {
                  description
                    "Show statistics only from board (e.g\\. gu-0/5/0)";
                  type string {
                    pattern '(gu-0/(30|(1|2)[0-9]|[1-9])/0)' {
                      error-message "Invalid board name";
                    }
                  }
                }
              }
              output {
                leaf result {
                  type string;
                  mandatory true;
                }
              }
            }
          }
          container lacp {
            status current {
              yexte:preliminary;
            }
            description
              "Lacp commands";
            action show {
              description
                "Print lacp";
              input {
                leaf board {
                  description
                    "Show statistics only from board (e.g\\. gu-0/5/0)";
                  type string {
                    pattern '(gu-0/(30|(1|2)[0-9]|[1-9])/0)' {
                      error-message "Invalid board name";
                    }
                  }
                }
              }
              output {
                leaf result {
                  type string;
                  mandatory true;
                }
              }
            }
          }
          container ndp {
            status current {
              yexte:preliminary;
            }
            description
              "Ndp commands";
            action show {
              description
                "Print ndp";
              input {
                leaf board {
                  description
                    "Show statistics only from board (e.g\\. gu-0/5/0)";
                  type string {
                    pattern '(gu-0/(30|(1|2)[0-9]|[1-9])/0)' {
                      error-message "Invalid board name";
                    }
                  }
                }
              }
              output {
                leaf result {
                  type string;
                  mandatory true;
                }
              }
            }
          }
          container arp {
            description
              "Adress Resolution Protocol";
            status current {
              yexte:preliminary;
            }
            action show {
              description
                "Print arp";
              input {
                leaf board {
                  description
                    "Show statistics only from board (e.g\\. gu-0/5/0)";
                  type string {
                    pattern '(gu-0/(30|(1|2)[0-9]|[1-9])/0)' {
                      error-message "Invalid board name";
                    }
                  }
                }
              }
              output {
                leaf result {
                  type string;
                  mandatory true;
                }
              }
            }
          }
          container dtls {
            status current {
              yexte:preliminary;
            }
            description
              "Datagram Transport Layer Security";
            action show {
              description
                "Print dtls";
              input {
                leaf board {
                  description
                    "Show statistics only from board (e.g\\. gu-0/5/0)";
                  type string {
                    pattern '(gu-0/(30|(1|2)[0-9]|[1-9])/0)' {
                      error-message "Invalid board name";
                    }
                  }
                }
              }
              output {
                leaf result {
                  type string;
                  mandatory true;
                }
              }
            }
            container log {
              status current {
                yexte:preliminary;
              }
              description
                "Log options";
              leaf enable {
                status current {
                  yexte:preliminary;
                }
                description
                  "Enable logging";
                type empty;
              }
            }
          }
          container gre {
            status current {
              yexte:preliminary;
            }
            description
              "Generic Routing Encapsulation";
            container log {
              status current {
                yexte:preliminary;
              }
              description
                "Log options";
              container control {
                status current {
                  yexte:preliminary;
                }
                description
                  "Control logs";
                leaf enable {
                  status current {
                    yexte:preliminary;
                  }
                  description
                    "Enable logging";
                  type empty;
                }
              }
              container data {
                status current {
                  yexte:preliminary;
                }
                description
                  "Data logs";
                leaf enable {
                  status current {
                    yexte:preliminary;
                  }
                  description
                    "Enable logging";
                  type empty;
                }
              }
            }
          }
          container gtp {
            status current {
              yexte:preliminary;
            }
            description
              "GPRS Tunneling Protocol";
            container tunnel-access {
              status current {
                yexte:preliminary;
              }
              description
                "GTP tunnel access commands";
              action show {
                description
                  "Print max 10000 ACCESS gtp tunnels";
                input {
                  leaf board {
                    description
                      "Show statistics only from board (e.g\\. gu-0/5/0)";
                    type string {
                      pattern '(gu-0/(30|(1|2)[0-9]|[1-9])/0)' {
                        error-message "Invalid board name";
                      }
                    }
                  }
                }
                output {
                  leaf result {
                    type string;
                    mandatory true;
                  }
                }
              }
            }
            container tunnel-core {
              status current {
                yexte:preliminary;
              }
              description
                "Tunnel-core commands";
              action show {
                description
                  "Print max 10000 CORE gtp tunnels";
                input {
                  leaf board {
                    description
                      "Show statistics only from board (e.g\\. gu-0/5/0)";
                    type string {
                      pattern '(gu-0/(30|(1|2)[0-9]|[1-9])/0)' {
                        error-message "Invalid board name";
                      }
                    }
                  }
                }
                output {
                  leaf result {
                    type string;
                    mandatory true;
                  }
                }
              }
            }
            action show {
              description
                "Print gtp";
              input {
                leaf board {
                  description
                    "Show statistics only from board (e.g\\. gu-0/5/0)";
                  type string {
                    pattern '(gu-0/(30|(1|2)[0-9]|[1-9])/0)' {
                      error-message "Invalid board name";
                    }
                  }
                }
              }
              output {
                leaf result {
                  type string;
                  mandatory true;
                }
              }
            }
            container log {
              status current {
                yexte:preliminary;
              }
              description
                "Log options";
              leaf enable {
                status current {
                  yexte:preliminary;
                }
                description
                  "Enable logging";
                type empty;
              }
            }
          }
          container ipudp {
            status current {
              yexte:preliminary;
            }
            description
              "IP User Datagram Protocol";
            action show {
              description
                "Print ipudp";
              input {
                leaf board {
                  description
                    "Show statistics only from board (e.g\\. gu-0/5/0)";
                  type string {
                    pattern '(gu-0/(30|(1|2)[0-9]|[1-9])/0)' {
                      error-message "Invalid board name";
                    }
                  }
                }
              }
              output {
                leaf result {
                  type string;
                  mandatory true;
                }
              }
            }
            container log {
              status current {
                yexte:preliminary;
              }
              description
                "Log options";
              leaf enable {
                status current {
                  yexte:preliminary;
                }
                description
                  "Enable logging";
                type empty;
              }
            }
          }
        }
        container dropfifo {
          status current {
            yexte:preliminary;
          }
          description
            "Dropfifo commands";
          container gtp {
            status current {
              yexte:preliminary;
            }
            description
              "Commands for the dropfifo on GTP";
            action status {
              status current {
                yexte:preliminary;
              }
              description
                "Information about the the dropfifo on gtp";
              output {
                leaf result {
                  type string;
                  mandatory true;
                }
              }
            }
            action enable {
              status current {
                yexte:preliminary;
              }
              description
                "Enable the dropfifo on gtp";
              output {
                leaf result {
                  type string;
                  mandatory true;
                }
              }
            }
            action disable {
              status current {
                yexte:preliminary;
              }
              description
                "Disable the dropfifo on gtp";
              output {
                leaf result {
                  type string;
                  mandatory true;
                }
              }
            }
            action dimension {
              status current {
                yexte:preliminary;
              }
              description
                "Set the dimension (number of elements x size of elements) in the dropfifo on gtp";
              input {
                leaf set {
                  description
                    "The number of elements x the size of each element, eg. 10x1000.";
                  type string {
                    pattern '[0-9]+x[0-9]+' {
                      error-message "Invalid value for attribute 'value'. Valid values are two numbers separated by 'x'. Eg. 10x1000.";
                    }
                  }
                }
              }
              output {
                leaf result {
                  type string;
                  mandatory true;
                }
              }
            }
            container snapshots {
              status current {
                yexte:preliminary;
              }
              description
                "Manage snapshots of a dropfifo";
              action list {
                description
                  "List the existing snapshots on gtp";
                output {
                  leaf result {
                    type string;
                    mandatory true;
                  }
                }
              }
              action clear {
                description
                  "Clear the list of snapshots on gtp";
                output {
                  leaf result {
                    type string;
                    mandatory true;
                  }
                }
              }
              action take {
                description
                  "Take a snapshot of the dropfifo on gtp";
                output {
                  leaf result {
                    type string;
                    mandatory true;
                  }
                }
              }
              action show {
                description
                  "Show one of the dropfifo snapshots on gtp";
                input {
                  leaf number {
                    description
                      "The index of the snapshot from 1 to # of snapshots (chronological order)";
                    type uint32;
                  }
                }
                output {
                  leaf result {
                    type string;
                    mandatory true;
                  }
                }
              }
              action pcap {
                description
                  "Create pcap file from one of the dropfifo snapshots on gtp";
                input {
                  leaf number {
                    description
                      "The index of the snapshot from 1 to # of snapshots (chronological order)";
                    type uint32;
                  }
                }
                output {
                  leaf result {
                    type string;
                    mandatory true;
                  }
                }
              }
            }
          }
          container all {
            status current {
              yexte:preliminary;
            }
            description
              "Commands for the dropfifo on all protocols";
            action status {
              status current {
                yexte:preliminary;
              }
              description
                "Information about the dropfifo on all protocols";
              output {
                leaf result {
                  type string;
                  mandatory true;
                }
              }
            }
            action enable {
              status current {
                yexte:preliminary;
              }
              description
                "Enable the dropfifo on all protocols";
              output {
                leaf result {
                  type string;
                  mandatory true;
                }
              }
            }
            action disable {
              status current {
                yexte:preliminary;
              }
              description
                "Disable the dropfifo on all protocols";
              output {
                leaf result {
                  type string;
                  mandatory true;
                }
              }
            }
            action dimension {
              status current {
                yexte:preliminary;
              }
              description
                "Set the dimension (number of elements x size of elements) in the dropfifo on all protocols";
              input {
                leaf set {
                  description
                    "The number of elements x the size of each element, eg. 10x1000.";
                  type string {
                    pattern '[0-9]+x[0-9]+' {
                      error-message "Invalid value for attribute 'value'. Valid values are two numbers separated by 'x'. Eg. 10x1000.";
                    }
                  }
                }
              }
              output {
                leaf result {
                  type string;
                  mandatory true;
                }
              }
            }
            container snapshots {
              status current {
                yexte:preliminary;
              }
              description
                "Manage snapshots of a dropfifo";
              action list {
                description
                  "List the existing snapshots on all protocols";
                output {
                  leaf result {
                    type string;
                    mandatory true;
                  }
                }
              }
              action clear {
                description
                  "Clear the list of snapshots on all protocols";
                output {
                  leaf result {
                    type string;
                    mandatory true;
                  }
                }
              }
              action take {
                description
                  "Take a snapshot of the dropfifo on all protocols";
                output {
                  leaf result {
                    type string;
                    mandatory true;
                  }
                }
              }
            }
          }
        }
        container framework {
          status current {
            yexte:preliminary;
          }
          description
            "Framework commands";
          container bsp-mailbox {
            status current {
              yexte:preliminary;
            }
            description
              "BSP mailbox commands";
            action show {
              description
                "Print mailbox";
              input {
                leaf board {
                  description
                    "Show statistics only from board (e.g\\. gu-0/5/0)";
                  type string {
                    pattern '(gu-0/(30|(1|2)[0-9]|[1-9])/0)' {
                      error-message "Invalid board name";
                    }
                  }
                }
              }
              output {
                leaf result {
                  type string;
                  mandatory true;
                }
              }
            }
            container log {
              status current {
                yexte:preliminary;
              }
              description
                "Log options";
              leaf enable {
                status current {
                  yexte:preliminary;
                }
                description
                  "Enable logging";
                type empty;
              }
            }
          }
          container bsp-memory {
            status current {
              yexte:preliminary;
            }
            description
              "BSP Memory commands";
            action show {
              description
                "Print BSP memory";
              input {
                leaf board {
                  description
                    "Show statistics only from board (e.g\\. gu-0/5/0)";
                  type string {
                    pattern '(gu-0/(30|(1|2)[0-9]|[1-9])/0)' {
                      error-message "Invalid board name";
                    }
                  }
                }
              }
              output {
                leaf result {
                  type string;
                  mandatory true;
                }
              }
            }
          }
          container sysmon {
            status current {
              yexte:preliminary;
            }
            description
              "Sysmon commands";
            action show {
              description
                "Print sysmon";
              input {
                leaf board {
                  description
                    "Show statistics only from board (e.g\\. gu-0/5/0)";
                  type string {
                    pattern '(gu-0/(30|(1|2)[0-9]|[1-9])/0)' {
                      error-message "Invalid board name";
                    }
                  }
                }
              }
              output {
                leaf result {
                  type string;
                  mandatory true;
                }
              }
            }
          }
          container cpu-load {
            status current {
              yexte:preliminary;
            }
            description
              "CPU-load commands";
            action show {
              description
                "print cpu load";
              input {
                leaf board {
                  description
                    "Show statistics only from board (e.g\\. gu-0/5/0)";
                  type string {
                    pattern '(gu-0/(30|(1|2)[0-9]|[1-9])/0)' {
                      error-message "Invalid board name";
                    }
                  }
                }
              }
              output {
                leaf result {
                  type string;
                  mandatory true;
                }
              }
            }
          }
          container timers {
            status current {
              yexte:preliminary;
            }
            description
              "Timers commands";
            action show {
              description
                "Print normal timers";
              input {
                leaf board {
                  description
                    "Show statistics only from board (e.g\\. gu-0/5/0)";
                  type string {
                    pattern '(gu-0/(30|(1|2)[0-9]|[1-9])/0)' {
                      error-message "Invalid board name";
                    }
                  }
                }
              }
              output {
                leaf result {
                  type string;
                  mandatory true;
                }
              }
            }
          }
          container pkt-adm {
            status current {
              yexte:preliminary;
            }
            description
              "pkt-adm commands";
            action show {
              description
                "Print pkt-adm";
              input {
                leaf board {
                  description
                    "Show statistics only from board (e.g\\. gu-0/5/0)";
                  type string {
                    pattern '(gu-0/(30|(1|2)[0-9]|[1-9])/0)' {
                      error-message "Invalid board name";
                    }
                  }
                }
              }
              output {
                leaf result {
                  type string;
                  mandatory true;
                }
              }
            }
          }
          container pktio {
            status current {
              yexte:preliminary;
            }
            description
              "Pktio commands";
            container detail {
              status current {
                yexte:preliminary;
              }
              description
                "Pktio-detail commands";
              action show {
                description
                  "Print pktio-detail";
                input {
                  leaf board {
                    description
                      "Show statistics only from board (e.g\\. gu-0/5/0)";
                    type string {
                      pattern '(gu-0/(30|(1|2)[0-9]|[1-9])/0)' {
                        error-message "Invalid board name";
                      }
                    }
                  }
                }
                output {
                  leaf result {
                    type string;
                    mandatory true;
                  }
                }
              }
            }
            container reassembler {
              status current {
                yexte:preliminary;
              }
              description
                "Pktio-reassembler commands";
              action show {
                description
                  "Print pktio-reassembler";
                input {
                  leaf board {
                    description
                      "Show statistics only from board (e.g\\. gu-0/5/0)";
                    type string {
                      pattern '(gu-0/(30|(1|2)[0-9]|[1-9])/0)' {
                        error-message "Invalid board name";
                      }
                    }
                  }
                }
                output {
                  leaf result {
                    type string;
                    mandatory true;
                  }
                }
              }
            }
          }
          container dbproxy {
            status current {
              yexte:preliminary;
            }
            description
              "DBproxy commands";
            action show {
              description
                "Print rdb dbproxy";
              output {
                leaf result {
                  type string;
                  mandatory true;
                }
              }
            }
          }
        }
        container service {
          status current {
            yexte:preliminary;
          }
          description
            "Service commands";
          container lim {
            status current {
              yexte:preliminary;
            }
            description
              "Lim commands";
            action show {
              description
                "Print upf lim controller";
              input {
                leaf board {
                  description
                    "Show statistics only from board (e.g\\. gu-0/5/0)";
                  type string {
                    pattern '(gu-0/(30|(1|2)[0-9]|[1-9])/0)' {
                      error-message "Invalid board name";
                    }
                  }
                }
              }
              output {
                leaf result {
                  type string;
                  mandatory true;
                }
              }
            }
            container log {
              status current {
                yexte:preliminary;
              }
              description
                "LIM logs";
              leaf enable {
                status current {
                  yexte:preliminary;
                }
                description
                  "Enable logging";
                type empty;
              }
              leaf-list filter {
                status current {
                  yexte:preliminary;
                }
                description
                  "Load index to log";
                type string {
                  pattern '([0-9])|([1-9][0-9]{0,10})|(0-[1-9][0-9]{0,10})|([1-9][0-9]{0,10}-[1-9][0-9]{0,10})' {
                    error-message "Must be a single integer or a range of integers of the form 'X-Y'.";
                  }
                }
              }
            }
          }
          container lim-table {
            status current {
              yexte:preliminary;
            }
            description
              "Lim-table commands";
            action show {
              description
                "Print upf lim table";
              input {
                leaf board {
                  description
                    "Show statistics only from board (e.g\\. gu-0/5/0)";
                  type string {
                    pattern '(gu-0/(30|(1|2)[0-9]|[1-9])/0)' {
                      error-message "Invalid board name";
                    }
                  }
                }
              }
              output {
                leaf result {
                  type string;
                  mandatory true;
                }
              }
            }
          }
          container loadindex-distribution {
            status current {
              yexte:preliminary;
            }
            description
              "loadindex-distribution commands";
            action show {
              description
                "Print active and standby loadindex distribution";
              output {
                leaf result {
                  type string;
                  mandatory true;
                }
              }
            }
          }
          container event-agent {
            status current {
              yexte:preliminary;
            }
            description
              "Event agent";
            container log {
              status current {
                yexte:preliminary;
              }
              description
                "Log options";
              leaf enable {
                status current {
                  yexte:preliminary;
                }
                description
                  "Enable logging";
                type empty;
              }
            }
          }
          container icd-service {
            status current {
              yexte:preliminary;
            }
            description
              "Icd service";
            container log {
              status current {
                yexte:preliminary;
              }
              description
                "Log options";
              leaf enable {
                status current {
                  yexte:preliminary;
                }
                description
                  "Enable logging";
                type empty;
              }
            }
          }
          container icmagent {
            status current {
              yexte:preliminary;
            }
            description
              "PIAF internal configuration management agent";
            container log {
              status current {
                yexte:preliminary;
              }
              description
                "Log options";
              leaf enable {
                status current {
                  yexte:preliminary;
                }
                description
                  "Enable logging";
                type empty;
              }
            }
          }
          container ppbconfig {
            status current {
              yexte:preliminary;
            }
            description
              "PPB config";
            container log {
              status current {
                yexte:preliminary;
              }
              description
                "Log options";
              leaf enable {
                status current {
                  yexte:preliminary;
                }
                description
                  "Enable logging";
                type empty;
              }
            }
          }
          container rsadapter {
            status current {
              yexte:preliminary;
            }
            description
              "Rsadapter commands";
            action show {
              description
                "Print rsadapter statistics";
              output {
                leaf result {
                  type string;
                  mandatory true;
                }
              }
            }
            container log {
              status current {
                yexte:preliminary;
              }
              description
                "Log options";
              leaf enable {
                status current {
                  yexte:preliminary;
                }
                description
                  "Enable logging";
                type empty;
              }
            }
          }
        }
        container session {
          status current {
            yexte:preliminary;
          }
          description
            "PFCP session commands";
          container config {
            status current {
              yexte:preliminary;
            }
            description
              "Commands for upf-configuration";
            action show {
              description
                "Print information related to UPF configuration";
              input {
                leaf board {
                  description
                    "Show statistics only from board (e.g\\. gu-0/5/0)";
                  type string {
                    pattern '(gu-0/(30|(1|2)[0-9]|[1-9])/0)' {
                      error-message "Invalid board name";
                    }
                  }
                }
              }
              output {
                leaf result {
                  type string;
                  mandatory true;
                }
              }
            }
          }
          container reprovision {
            status current {
              yexte:preliminary;
            }
            description
              "Commands for upf-reprovision";
            action show {
              description
                "Print information related to UPF reprovision";
              input {
                leaf board {
                  description
                    "Show statistics only from board (e.g\\. gu-0/5/0)";
                  type string {
                    pattern '(gu-0/(30|(1|2)[0-9]|[1-9])/0)' {
                      error-message "Invalid board name";
                    }
                  }
                }
              }
              output {
                leaf result {
                  type string;
                  mandatory true;
                }
              }
            }
          }
          container nw-instance-cache {
            status current {
              yexte:preliminary;
            }
            description
              "Nw-instance-cache commands";
            action show {
              description
                "Print information related to nw instance cache";
              input {
                leaf board {
                  description
                    "Show statistics only from board (e.g\\. gu-0/5/0)";
                  type string {
                    pattern '(gu-0/(30|(1|2)[0-9]|[1-9])/0)' {
                      error-message "Invalid board name";
                    }
                  }
                }
              }
              output {
                leaf result {
                  type string;
                  mandatory true;
                }
              }
            }
          }
          container user-plane {
            status current {
              yexte:preliminary;
            }
            description
              "user-plane function";
            action show {
              description
                "Print upf controller, up session controller and upf engine";
              input {
                leaf board {
                  description
                    "Show statistics only from board (e.g\\. gu-0/5/0)";
                  type string {
                    pattern '(gu-0/(30|(1|2)[0-9]|[1-9])/0)' {
                      error-message "Invalid board name";
                    }
                  }
                }
              }
              output {
                leaf result {
                  type string;
                  mandatory true;
                }
              }
            }
            container log {
              status current {
                yexte:preliminary;
              }
              description
                "Log options";
              container control {
                status current {
                  yexte:preliminary;
                }
                description
                  "Control logs";
                leaf enable {
                  status current {
                    yexte:preliminary;
                  }
                  description
                    "Enable logging";
                  type empty;
                }
              }
            }
          }
          container first-session {
            status current {
              yexte:preliminary;
            }
            description
              "The first session commands";
            action show {
              description
                "Print information related to the first PFCP Session";
              input {
                leaf board {
                  description
                    "Show statistics only from board (e.g\\. gu-0/5/0)";
                  type string {
                    pattern '(gu-0/(30|(1|2)[0-9]|[1-9])/0)' {
                      error-message "Invalid board name";
                    }
                  }
                }
              }
              output {
                leaf result {
                  type string;
                  mandatory true;
                }
              }
            }
          }
          container session-queue {
            status current {
              yexte:preliminary;
            }
            description
              "Session-queue commands";
            action show {
              description
                "Print up session message queue";
              input {
                leaf board {
                  description
                    "Show statistics only from board (e.g\\. gu-0/5/0)";
                  type string {
                    pattern '(gu-0/(30|(1|2)[0-9]|[1-9])/0)' {
                      error-message "Invalid board name";
                    }
                  }
                }
              }
              output {
                leaf result {
                  type string;
                  mandatory true;
                }
              }
            }
          }
          container session-distribution {
            status current {
              yexte:preliminary;
            }
            description
              "Session-distrubution commands";
            action show {
              description
                "Print all up session distribution (CPUID|COUNT)";
              output {
                leaf result {
                  type string;
                  mandatory true;
                }
              }
            }
          }
          container sessions {
            status current {
              yexte:preliminary;
            }
            description
              "Sessions commands";
            action show {
              description
                "Print all up sessions (SEID|CPUID)";
              output {
                leaf result {
                  type string;
                  mandatory true;
                }
              }
            }
          }
          container pfcp {
            status current {
              yexte:preliminary;
            }
            description
              "PFCP commands";
            action show {
              description
                "Print information related to upf pfcp";
              output {
                leaf result {
                  type string;
                  mandatory true;
                }
              }
            }
          }
          container pfcp-detail {
            status current {
              yexte:preliminary;
            }
            description
              "PFCP-detail commands";
            action show {
              description
                "Print information related to upf pfcp in detail";
              output {
                leaf result {
                  type string;
                  mandatory true;
                }
              }
            }
          }
          container pfcp-error {
            status current {
              yexte:preliminary;
            }
            description
              "PFCP-error commands. These commands will show PFCP error messages.";
            container human-readable {
              status current {
                yexte:preliminary;
              }
              description
                "PFCP-error commands for human-readable.";
              action show {
                description
                  "Show a human readable part of failed PFCP messages.";
                output {
                  leaf result {
                    type string;
                    mandatory true;
                  }
                }
              }
            }
            container l3-hex {
              status current {
                yexte:preliminary;
              }
              description
                "PFCP-error commands for L3-hex.";
              action show {
                description
                  "Show failed PFCP messages in hex format, prepended with UDP and IP headers.";
                output {
                  leaf result {
                    type string;
                    mandatory true;
                  }
                }
              }
            }
            container li-interface {
              status current {
                yexte:preliminary;
              }
              yexte:user-group "epg-lawful-intercept-admin";
              description
                "PFCP-error commands over LI-interface. These commands will show PFCP error messages.";
              container human-readable {
                status current {
                  yexte:preliminary;
                }
                description
                  "PFCP-error commands for human-readable over li-interface.";
                action show {
                  yexte:user-group "epg-lawful-intercept-admin";
                  description
                    "Show a decoded part of failed PFCP messages over the LI interface.";
                  output {
                    leaf result {
                      type string;
                      mandatory true;
                    }
                  }
                }
              }
              container l3-hex {
                status current {
                  yexte:preliminary;
                }
                description
                  "PFCP-error commands for layer3-hex over li-interface.";
                action show {
                  yexte:user-group "epg-lawful-intercept-admin";
                  description
                    "Show failed PFCP messages in hex format over the LI interface, prepended with UDP and IP headers.";
                  output {
                    leaf result {
                      type string;
                      mandatory true;
                    }
                  }
                }
              }
            }
          }
        }
        container tracing {
          yexte:user-group "epg-lawful-intercept-admin";
          status current {
            yexte:preliminary;
          }
          description
            "Tracing";
          container session {
            yexte:user-group "epg-lawful-intercept-admin";
            status current {
              yexte:preliminary;
            }
            description
              "session commands";
            action show {
              description
                "Print information related to session";
              input {
                leaf board {
                  description
                    "Show statistics only from board (e.g\\. gu-0/5/0)";
                  type string {
                    pattern '(gu-0/(30|(1|2)[0-9]|[1-9])/0)' {
                      error-message "Invalid board name";
                    }
                  }
                }
              }
              output {
                leaf result {
                  type string;
                  mandatory true;
                }
              }
            }
            container log {
              yexte:user-group "epg-lawful-intercept-admin";
              status current {
                yexte:preliminary;
              }
              description
                "Log options";
              leaf enable {
                status current {
                  yexte:preliminary;
                }
                description
                  "Enable logging";
                type empty;
              }
            }
          }
          container manager {
            yexte:user-group "epg-lawful-intercept-admin";
            status current {
              yexte:preliminary;
            }
            description
              "manager commands";
            action show {
              description
                "Print information related to manager";
              input {
                leaf board {
                  description
                    "Show statistics only from board (e.g\\. gu-0/5/0)";
                  type string {
                    pattern '(gu-0/(30|(1|2)[0-9]|[1-9])/0)' {
                      error-message "Invalid board name";
                    }
                  }
                }
              }
              output {
                leaf result {
                  type string;
                  mandatory true;
                }
              }
            }
            container log {
              yexte:user-group "epg-lawful-intercept-admin";
              status current {
                yexte:preliminary;
              }
              description
                "Log options";
              leaf enable {
                status current {
                  yexte:preliminary;
                }
                description
                  "Enable logging";
                type empty;
              }
            }
          }
          container credential {
            yexte:user-group "epg-lawful-intercept-admin";
            status current {
              yexte:preliminary;
            }
            description
              "Credential controller/engine";
            action show {
              description
                "Print information related to the credential module";
              input {
                leaf board {
                  description
                    "Show statistics only from board (e.g\\. gu-0/5/0)";
                  type string {
                    pattern '(gu-0/(30|(1|2)[0-9]|[1-9])/0)' {
                      error-message "Invalid board name";
                    }
                  }
                }
              }
              output {
                leaf result {
                  type string;
                  mandatory true;
                }
              }
            }
            container log {
              status current {
                yexte:preliminary;
              }
              description
                "Log options";
              container control {
                status current {
                  yexte:preliminary;
                }
                description
                  "Credential controller logs";
                leaf enable {
                  status current {
                    yexte:preliminary;
                  }
                  description
                    "Enable logging";
                  type empty;
                }
              }
              container engine {
                status current {
                  yexte:preliminary;
                }
                description
                  "Credential engine logs";
                leaf enable {
                  status current {
                    yexte:preliminary;
                  }
                  description
                    "Enable logging";
                  type empty;
                }
              }
            }
          }
        }
      }
      container redis-coordinator {
        description
          "UP Redis Coordinator";
        status current {
          yexte:preliminary;
        }
        action status {
          description
            "Show UP Redis Coordinator status";
          output {
            leaf result {
              type string;
              mandatory true;
            }
          }
        }
        action statistics {
          description
            "Show UP Redis Coordinator statistics";
          output {
            leaf result {
              type string;
              mandatory true;
            }
          }
        }
        action cluster_active_hosts {
          description
            "Show UP Redis Coordinator set of active hosts in cluster";
          output {
            leaf result {
              type string;
              mandatory true;
            }
          }
        }
        action history {
          description
            "Show UP Redis Coordinator dump history records";
          output {
            leaf result {
              type string;
              mandatory true;
            }
          }
        }
      }
      container metrics-collector {
        description
          "UP Metrics Collector";
        status current {
          yexte:preliminary;
        }
        container show {
          description
            "Show Metrics Collector information";
          action index {
            description
              "Show Metrics Collector index";
            output {
              leaf result {
                type string;
                mandatory true;
              }
            }
          }
          action label-map {
            description
              "Show Metrics Collector label map";
            output {
              leaf result {
                type string;
                mandatory true;
              }
            }
          }
          action metrics {
            description
              "Show Metrics Collector metrics database";
            output {
              leaf result {
                type string;
                mandatory true;
              }
            }
          }
          action peers {
            description
              "Show Metrics Collector peers";
            output {
              leaf result {
                type string;
                mandatory true;
              }
            }
          }
          action time-info {
            description
              "Show Metrics Collector processing times";
            output {
              leaf result {
                type string;
                mandatory true;
              }
            }
          }
        }
        container set {
          description
            "Set different Metrics Collector parameters";
          action log-level {
            description
              "Set Metrics Collector Log Level";
            input {
              leaf level {
                type log-level;
              }
            }
            output {
              leaf result {
                type string;
                mandatory true;
              }
            }
          }
        }
      }
    }
    container packet-detection {
      description
        "Configuration for packet detection";
      uses applist;
      uses filterlist;
      uses packet-detection-dns-monitoring;
      leaf escape-character-conversion {
        description
          "Sets the escape character conversion feature on PISC";
        type empty;
      }
      leaf heuristics-package-activation {
        description
          "Heuristics package activation";
        type string {
          pattern '[.0-9A-Za-z_-]*' {
            error-message "Must contain only letters, numbers, underscores or dashes";
          }
          length "1..63";
        }
      }
      action heuristics-package-install {
        yexte:user-group "ericsson-support,epg-admin";
        description
          "Install heuristics package for packet inspection";
        input {
          leaf package {
            description
              "Heuristics package";
            type string;
            mandatory true;
          }
        }
        output {
          leaf result {
            type string;
            mandatory true;
          }
        }
      }
      action heuristics-package-uninstall {
        yexte:user-group "ericsson-support,epg-admin";
        description
          "Uninstall heuristics package for packet inspection";
        input {
          leaf package {
            description
              "Heuristics package";
            type string;
            mandatory true;
          }
        }
        output {
          leaf result {
            type string;
            mandatory true;
          }
        }
      }
      action heuristics-package-information {
        description
          "Show heuristics package information for packet inspection";
        input {
          leaf package {
            description
              "Heuristics package";
            type string {
              pattern '[.0-9A-Za-z_-]*' {
                error-message "Must contain only letters, numbers, underscores or dashes";
              }
            }
            mandatory true;
          }
        }
        output {
          leaf result {
            type string;
            mandatory true;
          }
        }
      }
      container flows {
        description
          "PISC flows";
        action statistics {
          description
            "Show detailed PISC flow statistics";
          output {
            leaf result {
              type string;
              mandatory true;
            }
          }
        }
      }
      container performance {
        description
          "PISC performance";
        action statistics {
          description
            "show PISC performance counters";
          output {
            leaf result {
              type string;
              mandatory true;
            }
          }
        }
      }
    }
    container tcp-setup-deferred-charging {
      description
        "Configure TCP setup deferred charging";
      choice tcp-setup-deferred-charging-application-list {
        leaf applications-all {
          description
            "Enable for all applications";
          type empty;
        }
        leaf applications-none {
          description
            "Disable for all applications";
          type empty;
        }
      }
    }
    container forwarding-action {
      description
        "Configuration for forwarding actions";
      container content-enrichment {
        description
          "Configuration for content enrichment";
        uses enrichment;
      }
    }
    leaf tcp-mss-ipv4 {
      description
        "Maximum TCP segment size (MSS) for end user IPv4 packets. This attribute is overridden if tcpMssIpv4 is configured on network-instance or interface level. This value is applied if TCP MSS feature is active";
      type uint16 {
        range "536..2860" {
          error-message "Invalid value for attribute. 'tcp-mss-ipv4'. Valid values are in range:[536,2860] bytes.";
        }
      }
    }
    leaf tcp-mss-ipv6 {
      description
        "Maximum TCP segment size (MSS) for end user IPv6 packets. This attribute is overridden if tcpMssIpv6 is configured on network-instance or interface level. This value is applied if TCP MSS feature is active.";
      type uint16 {
        range "1220..2840" {
          error-message "Invalid value for attribute 'tcp-mss-ipv6'. Valid values are in range:[1220,2840] bytes.";
        }
      }
    }
    container feature {
      status current {
        yexte:preliminary;
      }
      description
        "Control the UP Function Features";
      leaf no-empu {
        status current {
          yexte:preliminary;
        }
        description
          "If enabled, disables sending of End Marker packets by the UP function";
        type empty;
      }
      leaf ip-dl-ingress-optimization {
        status current {
          yexte:preliminary;
        }
        description
          "Enable IP downlink ingress optimization for Gi/SGi/N6";
        type empty;
      }
    }
    action statistics {
      description
        "Show UPF statistics";
      output {
        leaf result {
          type string;
          mandatory true;
        }
      }
    }
    action resilience {
      description
        "Show UPF resilience status";
      output {
        leaf result {
          type string;
          mandatory true;
        }
      }
    }
    container feature-activation {
      description
        "Feature activation";
      leaf network-address-translation {
        status current {
          yexte:preliminary;
        }
        description
          "Carrier-Grade NAT for user plane";
        type empty;
      }
      leaf event-based-monitoring {
        description
          "Activate event based monitoring for user plane";
        type empty;
        must 'not(../event-data-records)' {
          error-message "'event-based-monitoring' and 'event-data-records' cannot be configured at the same time.";
        }
      }
      leaf event-data-records {
        description
          "Activate event data records for user plane";
        type empty;
        must 'not(../event-based-monitoring)' {
          error-message "'event-based-monitoring' and 'event-data-records' cannot be configured at the same time.";
        }
        status current {
          yexte:preliminary;
        }
      }
      leaf abr-shaping {
        description
          "Enable ABR Shaping feature";
        type empty;
      }
      leaf http-last-request-classification {
        description
          "Disable pipeline";
        type empty;
      }
      leaf tcp-mss {
        description
          "Enable TCP-mss feature";
        type empty;
      }
      leaf tcp-setup-deferred-charging {
        description
          "TCP setup deferred charging activation.";
        type empty;
      }
      leaf packet-inspection {
        description
          "Enables PISC";
        type empty;
      }
      leaf service-chaining {
        status current {
          yexte:preliminary;
        }
        description
          "Activate service chaining";
        type empty;
      }
      leaf destination-nat {
        description
          "Activates user plane destination IP redirection";
        type empty;
      }
      leaf remove-rtx-dupack-volume {
        description
          "Activates removal of volume in traffic that matched with TCP retransmission or DUP ACK rules";
        type empty;
      }
    }
    container usage-reporting {
      status current {
        yexte:preliminary;
      }
      container apply {
        description
          "Apply reporting parameters";
        status current {
          yexte:preliminary;
        }
        leaf stop-of-traffic-time {
          description
            "Stop Of Traffic Time, given as decimal uint32";
          type uint32 {
            range "1..600" {
              error-message "Invalid value for attribute 'stop-of-traffic-time'. Valid values are in range:[1,600]";
            }
          }
        }
      }
    }
    container network-address-translation {
      status current {
        yexte:preliminary;
      }

      grouping range-group {
        status current {
          yexte:preliminary;
        }
        leaf ipv4-base {
          status current {
            yexte:preliminary;
          }
          type inet:ipv4-address;
          mandatory true;
          description
            "Starting ip address";
        }
        leaf range {
          status current {
            yexte:preliminary;
          }
          type uint32;
          mandatory true;
          description
            "Length of the sequence of ip addresses in range";
        }
      }

      grouping nat-ip-pool-group {
        status current {
          yexte:preliminary;
        }
        leaf pool-name {
          status current {
            yexte:preliminary;
          }
          type string;
          mandatory true;
          description
            "Name of the nat pool";
        }
        list ipv4-base {
          status current {
            yexte:preliminary;
          }
          key "ipv4-base";
          uses range-group;
          ordered-by user;
          description
            "List of ranges defining the set of ip addresses of the pool";
          must 'sum(../ipv4-base/range/text()) >= 2048' {
            error-message "Number of IPs must be either equal to or higher than 2048";
          }
        }
      }
      list nat-ip-pool {
        status current {
          yexte:preliminary;
        }
        key "pool-name";
        uses nat-ip-pool-group;
        description
          "List of pools for nat";
      }
      leaf port-chunk-size {
        status current {
          yexte:preliminary;
        }
        type uint16 {
          range "8|16|32|64|128|256|512" {
            error-message
              "Invalid value for attribute 'port-chunk-size'.
               Valid values are :[8|16|32|64|128|256|512]";
          }
        }
        default "32";
        description
          "The number of ports assigned at once";
      }
      leaf max-chunks-session {
        status current {
          yexte:preliminary;
        }
        type uint16 {
          range "1..100" {
            error-message
              "Invalid value for attribute 'max-chunks-session'.
               Valid values are :[1..100]";
          }
        }
        default "10";
        description
          "The maximun number of chunks assigned to one user";
      }
      leaf max-udp-ports-session {
        status current {
          yexte:preliminary;
        }
        type uint16;
        default "320";
        must 'current() <= ../max-chunks-session * ../port-chunk-size' {
          error-message "max-udp-ports-session must be either equal to or less than max-chunks-session*port-chunk-size";
        }
        description
          "The maximun number of udp ports used by user";
      }
      leaf max-tcp-ports-session {
        status current {
          yexte:preliminary;
        }
        type uint16;
        default "320";
        must 'current() <= ../max-chunks-session * ../port-chunk-size' {
          error-message "max-tcp-ports-session must be either equal to or less than max-chunks-session*port-chunk-size";
        }
        description
          "The maximun number of tcp ports used by user";
      }
      leaf well-known-ports-disabled {
        status current {
          yexte:preliminary;
        }
        type boolean;
        default "true";
        description
          "Ports from 0 to 1023 will not be used";
      }
    }
    container reporting {
      container event-reporting {
        container edr-settings {
          status current {
            yexte:preliminary;
          }
          uses edr-data-file;
        }
        list profile {
          description
            "Event reporting profile";
          key "name";
          max-elements 1;
          leaf name {
            description
              "Event reporting profile id";
            type string {
              pattern '[0-9A-Za-z]+' {
                error-message "'profile' name must contain only letters and/or numbers.";
              }
            }
            mandatory true;
          }
          leaf reporting-interface {
            description
              "Event reporting interface type";
            mandatory true;
            type enumeration {
              enum ebm {
                description
                  "Event reporting via EBM interface to external EBM server";
              }
              enum edr {
                description
                  "Event reporting via an Event-Data Record (EDR) file, in CSV format";
              }
            }
          }
          list event {
            description
              "Event";
            key "name";
            min-elements 1;
            must "((../reporting-interface = 'ebm') and (name='service-usage')) or ((../reporting-interface = 'edr') and (name='http' or name='tls' or name='tcp' or name='udp'))" {
              error-message "Invalid 'event' for the configured 'reporting-interface'. Valid events for 'ebm': ('service-usage'). Valid events for 'edr' ('http', 'tls', 'tcp', 'udp').";
            }
            leaf name {
              description
                "Event name";
              type enumeration {
                enum service-usage {
                  description
                    "UPF Service Usage event associated to service classification per Sx session";
                }
                enum http {
                  description
                    "UPF Reporting per HTTP transaction";
                }
                enum tls {
                  description
                    "UPF Reporting per TLS transaction";
                }
                enum tcp {
                  description
                    "UPF Reporting per 5-tuple for TCP traffic";
                }
                enum udp {
                  description
                    "UPF Reporting per 5-tuple for UDP traffic";
                }
              }
              mandatory true;
            }
            leaf trigger {
              type enumeration {
                enum CLOSE {
                  description
                    "trigger CLOSE";
                }
              }
              default "CLOSE";
            }
            leaf parameter-list {
              when "(../../reporting-interface = 'ebm')";
              description
                "Selected parameter list for extended parameters";
              type leafref {
                path "/epg/user-plane/reporting/event-reporting/profile/parameter-list/name";
              }
            }
            leaf period {
              when "(../../reporting-interface = 'ebm')";
              description
                "Event reporting period in minutes";
              type uint8 {
                range "5|15|30|60" {
                  error-message "Invalid value for attribute 'period'. Valid values are :[5,15,30,60]";
                }
              }
              default "5";
            }
          }
          list parameter-list {
            when "../reporting-interface = 'ebm'";
            description
              "Parameter list";
            key "name";
            leaf name {
              description
                "Parameter list ID";
              type string;
              mandatory true;
            }
            leaf activity-time {
              description
                "Flag to include in report info regarding activity-time";
              type empty;
            }
            leaf service-chain-id {
              description
                "Flag to include in report info regarding uplink and downlink service chain id";
              type empty;
            }
            leaf service-throughput {
              description
                "Flag to include in report info regarding service-throughput";
              type empty;
            }
            leaf tcp-irtt-user {
              description
                "Flag to include in report the iRTT measured during 3-way TCP handshake for user side";
              type empty;
            }
            leaf tcp-irtt-server {
              description
                "Flag to include in report the iRTT measured during 3-way TCP handshake for server side";
              type empty;
            }
            leaf tcp-segment {
              description
                "Flag to include in report info regarding tcp-segment";
              type empty;
            }
            leaf tcp-segment-rtx {
              description
                "Flag to include in report info regarding tcp-segment retransmissions";
              type empty;
            }
            leaf tcp-flow {
              description
                "Flag to include in report info regarding tcp-flows";
              type empty;
            }
          }
        }
        action statistics {
          description
            "Show UPF EBM statistics";
          output {
            leaf result {
              type string;
              mandatory true;
            }
          }
        }
      }

      grouping priority_field {
        leaf priority {
          type uint16 {
            range "1..512" {
              error-message "Invalid value for attribute. Valid values are in range:[1,512]";
            }
          }
        }
      }

      grouping edr-data-file {
        leaf delimiter {
          description
            "Delimiter between the fields in the EDR file";
          type enumeration {
            enum comma {
              description
                "Comma as delimiter";
            }
            enum pipe {
              description
                "pipe as delimiter";
            }
            enum tab {
              description
                "tab as delimiter";
            }
            enum exclam {
              description
                "! as delimiter";
            }
            enum numsign {
              description
                "# as delimiter";
            }
            enum dollar {
              description
                "$ as delimiter";
            }
            enum asterisk {
              description
                "* as delimiter";
            }
            enum plus {
              description
                "+ as delimiter";
            }
            enum greater {
              description
                "> as delimiter";
            }
            enum at {
              description
                "@ as delimiter";
            }
            enum tilde {
              description
                "~  as delimiter";
            }
          }
          default "comma";
        }
        leaf maximum-size {
          description
            "Maximum size of charging data file";
          type uint32 {
            range "1024..102400" {
              error-message "Invalid value for attribute 'maximum-size'. Valid values are in range:[1024,102400]";
            }
          }
          default "20480";
        }
        leaf maximum-age {
          description
            "Maximum age of charging data file";
          type uint16 {
            range "5..1440" {
              error-message "Invalid value for attribute 'maximum-age'. Valid values are in range:[5,1440]";
            }
          }
          default "120";
        }
        leaf compression {
          description
            "Compress all EDR data files";
          type empty;
        }
        container edr-structure {
          status current {
            yexte:preliminary;
          }
          description
            "Set EDR fields priority";

          container radius-nas-id {
            description
              "Subscriber Radius NAS Identifier information.";
            uses priority_field;
          }
          container start-time {
            description
              "Time and date for the start of the transaction.";
            leaf priority {
              type priority_type;
              default "507";
            }
            leaf format {
              description
                "START_TIME format";
              type enumeration {
                enum iso112 {
                  description
                    "YYYYMMDDHHMMSS";
                }
                enum canonical {
                  description
                    "MM/DD/YYYY-HH:MM:SS";
                }
              }
              default "iso112";
            }
            leaf time-zone {
              description
                "START_TIME time-zone";
              type enumeration {
                enum local {
                  description
                    "Local time";
                }
                enum UTC {
                  description
                    "UTC time";
                }
              }
              default "UTC";
            }
          }
          container duration {
            description
              "Duration in seconds from START_TIME to the end of the event.";
            leaf unit {
              description
                "DURATION unit";
              type enumeration {
                enum milliseconds {
                  description
                    "milliseconds";
                }
                enum seconds {
                  description
                    "seconds";
                }
              }
              default "seconds";
            }
            leaf priority {
              type priority_type;
              default "508";
            }
          }
          container msisdn {
            description
              "Subscriber MSISDN.";
            uses priority_field;
          }
          container imsi {
            description
              "Subscriber IMSI.";
            uses priority_field;
          }
          container imeisv {
            description
              "Subscriber IMEISV.";
            uses priority_field;
          }
          container rat-type {
            description
              "Subscriber RAT type.";
            uses priority_field;
          }
          container pgwc-ip {
            description
              "IP address of Control Plane function.";
            uses priority_field;
          }
          container uli {
            description
              "Subscriber Uniform Location Information";
            uses priority_field;
          }
          container reserved {
            description
              "Column with blank values.";
            leaf-list priority {
              max-elements 8;
              type priority_type;
            }
          }
          container app-id {
            description
              "If available, application-id where the packets were classified.";
            uses priority_field;
          }
          container ip-event-volume {
            description
              "Volume for the event, including L3, L4 and L7 headers. It can be downlink or uplink (configurable, both can be added).";
            container uplink {
              container bytes {
                uses priority_field;
              }
              container packets {
                uses priority_field;
              }
            }
            container downlink {
              container bytes {
                uses priority_field;
              }
              container packets {
                uses priority_field;
              }
            }
          }
          container transaction-volume {
            description
              "Volume of the L7 transaction (if any), excluding all headers. Only for HTTP events. It can be downlink or uplink (configurable, both can be added).";
            container uplink {
              container bytes {
                uses priority_field;
              }
              container packets {
                uses priority_field;
              }
            }
            container downlink {
              container bytes {
                uses priority_field;
              }
              container packets {
                uses priority_field;
              }
            }
          }
          container subscriber-ip {
            description
              "Subscriber IP address, in IPv4 or IPv6 format.";
            leaf priority {
              type priority_type;
              default "508";
            }
          }
          container subscriber-port {
            description
              "Subscriber port number.";
            leaf priority {
              type priority_type;
              default "509";
            }
          }
          container server-ip {
            description
              "Subscriber IP address, in IPv4 or IPv6 format.";
            leaf priority {
              type priority_type;
              default "510";
            }
          }
          container server-port {
            description
              "Server port number.";
            leaf priority {
              type priority_type;
              default "511";
            }
          }
          container protocol-id {
            description
              "The protocol, as obtained in DPI analysis.";
            leaf priority {
              type priority_type;
              default "512";
            }
          }
          container sni {
            description
              "Server Name Identification extracted from TLS Client Hello message.";
            uses priority_field;
          }
          container http-host {
            description
              "Host information included in HTTP Request message.";
            uses priority_field;
          }
          container http-uri {
            description
              "URI information included in HTTP Request message.";
            uses priority_field;
          }
          container http-referer {
            description
              "URI referer information included in HTTP Request message.";
            uses priority_field;
          }
          container http-user-agent {
            description
              "HTTP User Agent information included in HTTP Request message.";
            uses priority_field;
          }
          container http-request-method {
            description
              "HTTP Method information included in HTTP Request message.";
            uses priority_field;
          }
          container http-response-code {
            description
              "HTTP Response Code included in HTTP Response message.";
            uses priority_field;
          }
          container http-content-type {
            description
              "HTTP Content Type included in HTTP Request PUT and POST method messages, or the one included in HTTP Response messages for method GET.";
            uses priority_field;
          }
          container http-content-length {
            description
              "HTTP Content Length included in HTTP Request PUT and POST method messages or the one included in HTTP Response messages for method GET.";
            uses priority_field;
          }
        }
      }
    }

    grouping abr-shaping-profile-user-plane-type {
      leaf profile-name {
        description
          "Profile name";
        type common-string-id;
        mandatory true;
      }
      list service {
        min-elements 1;
        max-elements 32;
        key "service-name";
        leaf service-name {
          description
            "Service name";
          type common-string-id;
        }
        leaf shaping-bitrate {
          description
            "ABR Shaping bitrate expressed in kbps";
          type uint32;
        }
      }
    }
    container abr-shaping {
      list profile {
        max-elements 64;
        key "profile-name";
        uses abr-shaping-profile-user-plane-type;
      }
      action statistics {
        description
          "Show ABR Shaping statistics";
        input {
          leaf network-instance {
            description
              "Network Instance";
            type string {
              pattern '[.0-9A-Za-z_-]*' {
                error-message "Must contain only letters, numbers, underscores or dashes";
              }
              length "1..255";
            }
          }
        }
        output {
          leaf result {
            type string;
            mandatory true;
          }
        }
      }
    }
    container predefined-pdr {
      leaf absolute-precedence {
        description
          "The precedence of the predefined PDRs is evaluated among all the active PDRs of the PFCP session";
        type empty;
      }
      list pdr {
        key "pdr-id";
        leaf pdr-id {
          description
            "Predefined pdr identifier";
          type uint16 {
            range "1..65535" {
              error-message "Invalid value for attribute 'predefined-pdr name'. Valid values are in range:[1,65535]";
            }
          }
        }
        leaf precedence {
          description
            "precedence value";
          type uint32;
          mandatory true;
        }
        leaf application {
          description
            "application name";
          type leafref {
            path "/epg/user-plane/packet-detection/application-list/application/name";
          }
          mandatory true;
        }
        leaf-list urr {
          max-elements 16;
          description
            "urr-id";
          type uint32 {
            range "0..2147483647" {
              error-message "Invalid value for attribute 'predefined-pdr urr'. Valid values are in range:[0,2147483647]";
            }
          }
        }
      }
    }
    container predefined-rule {
      list rule {
        key "rule-name";
        leaf rule-name {
          description
            "Rule name";
          type common-string-id;
        }
        choice predefined-rule-choice {
          leaf abr-shaping-profile {
            description
              "ABR Shaping profile name";
            type leafref {
              path "/epg/user-plane/abr-shaping/profile/profile-name";
            }
          }
          leaf-list predefined-pdr {
            description
              "Predefined PDR name";
            type leafref {
              path "/epg/user-plane/predefined-pdr/pdr/pdr-id";
            }
          }
        }
        must 'abr-shaping-profile or predefined-pdr' {
          error-message "A predefined rule cannot be empty";
        }
      }
    }
    container acls {
      description
        "This is a top-level container for Access Control Lists.
         It can have one or more acl nodes.";
      uses acls;
    }
    container flow-management {
      description
        "Flow settings";
      uses flow-management;
    }
  }

  grouping enrichment {
    list rule {
      max-elements 512;
      key "name";
      uses sid-content-enrichment;
    }
  }

  grouping sid-content-enrichment {
    leaf name {
      description
        "Rule name";
      type string {
        pattern '[0-9A-Za-z][0-9A-Za-z_-]*' {
          error-message "Must be a string beginning with a number or letter and consisting of letters, numbers, dashes and underscores.";
        }
        length "1..63";
      }
    }
    container http {
      description
        "HTTP Content enrichment rule";
      uses http-insert-group;
      uses http-invalidate-group;
    }
    container ssl-tls {
      description
        "SSL-TLS Content enrichment rule";
      uses tls-insert-group;
      uses tls-invalidate-group;
    }
  }

  grouping item {
    leaf name {
      description
        "Item name";
      type string {
        pattern '[0-9A-Za-z][0-9A-Za-z_-]*' {
          error-message "Must be a string beginning with a number or letter and consisting of letters, numbers, dashes and underscores.";
        }
        length "1..63";
      }
    }
    leaf key {
      description
        "Item keyword to insert";
      type string {
        pattern '[.0-9A-Za-z_-]*' {
          error-message "Must contain only letters, numbers, underscores or dashes";
        }
        length "1..256";
      }
    }
    uses parameter;
    uses separator {
      refine "separator" {
        description
          "Separator character to insert between key and parameter in an item";
        default "=";
      }
    }
  }

  grouping http-insert-group {
    container insert {
      description
        "Insert content";
      list extended-header {
        description
          "Content header to insert";
        max-elements 20;
        must '/epg/user-plane/forwarding-action/content-enrichment/rule[name=current()/../../../name]/http/insert/extended-header[name=current()/name]/item' {
          error-message "item is mandatory";
        }
        key "name";
        uses extended-header-name;
        uses header-encryption;
        uses encrypt {
          refine "encrypt" {
            must "not ((text()='rc4-md5') and (not(../rc4-md5-encryption/pre-shared-key)))" {
              error-message "pre-shared-key must be defined for using RC4-MD5 algorithm";
              tailf:dependency "/epg/user-plane/forwarding-action/content-enrichment/rule/http/insert/extended-header/item/encrypt";
            }
            must "not ((text()='rc4') and (not(../rc4-encryption/pre-shared-key-clear)))" {
              error-message "pre-shared-key-clear must be defined for using RC4 algorithm";
              tailf:dependency "/epg/user-plane/forwarding-action/content-enrichment/rule/http/insert/extended-header/item/encrypt";
            }
          }
        }
        uses separator {
          refine "separator" {
            description
              "Separator character to insert between items";
            default " ";
          }
        }
        list item {
          description
            "Content item to insert";
          max-elements 8;
          key "name";
          uses item;
          uses encrypt {
            refine "encrypt" {
              must "not ((text()='rc4-md5') and (not(../../rc4-md5-encryption/pre-shared-key)))" {
                error-message "pre-shared-key must be defined for using RC4-MD5 algorithm";
                tailf:dependency "/epg/user-plane/forwarding-action/content-enrichment/rule/http/insert/extended-header/item/encrypt";
              }
              must "not ((text()='rc4') and (not(../../rc4-encryption/pre-shared-key-clear)))" {
                error-message "pre-shared-key-clear must be defined for using RC4 algorithm";
                tailf:dependency "/epg/user-plane/forwarding-action/content-enrichment/rule/http/insert/extended-header/item/encrypt";
              }
            }
          }
          list item {
            description
              "Content sub-item to insert";
            max-elements 8;
            must 'not (../../item[name=current()/name/../name]/parameter)' {
              error-message "incompatible with 'parameter'";
            }
            must 'not (../../item[name=current()/name/../name]/key)' {
              error-message "Incompatible with 'key'";
            }
            key "name";
            uses item {
              refine "parameter" {
                description
                  "Sub-item parameter to insert";
              }
            }
          }
        }
      }
    }
  }

  grouping parameter {
    leaf parameter {
      description
        "Item parameter to insert";
      type string {
        length "0..255";
      }
    }
  }

  grouping separator {
    leaf separator {
      type string {
        pattern '[/?+*.0-9A-Za-z @_~!#:>=-]*' {
          error-message "Must contain only letters, numbers and the following symbols:!, #, $, ,*, +, -, ., /, :, >, ?, @, ~, _, = ";
        }
        length "0..63";
      }
    }
  }

  grouping http-invalidate-group {
    container invalidate {
      description
        "Invalidate content";
      list extended-header {
        description
          "Extended header to invalidate";
        max-elements 20;
        key "name";
        uses extended-header-name;
      }
    }
  }

  grouping extended-header-name {
    leaf name {
      description
        "Header name";
      type string {
        pattern '[.0-9A-Za-z_-]*' {
          error-message "Must contain only letters, numbers, underscores or dashes";
        }
        length "1..63";
      }
    }
  }

  grouping tls-insert-group {
    container insert {
      description
        "Insert content";
      presence "insert need presence";
      list extension-number {
        description
          "The number of the extension to insert";
        key "name";
        uses extension-number-name;
        list item {
          description
            "Any type-length-value to insert into the ssl-tls Client Hello";
          max-elements 20;
          key "name";
          uses tls-item;
        }
        max-elements 1;
      }
    }
  }

  grouping tls-item {
    leaf name {
      description
        "Id of this item";
      type string {
        pattern '[A-Za-z0-9][_0-9A-Za-z-]{0,62}' {
          error-message "ERROR: Invalid value for item name. Valid values are strings in a specified format. Type: name? for more information on the format to use.";
        }
      }
    }
    uses parameter;
    leaf type {
      description
        "The number of the subextension to insert";
      type uint8 {
        range "0..255" {
          error-message "Invalid value for attribute 'type'. Valid values are in range:[0,255]";
        }
      }
      mandatory true;
    }
    leaf priority {
      description
        "Priority specifying order of the items to insert\\. A value from 1 to 999999, where a lower value takes precedence.";
      type string {
        pattern '[1-9][0-9]*' {
          error-message "String must match: ^[1-9][0-9]*$'";
        }
        length "1..6";
      }
      default "999999";
    }
    leaf format {
      description
        "The format of the subextension";
      type enumeration {
        enum string {
          description
            "string encoding of the parameter";
        }
        enum decimal-binary8 {
          description
            "decimal digit converted into 8-octet encoding of the parameter";
        }
        enum ip-hex {
          description
            "textual representation of OPaddress";
        }
        enum ip-binary {
          description
            "textual representation of IPv4 or IPv6 encoding of the parameter";
        }
        enum hex-binary {
          description
            "hexadecimal digits encoding for parameter";
        }
      }
      mandatory true;
      must 'not(../parameter = "$ue-ip" and (../format != "ip-hex" and ../format != "ip-binary"))' {
        error-message "$ue-ip parameter format must be ip-hex or ip-binary";
      }
      must 'not(../parameter = "$timestamp" and (../format != "string" and ../format != "decimal-binary8"))' {
        error-message "$timestamp parameter format must be string or decimal-binary8";
      }
    }
    uses rc4-md5-encryption-tls-group {
      refine "rc4-md5-encryption" {
        must '(../format = "string" or ../format = "ip-hex")' {
          error-message "Encryption is only allow for string and ip-hex format";
        }
      }
    }
  }

  grouping tls-invalidate-group {
    container invalidate {
      description
        "Invalidate content";
      presence "invalidate need presence";
      list extension-number {
        description
          "extension number";
        max-elements 1;
        key "name";
        uses extension-number-name;
        leaf new-extension-number {
          description
            "The number of the replacement for the extension";
          type uint16 {
            range "0..65535" {
              error-message "Invalid value for attribute 'extension-number'. Valid values are in range:[0,65535]";
            }
          }
          mandatory true;
        }
        must 'name != new-extension-number' {
          error-message "Extension-number and new-extension-number must be different";
        }
      }
    }
  }

  grouping extension-number-name {
    leaf name {
      description
        "Extension number";
      type uint16 {
        range "0..65535" {
          error-message "Invalid value for attribute 'extension-number'. Valid values are in range:[0,65535]";
        }
      }
    }
  }

  grouping rc4-md5-encryption-tls-group {
    container rc4-md5-encryption {
      presence "rc4-md5-encryption need presence";
      leaf pre-shared-key {
        description
          "MD5 hashed key for RC4 encryption";
        type tailf:aes-cfb-128-encrypted-string {
          pattern '($[1-9]$(.|\n)*)|(($0$)?[.0-9A-Za-z_-]{1,255})' {
            error-message "Must contain only letters, numbers, dot, underscores or dashes. Up to 255 chars.";
          }
        }
        mandatory true;
      }
    }
  }

  grouping header-encryption {
    container rc4-md5-encryption {
      presence "rc4-md5-encryption need presence";
      leaf pre-shared-key {
        description
          "MD5 hashed key for RC4 encryption";
        type tailf:aes-cfb-128-encrypted-string {
          pattern '($[1-9]$(.|\n)*)|(($0$)?[.0-9A-Za-z_-]{1,255})' {
            error-message "Must contain only letters, numbers, dot, underscores or dashes. Up to 255 chars.";
          }
        }
        mandatory true;
      }
      uses encode-encryption-group;
    }
    container rc4-encryption {
      presence "rc4-encryption need presence";
      leaf pre-shared-key-clear {
        description
          "Plain text key for RC4 encryption";
        type tailf:aes-cfb-128-encrypted-string {
          pattern '($[1-9]$(.|\n)*)|(($0$)?[.0-9A-Za-z_-]{1,255})' {
            error-message "Must contain only letters, numbers, dot, underscores or dashes. Up to 255 chars.";
          }
        }
        mandatory true;
      }
      uses encode-encryption-group;
    }
  }

  grouping encode-encryption-group {
    choice encode_pre_shared_key_choice {
      leaf base64 {
        description
          "Apply base64 encoding scheme";
        type empty;
      }
      leaf base16 {
        description
          "Apply base16 encoding scheme";
        type empty;
      }
    }
  }

  grouping encrypt {
    leaf encrypt {
      description
        "Encrypt all the items contained under this item";
      type enumeration {
        enum rc4-md5 {
          description
            "Encrypt using RC4 algorithm with MD5.";
        }
        enum rc4 {
          description
            "Encrypt using RC4 algorithm without MD5.";
        }
      }
    }
  }

  grouping acls {
    description
      "This is a top level container for Access Control Lists.
       It can have one or more acl nodes.";
    list acl {
      key "name";
      description
        "An Access Control List (ACL) is an ordered list of
         Access Control Entries (ACE). Each ACE has a
         list of match criteria and a list of actions.
         Since there are several kinds of Access Control Lists
         implemented with different attributes for
         different vendors, this model accommodates customizing
         Access Control Lists for each kind and, for each vendor.";
      leaf name {
        type string {
          length "1..64";
        }
        description
          "The name of access list. A device MAY restrict the length
           and value of this name, possibly space and special
           characters are not allowed.";
      }
      leaf type {
        type acl-type;
        mandatory true;
        description
          "Type of access control list. Indicates the primary intended
           type of match criteria (e.g. IPv4, IPv6, mixed) used in the
           list instance.";
      }
      container aces {
        description
          "The aces container contains one or more ace nodes.";
        list ace {
          key "name";
          description
            "List of Access Control Entries (ACEs)";
          leaf name {
            type string {
              length "1..64";
            }
            description
              "A unique name identifying this Access Control
               Entry (ACE).";
          }
          container matches {
            description
              "The rules in this set determine what fields will be
               matched upon before any action is taken on them.
               The rules are selected based on the feature set
               defined by the server and the acl-type defined.
               If no matches are defined in a particular container,
               then any packet will match that container. If no
               matches are specified at all in an ACE, then any
               packet will match the ACE.";
            choice l3 {
              container ipv4 {
                when "derived-from-or-self(../../../../type, 'epg:ipv4-acl-type')";
                if-feature "match-on-ipv4";
                uses acl-ip-header-fields;
                uses acl-ipv4-header-fields;
                description
                  "Rule set that matches IPv4 headers.";
              }
              container ipv6 {
                when "derived-from-or-self(../../../../type, 'epg:ipv6-acl-type')";
                if-feature "match-on-ipv6";
                uses acl-ip-header-fields;
                uses acl-ipv6-header-fields;
                description
                  "Rule set that matches IPv6 headers.";
              }
              description
                "Choice of either ipv4 or ipv6 headers";
            }
            choice l4 {
              container tcp {
                if-feature "match-on-tcp";
                container source-port {
                  choice source-port {
                    case range-or-operator {
                      uses port-range-or-operator;
                      description
                        "Source port definition from range or
                         operator.";
                    }
                    description
                      "Choice of source port definition using
                       range/operator or a choice to support future
                       'case' statements, such as one enabling a
                       group of source ports to be referenced.";
                  }
                  description
                    "Source port definition.";
                  presence "set source-port value";
                }
                container destination-port {
                  status current {
                    yexte:preliminary;
                  }
                  choice destination-port {
                    case range-or-operator {
                      uses port-range-or-operator;
                      description
                        "Destination port definition from range or
                         operator.";
                    }
                    description
                      "Choice of destination port definition using
                       range/operator or a choice to support future
                       'case' statements, such as one enabling a
                       group of destination ports to be referenced.";
                  }
                  description
                    "Destination port definition.";
                  presence "set destination-port value";
                }
                description
                  "Rule set that matches TCP headers.";
              }
              container udp {
                if-feature "match-on-udp";
                container source-port {
                  status current {
                    yexte:preliminary;
                  }
                  choice source-port {
                    case range-or-operator {
                      uses port-range-or-operator;
                      description
                        "Source port definition from range or
                         operator.";
                    }
                    description
                      "Choice of source port definition using
                       range/operator or a choice to support future
                       'case' statements, such as one enabling a
                       group of source ports to be referenced.";
                  }
                  description
                    "Source port definition.";
                  presence "set source-port value";
                }
                container destination-port {
                  status current {
                    yexte:preliminary;
                  }
                  choice destination-port {
                    case range-or-operator {
                      uses port-range-or-operator;
                      description
                        "Destination port definition from range or
                         operator.";
                    }
                    description
                      "Choice of destination port definition using
                       range/operator or a choice to support future
                       'case' statements, such as one enabling a
                       group of destination ports to be referenced.";
                  }
                  description
                    "Destination port definition.";
                  presence "set destination-port value";
                }
                description
                  "Rule set that matches UDP headers.";
              }
              description
                "Choice of TCP, UDP headers.";
            }
          }
          container actions {
            description
              "Definitions of action for this ace entry";
            leaf forwarding {
              type identityref {
                base forwarding-action;
              }
              mandatory true;
              description
                "Specifies the forwarding action per ace entry";
            }
          }
        }
      }
    }
    container attachment-points {
      description
        "Enclosing container for the list of
         attachment-points on which ACLs are set";

      grouping routing-instance-acl {
        description
          "Grouping for per-routing-instance ingress ACL data";
        container acl-sets {
          description
            "Enclosing container the list of ingress ACLs on the
             routing-instance";
          leaf acl-set {
            description
              "ingress ACLs on the routing-instance";
            type leafref {
              path "/epg/user-plane/acls/acl/name";
            }
          }
        }
      }
      action show-statistics {
        description
          "statistics for routing-instance  ";
        input {
          leaf board {
            description
              "Run command on board (e.g\\. gu-0/5/1)";
            type string {
              pattern '(gu-0/(30|(1|2)[0-9]|[1-9])/1)' {
                error-message "Invalid board name";
              }
            }
            mandatory false;
          }
        }
        output {
          leaf result {
            type string;
            mandatory true;
          }
        }
      }
      action clear-statistics {
        description
          "clear for routing-instance  ";
        input {
          leaf board {
            description
              "Run command on board (e.g\\. gu-0/5/1)";
            type string {
              pattern '(gu-0/(30|(1|2)[0-9]|[1-9])/1)' {
                error-message "Invalid board name";
              }
            }
            mandatory false;
          }
        }
        output {
          leaf result {
            type string;
            mandatory true;
          }
        }
      }
      list routing-instance {
        if-feature "routing-instance-attachment";
        key "routing-instance-name";
        description
          "List of routing-instances on which ACLs are set";
        leaf routing-instance-name {
          type epg:routing-instance-type;
          description
            "Reference to the routing-instance list key";
        }
        container ingress {
          uses routing-instance-acl;
          description
            "The ACLs applied to ingress routing-instance";
        }
        container egress {
          uses routing-instance-acl;
          description
            "The ACLs applied to egress routing-instance";
        }
      }
    }
  }

  grouping port-range-or-operator {
    description
      "Grouping for port definitions in the form of a
       choice statement.";
    choice port-range-or-operator {
      case range {
        leaf lower-port {
          type inet:port-number;
          must '. <= ../upper-port' {
            error-message
              "The lower-port must be less than or equal to
               upper-port.";
          }
          mandatory true;
          description
            "Lower boundry for a port.";
        }
        leaf upper-port {
          type inet:port-number;
          mandatory true;
          description
            "Upper boundry for port.";
        }
      }
      case operator {
        leaf operator {
          type operator;
          default "eq";
          description
            "Operator to be applied on the port below.";
        }
        leaf port {
          type inet:port-number;
          mandatory true;
          description
            "Port number along with operator on which to
             match.";
        }
      }
      description
        "Choice of specifying a port range or a single
         port along with an operator.";
    }
  }

  grouping acl-ip-header-fields {
    description
      "IP header fields common to ipv4 and ipv6";
    reference "RFC 791: Internet Protocol.";
    leaf protocol {
      type uint8;
      description
        "Internet Protocol number. Refers to the protocol of the
         payload. In IPv6, this field is known as 'next-header,
         and if extension headers are present, the protocol is
         present in the 'upper-layer' header.";
      reference
        "RFC 791: Internet Protocol,
         RFC 8200: Internet Protocol, Version 6 (IPv6) Specification.";
    }
  }

  grouping acl-ipv4-header-fields {
    description
      "Fields in IPv4 header.";
    choice destination-network {
      case destination-ipv4-network {
        leaf destination-ipv4-network {
          type inet:ipv4-prefix;
          description
            "Destination IPv4 address prefix.";
        }
      }
      description
        "Choice of specifying a destination IPv4 address or
         referring to a group of IPv4 destination addresses.";
    }
    choice source-network {
      case source-ipv4-network {
        leaf source-ipv4-network {
          type inet:ipv4-prefix;
          description
            "Source IPv4 address prefix.";
        }
      }
      description
        "Choice of specifying a source IPv4 address or
         referring to a group of IPv4 source addresses.";
    }
  }

  grouping acl-ipv6-header-fields {
    description
      "Fields in IPv6 header";
    choice destination-network {
      case destination-ipv6-network {
        leaf destination-ipv6-network {
          type inet:ipv6-prefix;
          description
            "Destination IPv6 address prefix.";
        }
      }
      description
        "Choice of specifying a destination IPv6 address
         or referring to a group of IPv6 destination
         addresses.";
    }
    choice source-network {
      case source-ipv6-network {
        leaf source-ipv6-network {
          type inet:ipv6-prefix;
          description
            "Source IPv6 address prefix.";
        }
      }
      description
        "Choice of specifying a source IPv6 address or
         referring to a group of IPv6 source addresses.";
    }
    reference
      "RFC 4291: IP Version 6 Addressing Architecture
       RFC 4007: IPv6 Scoped Address Architecture
       RFC 5952: A Recommendation for IPv6 Address Text
                 Representation";
  }

  identity forwarding-action {
    description
      "Base identity for actions in the forwarding category";
  }

  identity accept {
    base forwarding-action;
    description
      "Accept the packet";
  }

  identity drop {
    base forwarding-action;
    description
      "Drop packet without sending any ICMP error message";
  }

  identity acl-base {
    description
      "Base Access Control List type for all Access Control List type
       identifiers.";
  }

  identity ipv4-acl-type {
    base acl-base;
    if-feature "ipv4";
    description
      "An ACL that matches on fields from the IPv4 header
       (e.g. IPv4 destination address) and layer 4 headers (e.g. TCP
       destination port). An acl of type ipv4 does not contain
       matches on fields in the ethernet header or the IPv6 header.";
  }

  identity ipv6-acl-type {
    base acl-base;
    if-feature "ipv6";
    description
      "An ACL that matches on fields from the IPv6 header
       (e.g. IPv6 destination address) and layer 4 headers (e.g. TCP
       destination port). An acl of type ipv6 does not contain
       matches on fields in the ethernet header or the IPv4 header.";
  }

  identity mixed-ipv4-ipv6-acl-type {
    base ipv4-acl-type;
    base ipv6-acl-type;
    if-feature "mixed-ipv4-ipv6";
    description
      "ACL that contains a mix of entries
       that match on fields in IPv4 headers, and entries
       that match on fields in IPv6 headers. Matching on
       layer 4 header fields may also exist in the list.";
  }

  feature match-on-ipv4 {
    description
      "The device can support matching on IPv4 headers.";
  }

  feature match-on-ipv6 {
    description
      "The device can support matching on IPv6 headers.";
  }

  feature match-on-tcp {
    description
      "The device can support matching on TCP headers.";
  }

  feature match-on-udp {
    description
      "The device can support matching on UDP headers.";
  }

  feature ipv4 {
    if-feature "match-on-ipv4";
    description
      "Plain IPv4 ACL supported";
  }

  feature ipv6 {
    if-feature "match-on-ipv6";
    description
      "Plain IPv6 ACL supported";
  }

  feature mixed-ipv4-ipv6 {
    if-feature
      "match-on-ipv4
       and match-on-ipv6";
    description
      "IPv4 and IPv6 ACL combinations supported.";
  }

  feature routing-instance-attachment {
    description
      "ACLs are set on routing-instances.";
  }

  grouping sensitive-uri-like-string-value {
    leaf value {
      description
        "value to match";
      type string {
        length "1..255";
      }
    }
    leaf case-sensitive {
      description
        "Enables case sensitivity matching";
      type empty;
    }
  }

  grouping dns-group-unique-items {
    status current {
      yexte:preliminary;
    }
    list dns-query-name {
      key "value";
      description
        "DNS query value to match";
      uses sensitive-uri-like-string-value;
      max-elements 1;
    }
    list dns-query-name-not {
      key "value";
      description
        "DNS query value to NOT match";
      uses sensitive-uri-like-string-value;
      max-elements 10;
    }
  }

  grouping dns-group-multiple-items {
    status current {
      yexte:preliminary;
    }
    list dns-query-name {
      key "value";
      description
        "DNS query value to match";
      uses sensitive-uri-like-string-value;
    }
    list dns-query-name-not {
      key "value";
      description
        "DNS query value to NOT match";
      uses sensitive-uri-like-string-value;
    }
  }

  grouping http-group-unique-items {
    leaf http-1x-malformed {
      description
        "Http 1X packets do NOT verify RFCs syntax.";
      type empty;
      must '(not(../http-1x-wellformed))' {
        error-message "http-1x-wellformed and http-1x-malformed are incompatible";
      }
    }
    leaf http-1x-wellformed {
      description
        "Http 1X packets verify RFCs syntax.";
      type empty;
      must '(not(../http-1x-malformed))' {
        error-message "http-1x-wellformed and http-1x-malformed are incompatible";
      }
    }
    list http-uri {
      key "value";
      description
        "HTTP URI value to match";
      uses sensitive-uri-like-string-value;
      max-elements 1;
    }
    list http-uri-not {
      key "value";
      description
        "HTTP URI value to NOT match";
      uses sensitive-uri-like-string-value;
      max-elements 10;
    }
    list http-host {
      key "value";
      description
        "HTTP HOST value to match";
      uses sensitive-uri-like-string-value;
      max-elements 1;
    }
    list http-host-not {
      key "value";
      description
        "HTTP HOST value to NOT match";
      uses sensitive-uri-like-string-value;
      max-elements 10;
    }
    list http-user-agent {
      key "value";
      description
        "HTTP USER AGENT value to match";
      uses sensitive-uri-like-string-value;
      max-elements 1;
    }
    list http-user-agent-not {
      key "value";
      description
        "HTTP USER AGENT value to NOT match";
      uses sensitive-uri-like-string-value;
      max-elements 10;
    }
    list http-domain {
      key "value";
      description
        "HTTP DOMAIN value to match";
      uses sensitive-uri-like-string-value;
      max-elements 1;
    }
    list http-domain-not {
      key "value";
      description
        "HTTP DOMAIN value to NOT match";
      uses sensitive-uri-like-string-value;
      max-elements 10;
    }
    leaf-list http-operation {
      description
        "HTTP OPERATION value to match";
      type enumeration {
        enum CONNECT;
        enum DELETE;
        enum GET;
        enum HEAD;
        enum OPTIONS;
        enum POST;
        enum PUT;
        enum TRACE;
      }
      max-elements 1;
    }
    list http-content-type {
      key "value";
      description
        "HTTP Content-Type value to match";
      uses sensitive-uri-like-string-value;
      max-elements 1;
    }
    list http-content-type-not {
      key "value";
      description
        "HTTP Content-Type value to NOT match";
      uses sensitive-uri-like-string-value;
      max-elements 10;
    }
  }

  grouping http-group-multiple-items {
    leaf http-1x-malformed {
      description
        "Http 1X packets do NOT verify RFCs syntax.";
      type empty;
      must '(not(../http-1x-wellformed))' {
        error-message "http-1x-wellformed and http-1x-malformed are incompatible";
      }
    }
    leaf http-1x-wellformed {
      description
        "Http 1X packets verify RFCs syntax.";
      type empty;
      must '(not(../http-1x-malformed))' {
        error-message "http-1x-wellformed and http-1x-malformed are incompatible";
      }
    }
    list http-uri {
      key "value";
      description
        "HTTP URI value to match";
      uses sensitive-uri-like-string-value;
    }
    list http-uri-not {
      key "value";
      description
        "HTTP URI value to NOT match";
      uses sensitive-uri-like-string-value;
    }
    list http-host {
      key "value";
      description
        "HTTP HOST value to match";
      uses sensitive-uri-like-string-value;
    }
    list http-host-not {
      key "value";
      description
        "HTTP HOST value to NOT match";
      uses sensitive-uri-like-string-value;
    }
    list http-user-agent {
      key "value";
      description
        "HTTP USER AGENT value to match";
      uses sensitive-uri-like-string-value;
    }
    list http-user-agent-not {
      key "value";
      description
        "HTTP USER AGENT value to NOT match";
      uses sensitive-uri-like-string-value;
    }
    list http-domain {
      key "value";
      description
        "HTTP DOMAIN value to match";
      uses sensitive-uri-like-string-value;
    }
    list http-domain-not {
      key "value";
      description
        "HTTP DOMAIN value to NOT match";
      uses sensitive-uri-like-string-value;
    }
    leaf-list http-operation {
      description
        "HTTP OPERATION value to match";
      type enumeration {
        enum CONNECT;
        enum DELETE;
        enum GET;
        enum HEAD;
        enum OPTIONS;
        enum POST;
        enum PUT;
        enum TRACE;
      }
    }
    list http-content-type {
      key "value";
      description
        "HTTP Content-Type value to match";
      uses sensitive-uri-like-string-value;
    }
    list http-content-type-not {
      key "value";
      description
        "HTTP Content-Type value to NOT match";
      uses sensitive-uri-like-string-value;
    }
  }

  grouping tls-group-unique-items {
    list tls-sni {
      key "value";
      description
        "TLS SNI value to match";
      uses sensitive-uri-like-string-value;
      max-elements 1;
    }
    list tls-sni-not {
      key "value";
      description
        "TLS SNI value to NOT match";
      uses sensitive-uri-like-string-value;
      max-elements 10;
    }
  }

  grouping tls-group-multiple-items {
    list tls-sni {
      key "value";
      description
        "TLS SNI value to match";
      uses sensitive-uri-like-string-value;
    }
    list tls-sni-not {
      key "value";
      description
        "TLS SNI value to NOT match";
      uses sensitive-uri-like-string-value;
    }
  }

  grouping rtsp-group-multiple-items {
    list rtsp-uri {
      key "value";
      description
        "RTSP URI value to match";
      uses sensitive-uri-like-string-value;
    }
    list rtsp-uri-not {
      key "value";
      description
        "RTSP URI value to NOT match";
      uses sensitive-uri-like-string-value;
    }
  }

  grouping rtsp-group-unique-items {
    list rtsp-uri {
      key "value";
      description
        "RTSP URI value to match";
      uses sensitive-uri-like-string-value;
      max-elements 1;
    }
    list rtsp-uri-not {
      key "value";
      description
        "RTSP URI value to NOT match";
      uses sensitive-uri-like-string-value;
      max-elements 10;
    }
  }

  grouping matching-condition-group-for-and {
    leaf tethering {
      description
        "Match tethering detection traffic";
      type empty;
    }
    leaf-list tls-extension {
      description
        "Classification of traffic with TLS extension as configured value";
      type uint16 {
        range "0..65535" {
          error-message "Invalid value for attribute 'tls-extension'. Valid values are in range:[0,65535]";
        }
      }
      max-elements 1;
    }
    leaf-list ip-flow-ttl-uplink {
      description
        "Classification of traffic with TTL as configured value";
      type uint16 {
        range "1..255" {
          error-message "Invalid value for attribute 'ip-flow-ttl-uplink'. Valid values are in range:[1,255]";
        }
      }
      max-elements 1;
    }
    leaf-list ip-flow-ttl-uplink-not {
      description
        "Classification of traffic with TTL different as configured value";
      type uint16 {
        range "1..255" {
          error-message "Invalid value for attribute 'ip-flow-ttl-uplink-not'. Valid values are in range:[1,255]";
        }
      }
      max-elements 10;
    }
    leaf-list ip-flow-ttl-uplink-less-than {
      description
        "Match Uplink/Access packets with TTL lower than the specified value";
      type uint16 {
        range "2..255" {
          error-message "Invalid value for attribute 'ip-flow-ttl-uplinki-less-than'. Valid values are in range:[2,255]";
        }
      }
      max-elements 1;
    }
    leaf-list ip-flow-ttl-uplink-greater-than {
      description
        "Match Uplink/Access packets with TTL greater than the specified value";
      type int16 {
        range "0..253" {
          error-message "Invalid value for attribute 'ip-flow-ttl-uplink-greater-than'. Valid values are in range:[0,253]";
        }
      }
      max-elements 1;
    }
    leaf-list ip-packet-ttl-uplink-less-than {
      description
        "Match Uplink/Access packets with TTL lower than the specified value";
      type uint8 {
        range "2..255" {
          error-message "Invalid value for attribute 'ip-packet-ttl-uplink-less-than'. Valid values are in range:[2,255]";
        }
      }
      default "2";
      max-elements 1;
    }
    leaf tcp-signaling-setup {
      description
        "Match setup signaling traffic on TCP";
      must '(not(../tcp-signaling-teardown))' {
        error-message "Not compatible with TCP Signaling Teardown";
      }
      type empty;
    }
    leaf tcp-signaling-teardown {
      description
        "Match teardown signaling traffic on TCP";
      must '(not(../tcp-signaling-setup))' {
        error-message "Not compatible with TCP Signaling Setup";
      }
      type empty;
    }
    leaf fraud-risk-http {
      description
        "Match fraudulent HTTP traffic";
      type empty;
    }
    leaf fraud-risk-tls {
      description
        "Match fraudulent TLS traffic";
      type empty;
    }
    leaf-list ip-flow-network-address {
      description
        "IP Flow Network Address value to match";
      type eip-prefix-optional;
      max-elements 1;
    }
    leaf-list ip-flow-ue-address {
      description
        "IP Flow UE Address value to match";
      type eip-prefix-optional;
      max-elements 1;
    }
    leaf-list ip-flow-network-port {
      description
        "IP Flow Network Port value to match";
      type network-port-or-range;
      max-elements 1;
    }
    leaf-list ip-flow-network-port-tcp {
      description
        "IP Flow Network TCP Port value to match";
      type network-port-or-range;
      max-elements 1;
    }
    leaf-list ip-flow-network-port-udp {
      description
        "IP Flow Network UDP Port value to match";
      type network-port-or-range;
      max-elements 1;
    }
    leaf-list ip-flow-ue-port {
      description
        "IP Flow UE Port value to match";
      type network-port-or-range;
      max-elements 1;
    }
    leaf-list ip-flow-ue-port-tcp {
      description
        "IP Flow UE Port TCP value to match";
      type network-port-or-range;
      max-elements 1;
    }
    leaf-list ip-flow-ue-port-udp {
      description
        "IP Flow UE Port UDP value to match";
      type network-port-or-range;
      max-elements 1;
    }
    leaf-list ip-flow-protocol {
      description
        "IP Flow Protocol value to match";
      type enumeration {
        enum ah;
        enum egp;
        enum esp;
        enum gre;
        enum icmp;
        enum icmpv6;
        enum igmp;
        enum ipip;
        enum ospf;
        enum pim;
        enum rsvp;
        enum sctp;
        enum tcp;
        enum udp;
      }
      max-elements 1;
    }
    leaf-list ip-server-domain-name {
      description
        "IP Domain for DNS Query Name to match";
      must "(../ip-flow-protocol[text()='tcp']) or (../ip-flow-protocol[text()='udp']) or (not(../ip-flow-protocol))" {
        error-message "Only compatible with TCP or UDP protocols";
      }
      type common-domain-string-id;
      max-elements 1;
    }
    leaf-list heuristic-protocol {
      description
        "Heuristic protocol to match";
      type common-string-id;
      must
        "(not((text()='skype-serv-default') or (text()='skype-serv-file-transfer') or (text()='skype-serv-voip') or
         (text()='skype-serv-instant-messaging') or (text()='skype')))" {
        error-message "Protocol not supported: skype, skype-serv-[default | instant-messaging | file-transfer | voip]. Please, configure skype-new, skype-new-serv-[instant-messaging | file-transfer | voip] instead";
      }
      max-elements 1;
    }
    leaf-list icmp-answer {
      description
        "Classification of ICMP answer";
      must "(../ip-flow-protocol[text()='icmp']) and (../ip-flow-ttl-uplink or ../ip-flow-ttl-uplink-not or ../ip-flow-ttl-uplink-less-than or ../ip-flow-ttl-uplink-greater-than)" {
        error-message "Only configurable if a ttl-identification-condition (ip-flow-ttl-uplink, ip-flow-ttl-uplink-not, ip-flow-ttl-uplink-less-than, ip-flow-ttl-uplink-greater-than)  matching condition and ip-flow-protocol icmp are configured";
      }
      type enumeration {
        enum fail;
        enum success;
      }
      max-elements 1;
    }
    leaf-list icmpv6-answer {
      description
        "Classification of ICMPv6 answer";
      must "(../ip-flow-protocol[text()='icmpv6']) and (../ip-flow-ttl-uplink or ../ip-flow-ttl-uplink-not or ../ip-flow-ttl-uplink-less-than or ../ip-flow-ttl-uplink-greater-than)" {
        error-message "Only configurable if a ttl-identification-condition (ip-flow-ttl-uplink, ip-flow-ttl-uplink-not, ip-flow-ttl-uplink-less-than, ip-flow-ttl-uplink-greater-than) matching condition and ip-flow-protocol icmpv6 are configured";
      }
      type enumeration {
        enum fail;
        enum success;
      }
      max-elements 1;
    }
    uses http-group-unique-items;
    uses tls-group-unique-items;
    uses dns-group-unique-items;
    uses rtsp-group-unique-items;
  }

  grouping matching-condition-group-for-or {
    leaf tethering {
      description
        "Match tethering detection traffic";
      type empty;
    }
    leaf-list tls-extension {
      description
        "Classification of traffic with TLS extension as configured value";
      type uint16 {
        range "0..65535" {
          error-message "Invalid value for attribute 'tls-extension'. Valid values are in range:[0,65535]";
        }
      }
    }
    leaf-list ip-flow-ttl-uplink {
      description
        "Classification of traffic with TTL as configured value";
      type uint16 {
        range "1..255" {
          error-message "Invalid value for attribute 'ip-flow-ttl-uplink'. Valid values are in range:[1,255]";
        }
      }
    }
    leaf-list ip-flow-ttl-uplink-not {
      description
        "Classification of traffic with TTL different as configured value";
      type uint16 {
        range "1..255" {
          error-message "Invalid value for attribute 'ip-flow-ttl-uplink-not'. Valid values are in range:[1,255]";
        }
      }
    }
    leaf-list ip-flow-ttl-uplink-less-than {
      description
        "Match Uplink/Access packets with TTL lower than the specified value";
      type uint16 {
        range "2..255" {
          error-message "Invalid value for attribute 'ip-flow-ttl-uplinki-less-than'. Valid values are in range:[2,255]";
        }
      }
    }
    leaf-list ip-flow-ttl-uplink-greater-than {
      description
        "Match Uplink/Access packets with TTL greater than the specified value";
      type int16 {
        range "0..253" {
          error-message "Invalid value for attribute 'ip-flow-ttl-uplink-greater-than'. Valid values are in range:[0,253]";
        }
      }
    }
    leaf tcp-signaling-setup {
      description
        "Match setup signaling traffic on TCP";
      type empty;
    }
    leaf tcp-signaling-teardown {
      description
        "Match teardown signaling traffic on TCP";
      type empty;
    }
    leaf fraud-risk-http {
      description
        "Match fraudulent HTTP traffic";
      type empty;
    }
    leaf fraud-risk-tls {
      description
        "Match fraudulent TLS traffic";
      type empty;
    }
    leaf-list ip-packet-ttl-uplink-less-than {
      description
        "Match Uplink/Access packets with TTL lower than the specified value";
      type uint8 {
        range "2..255" {
          error-message "Invalid value for attribute 'ip-packet-ttl-uplink-less-than'. Valid values are in range:[2,255]";
        }
      }
      default "2";
    }
    leaf-list ip-flow-network-address {
      description
        "IP Flow Network Address value to match";
      type eip-prefix-optional;
    }
    leaf-list ip-flow-ue-address {
      description
        "IP Flow UE Address value to match";
      type eip-prefix-optional;
    }
    leaf-list ip-flow-network-port {
      description
        "IP Flow Network Port value to match";
      type network-port-or-range;
    }
    leaf-list ip-flow-network-port-tcp {
      description
        "IP Flow Network TCP Port value to match";
      type network-port-or-range;
    }
    leaf-list ip-flow-network-port-udp {
      description
        "IP Flow Network UDP Port value to match";
      type network-port-or-range;
    }
    leaf-list ip-flow-ue-port {
      description
        "IP Flow UE Port value to match";
      type network-port-or-range;
    }
    leaf-list ip-flow-ue-port-tcp {
      description
        "IP Flow UE Port TCP value to match";
      type network-port-or-range;
    }
    leaf-list ip-flow-ue-port-udp {
      description
        "IP Flow UE Port UDP value to match";
      type network-port-or-range;
    }
    leaf-list ip-flow-protocol {
      description
        "IP Flow Protocol value to match";
      type enumeration {
        enum ah;
        enum egp;
        enum esp;
        enum gre;
        enum icmp;
        enum icmpv6;
        enum igmp;
        enum ipip;
        enum ospf;
        enum pim;
        enum rsvp;
        enum sctp;
        enum tcp;
        enum udp;
      }
    }
    leaf-list ip-server-domain-name {
      description
        "IP Domain for DNS Query Name to match";
      type common-domain-string-id;
    }
    leaf-list heuristic-protocol {
      description
        "Heuristic protocol to match";
      type common-string-id;
      must
        "(not((text()='skype-serv-default') or (text()='skype-serv-file-transfer') or (text()='skype-serv-voip') or
         (text()='skype-serv-instant-messaging') or (text()='skype')))" {
        error-message "Protocol not supported: skype, skype-serv-[default | instant-messaging | file-transfer | voip]. Please, configure skype-new, skype-new-serv-[instant-messaging | file-transfer | voip] instead";
      }
    }
    uses http-group-multiple-items;
    uses tls-group-multiple-items;
    uses dns-group-multiple-items;
    uses rtsp-group-multiple-items;
  }

  grouping applist {
    container application-list {
      description
        "Configuration for packet inspection";
      action statistics {
        status current;
        description
          "Show detailed application list statistics";
        input {
          leaf appid {
            description
              "Application Identifier";
            type leafref {
              path "/epg/user-plane/packet-detection/application-list/application/name";
            }
          }
        }
        output {
          leaf result {
            type string;
            mandatory true;
          }
        }
      }
      list application {
        key "name";
        leaf name {
          description
            "Application identifier to be mapped with the pdr-pdi identifier";
          type common-string-id;
          mandatory true;
        }
        choice app-matching-conditions-start-menu {
          mandatory true;
          leaf default {
            description
              "Set as match-all conditioned application";
            type empty;
          }
          leaf tcp-retransmission {
            description
              "Match retransmitted traffic on TCP";
            type empty;
          }
          leaf tcp-duplicated-ack {
            description
              "Match duplicated ACKs on TCP";
            type empty;
          }
          leaf filter {
            description
              "Matching Condition Filter identifier to match";
            type leafref {
              path "../../../filter-list/filter/name";
            }
          }
          leaf tethering {
            description
              "Match tethering detection traffic";
            type empty;
          }
          leaf tethering-first-uplink-packet {
            description
              "Match the first uplink tethering detection traffic";
            type empty;
          }
          leaf-list tls-extension {
            description
              "Classification of traffic with TLS extension as configured value";
            type uint16 {
              range "0..65535" {
                error-message "Invalid value for attribute 'tls-extension'. Valid values are in range:[0,65535]";
              }
            }
            max-elements 1;
          }
          leaf-list ip-flow-ttl-uplink {
            description
              "Classification of traffic with TTL as configured value";
            type uint16 {
              range "1..255" {
                error-message "Invalid value for attribute 'ip-flow-ttl-uplink'. Valid values are in range:[1,255]";
              }
            }
            max-elements 1;
          }
          leaf-list ip-flow-ttl-uplink-not {
            description
              "Classification of traffic with TTL different as configured value";
            type uint16 {
              range "1..255" {
                error-message "Invalid value for attribute 'ip-flow-ttl-uplink-not'. Valid values are in range:[1,255]";
              }
            }
            max-elements 1;
          }
          leaf-list ip-flow-ttl-uplink-less-than {
            description
              "Match Uplink/Access packets with TTL lower than the specified value";
            type uint16 {
              range "2..255" {
                error-message "Invalid value for attribute 'ip-flow-ttl-uplinki-less-than'. Valid values are in range:[2,255]";
              }
            }
            max-elements 1;
          }
          leaf-list ip-flow-ttl-uplink-greater-than {
            description
              "Match Uplink/Access packets with TTL greater than the specified value";
            type int16 {
              range "0..253" {
                error-message "Invalid value for attribute 'ip-flow-ttl-uplink-greater-than'. Valid values are in range:[0,253]";
              }
            }
            max-elements 1;
          }
          leaf tcp-signaling-setup {
            description
              "Match setup signaling traffic on TCP";
            type empty;
          }
          leaf tcp-signaling-teardown {
            description
              "Match teardown signaling traffic on TCP";
            type empty;
          }
          leaf fraud-risk-http {
            description
              "Match fraudulent HTTP traffic";
            type empty;
          }
          leaf fraud-risk-tls {
            description
              "Match fraudulent TLS traffic";
            type empty;
          }
          leaf-list ip-packet-ttl-uplink-less-than {
            description
              "Match Uplink/Access packets with TTL lower than the specified value";
            type uint8 {
              range "2..255" {
                error-message "Invalid value for attribute 'ip-packet-ttl-uplink-less-than'. Valid values are in range:[2,255]";
              }
            }
            default "2";
            max-elements 1;
          }
          leaf-list ip-flow-network-address {
            description
              "IP Flow Network Address value to match";
            type eip-prefix-optional;
            max-elements 1;
          }
          leaf-list ip-flow-ue-address {
            description
              "IP Flow UE Address value to match";
            type eip-prefix-optional;
            max-elements 1;
          }
          leaf-list ip-flow-network-port {
            description
              "IP Flow Network Port value to match";
            type network-port-or-range;
            max-elements 1;
          }
          leaf-list ip-flow-network-port-tcp {
            description
              "IP Flow Network TCP Port value to match";
            type network-port-or-range;
            max-elements 1;
          }
          leaf-list ip-flow-network-port-udp {
            description
              "IP Flow Network UDP Port value to match";
            type network-port-or-range;
            max-elements 1;
          }
          leaf-list ip-flow-ue-port {
            description
              "IP Flow UE Port value to match";
            type network-port-or-range;
            max-elements 1;
          }
          leaf-list ip-flow-ue-port-tcp {
            description
              "IP Flow UE Port TCP value to match";
            type network-port-or-range;
            max-elements 1;
          }
          leaf-list ip-flow-ue-port-udp {
            description
              "IP Flow UE Port UDP value to match";
            type network-port-or-range;
            max-elements 1;
          }
          leaf-list ip-flow-protocol {
            description
              "IP Flow Protocol value to match";
            type enumeration {
              enum ah;
              enum egp;
              enum esp;
              enum gre;
              enum icmp;
              enum icmpv6;
              enum igmp;
              enum ipip;
              enum ospf;
              enum pim;
              enum rsvp;
              enum sctp;
              enum tcp;
              enum udp;
            }
            max-elements 1;
          }
          leaf-list ip-server-domain-name {
            description
              "IP Domain for DNS Query Name to match";
            type common-domain-string-id;
            max-elements 1;
          }
          leaf-list heuristic-protocol {
            description
              "Heuristic protocol to match";
            type common-string-id;
            must
              "(not((text()='skype-serv-default') or (text()='skype-serv-file-transfer') or (text()='skype-serv-voip') or
               (text()='skype-serv-instant-messaging') or (text()='skype')))" {
              error-message "Protocol not supported: skype, skype-serv-[default | instant-messaging | file-transfer | voip]. Please, configure skype-new, skype-new-serv-[instant-messaging | file-transfer | voip] instead";
            }
            max-elements 1;
          }
          leaf http-1x-malformed {
            description
              "Http 1X packets do NOT verify RFCs syntax.";
            type empty;
            must '(not(../http-1x-wellformed))' {
              error-message "http-1x-wellformed and http-1x-malformed are incompatible";
            }
          }
          leaf http-1x-wellformed {
            description
              "Http 1X packets verify RFCs syntax.";
            type empty;
            must '(not(../http-1x-malformed))' {
              error-message "http-1x-wellformed and http-1x-malformed are incompatible";
            }
          }
          list http-uri {
            key "value";
            description
              "HTTP URI value to match";
            uses sensitive-uri-like-string-value;
            max-elements 1;
          }
          list http-uri-not {
            key "value";
            description
              "HTTP URI value to NOT match";
            uses sensitive-uri-like-string-value;
            max-elements 1;
          }
          list http-host {
            key "value";
            description
              "HTTP HOST value to match";
            uses sensitive-uri-like-string-value;
            max-elements 1;
          }
          list http-host-not {
            key "value";
            description
              "HTTP HOST value to NOT match";
            uses sensitive-uri-like-string-value;
            max-elements 1;
          }
          list http-user-agent {
            key "value";
            description
              "HTTP USER AGENT value to match";
            uses sensitive-uri-like-string-value;
            max-elements 1;
          }
          list http-user-agent-not {
            key "value";
            description
              "HTTP USER AGENT value to NOT match";
            uses sensitive-uri-like-string-value;
            max-elements 1;
          }
          list http-domain {
            key "value";
            description
              "HTTP DOMAIN value to match";
            uses sensitive-uri-like-string-value;
            max-elements 1;
          }
          list http-domain-not {
            key "value";
            description
              "HTTP DOMAIN value to NOT match";
            uses sensitive-uri-like-string-value;
            max-elements 1;
          }
          leaf-list http-operation {
            description
              "HTTP OPERATION value to match";
            type enumeration {
              enum CONNECT;
              enum DELETE;
              enum GET;
              enum HEAD;
              enum OPTIONS;
              enum POST;
              enum PUT;
              enum TRACE;
            }
            must '(not(../ip-flow-protocol)) and (not(../ip-flow-network-port)) and (not(../ip-flow-network-port-udp))' {
              error-message "Not compatible with protocol or non-TCP ports";
            }
            max-elements 1;
          }
          list http-content-type {
            key "value";
            description
              "HTTP Content-Type value to match";
            uses sensitive-uri-like-string-value;
            max-elements 1;
          }
          list http-content-type-not {
            key "value";
            description
              "HTTP Content-Type value to NOT match";
            uses sensitive-uri-like-string-value;
            max-elements 1;
          }
          list tls-sni {
            key "value";
            description
              "TLS SNI value to match";
            uses sensitive-uri-like-string-value;
            max-elements 1;
          }
          list tls-sni-not {
            key "value";
            description
              "TLS SNI value to NOT match";
            uses sensitive-uri-like-string-value;
            max-elements 1;
          }
          list rtsp-uri {
            key "value";
            description
              "RTSP URI value to match";
            uses sensitive-uri-like-string-value;
            max-elements 1;
          }
          list rtsp-uri-not {
            key "value";
            description
              "RTSP URI value to NOT match";
            uses sensitive-uri-like-string-value;
            max-elements 1;
          }
          list dns-query-name {
            key "value";
            description
              "DNS query value to match";
            uses sensitive-uri-like-string-value;
            max-elements 1;
          }
          list dns-query-name-not {
            key "value";
            description
              "DNS query value to NOT match";
            uses sensitive-uri-like-string-value;
            max-elements 10;
          }
          list and {
            description
              "AND";
            max-elements 1;
            key "name";
            leaf name {
              description
                "AND cardinality";
              mandatory true;
              type uint16 {
                range "1" {
                  error-message "Invalid value for attribute 'name'. Valid values are in range:[1,1]";
                }
              }
            }
            leaf-list filter {
              description
                "Matching Condition Filter identifier to match";
              type leafref {
                path "../../../../filter-list/filter/name";
              }
            }
            uses matching-condition-group-for-and;
            list or {
              description
                "OR";
              key "name";
              leaf name {
                description
                  "OR cardinality";
                mandatory true;
                type uint16;
              }
              leaf-list filter {
                description
                  "Matching Condition Filter identifier to match";
                type leafref {
                  path "../../../../../filter-list/filter/name";
                }
              }
              uses matching-condition-group-for-or;
            }
          }
          list or {
            description
              "OR";
            max-elements 1;
            key "name";
            leaf name {
              description
                "OR cardinality";
              mandatory true;
              type uint16 {
                range "1" {
                  error-message "Invalid value for attribute 'name'. Valid values are in range:[1,1]";
                }
              }
            }
            leaf tcp-retransmission {
              description
                "Match retransmitted traffic on TCP";
              type empty;
              must '(../tcp-duplicated-ack)' {
                error-message "tcp-retransmission is not compatible with anything other than tcp-duplicated-ack";
              }
            }
            leaf tcp-duplicated-ack {
              description
                "Match duplicated ACKs on TCP";
              type empty;
              must '(../tcp-retransmission)' {
                error-message "tcp-duplicated-ack is not compatible with anything other than tcp-retransmission";
              }
            }
            leaf-list filter {
              description
                "Matching Condition Filter identifier to match";
              type leafref {
                path "../../../../filter-list/filter/name";
              }
            }
            list and {
              description
                "AND";
              key "name";
              leaf name {
                description
                  "AND cardinality";
                mandatory true;
                type uint16;
              }
              leaf-list filter {
                description
                  "Matching Condition Filter identifier to match";
                type leafref {
                  path "../../../../../filter-list/filter/name";
                }
              }
              uses matching-condition-group-for-and;
            }
            uses matching-condition-group-for-or;
          }
        }
      }
    }
  }

  grouping filterlist {
    container filter-list {
      description
        "Configuration for packet inspection";
      list filter {
        key "name";
        leaf name {
          description
            "Filter identifier";
          type common-string-id;
          mandatory true;
        }
        choice filter-matching-conditions-start-menu {
          mandatory true;
          leaf tethering {
            description
              "Match tethering detection traffic";
            type empty;
          }
          leaf tethering-first-uplink-packet {
            description
              "Match the first uplink tethering detection traffic";
            type empty;
          }
          leaf-list tls-extension {
            description
              "Classification of traffic with TLS extension as configured value";
            type uint16 {
              range "0..65535" {
                error-message "Invalid value for attribute 'tls-extension'. Valid values are in range:[0,65535]";
              }
            }
            max-elements 1;
          }
          leaf-list ip-flow-ttl-uplink {
            description
              "Classification of traffic with TTL as configured value";
            type uint16 {
              range "1..255" {
                error-message "Invalid value for attribute 'ip-flow-ttl-uplink'. Valid values are in range:[1,255]";
              }
            }
            max-elements 1;
          }
          leaf-list ip-flow-ttl-uplink-not {
            description
              "Classification of traffic with TTL different as configured value";
            type uint16 {
              range "1..255" {
                error-message "Invalid value for attribute 'ip-flow-ttl-uplink-not'. Valid values are in range:[1,255]";
              }
            }
            max-elements 1;
          }
          leaf-list ip-flow-ttl-uplink-less-than {
            description
              "Match Uplink/Access packets with TTL lower than the specified value";
            type uint16 {
              range "2..255" {
                error-message "Invalid value for attribute 'ip-flow-ttl-uplinki-less-than'. Valid values are in range:[2,255]";
              }
            }
            max-elements 1;
          }
          leaf-list ip-flow-ttl-uplink-greater-than {
            description
              "Match Uplink/Access packets with TTL greater than the specified value";
            type int16 {
              range "0..253" {
                error-message "Invalid value for attribute 'ip-flow-ttl-uplink-greater-than'. Valid values are in range:[0,253]";
              }
            }
            max-elements 1;
          }
          leaf tcp-signaling-setup {
            description
              "Match setup signaling traffic on TCP";
            type empty;
          }
          leaf tcp-signaling-teardown {
            description
              "Match teardown signaling traffic on TCP";
            type empty;
          }
          leaf fraud-risk-http {
            description
              "Match fraudulent HTTP traffic";
            type empty;
          }
          leaf fraud-risk-tls {
            description
              "Match fraudulent TLS traffic";
            type empty;
          }
          leaf-list ip-packet-ttl-uplink-less-than {
            description
              "Match Uplink/Access packets with TTL lower than the specified value";
            type uint8 {
              range "2..255" {
                error-message "Invalid value for attribute 'ip-packet-ttl-uplink-less-than'. Valid values are in range:[2,255]";
              }
            }
            default "2";
            max-elements 1;
          }
          leaf-list ip-flow-network-address {
            description
              "IP Flow Network Address value to match";
            type eip-prefix-optional;
            max-elements 1;
          }
          leaf-list ip-flow-ue-address {
            description
              "IP Flow UE Address value to match";
            type eip-prefix-optional;
            max-elements 1;
          }
          leaf-list ip-flow-network-port {
            description
              "IP Flow Network Port value to match";
            type network-port-or-range;
            max-elements 1;
          }
          leaf-list ip-flow-network-port-tcp {
            description
              "IP Flow Network TCP Port value to match";
            type network-port-or-range;
            max-elements 1;
          }
          leaf-list ip-flow-network-port-udp {
            description
              "IP Flow Network UDP Port value to match";
            type network-port-or-range;
            max-elements 1;
          }
          leaf-list ip-flow-ue-port {
            description
              "IP Flow UE Port value to match";
            type network-port-or-range;
            max-elements 1;
          }
          leaf-list ip-flow-ue-port-tcp {
            description
              "IP Flow UE Port TCP value to match";
            type network-port-or-range;
            max-elements 1;
          }
          leaf-list ip-flow-ue-port-udp {
            description
              "IP Flow UE Port UDP value to match";
            type network-port-or-range;
            max-elements 1;
          }
          leaf-list ip-flow-protocol {
            description
              "IP Flow Protocol value to match";
            type enumeration {
              enum ah;
              enum egp;
              enum esp;
              enum gre;
              enum icmp;
              enum icmpv6;
              enum igmp;
              enum ipip;
              enum ospf;
              enum pim;
              enum rsvp;
              enum sctp;
              enum tcp;
              enum udp;
            }
            max-elements 1;
          }
          leaf-list ip-server-domain-name {
            description
              "IP Domain for DNS Query Name to match";
            type common-domain-string-id;
            max-elements 1;
          }
          leaf-list heuristic-protocol {
            description
              "Heuristic protocol to match";
            type common-string-id;
            must
              "(not((text()='skype-serv-default') or (text()='skype-serv-file-transfer') or (text()='skype-serv-voip') or
               (text()='skype-serv-instant-messaging') or (text()='skype')))" {
              error-message "Protocol not supported: skype, skype-serv-[default | instant-messaging | file-transfer | voip]. Please, configure skype-new, skype-new-serv-[instant-messaging | file-transfer | voip] instead";
            }
            max-elements 1;
          }
          leaf http-1x-malformed {
            description
              "Http 1X packets do NOT verify RFCs syntax.";
            type empty;
            must '(not(../http-1x-wellformed))' {
              error-message "http-1x-wellformed and http-1x-malformed are incompatible";
            }
          }
          leaf http-1x-wellformed {
            description
              "Http 1X packets verify RFCs syntax.";
            type empty;
            must '(not(../http-1x-malformed))' {
              error-message "http-1x-wellformed and http-1x-malformed are incompatible";
            }
          }
          list http-uri {
            key "value";
            description
              "HTTP URI value to match";
            uses sensitive-uri-like-string-value;
            max-elements 1;
          }
          list http-uri-not {
            key "value";
            description
              "HTTP URI value to NOT match";
            uses sensitive-uri-like-string-value;
            max-elements 1;
          }
          list http-host {
            key "value";
            description
              "HTTP HOST value to match";
            uses sensitive-uri-like-string-value;
            max-elements 1;
          }
          list http-host-not {
            key "value";
            description
              "HTTP HOST value to NOT match";
            uses sensitive-uri-like-string-value;
            max-elements 1;
          }
          list http-user-agent {
            key "value";
            description
              "HTTP USER AGENT value to match";
            uses sensitive-uri-like-string-value;
            max-elements 1;
          }
          list http-user-agent-not {
            key "value";
            description
              "HTTP USER AGENT value to NOT match";
            uses sensitive-uri-like-string-value;
            max-elements 1;
          }
          list http-domain {
            key "value";
            description
              "HTTP DOMAIN value to match";
            uses sensitive-uri-like-string-value;
            max-elements 1;
          }
          list http-domain-not {
            key "value";
            description
              "HTTP DOMAIN value to NOT match";
            uses sensitive-uri-like-string-value;
            max-elements 1;
          }
          leaf-list http-operation {
            description
              "HTTP OPERATION value to match";
            type enumeration {
              enum CONNECT;
              enum DELETE;
              enum GET;
              enum HEAD;
              enum OPTIONS;
              enum POST;
              enum PUT;
              enum TRACE;
            }
            must '(not(../ip-flow-protocol)) and (not(../ip-flow-network-port)) and (not(../ip-flow-network-port-udp))' {
              error-message "Not compatible with protocol or non-TCP ports";
            }
            max-elements 1;
          }
          list http-content-type {
            key "value";
            description
              "HTTP Content-Type value to match";
            uses sensitive-uri-like-string-value;
            max-elements 1;
          }
          list http-content-type-not {
            key "value";
            description
              "HTTP Content-Type value to NOT match";
            uses sensitive-uri-like-string-value;
            max-elements 1;
          }
          list tls-sni {
            key "value";
            description
              "TLS SNI value to match";
            uses sensitive-uri-like-string-value;
            max-elements 1;
          }
          list tls-sni-not {
            key "value";
            description
              "TLS SNI value to NOT match";
            uses sensitive-uri-like-string-value;
            max-elements 1;
          }
          list rtsp-uri {
            key "value";
            description
              "RTSP URI value to match";
            uses sensitive-uri-like-string-value;
            max-elements 1;
          }
          list rtsp-uri-not {
            key "value";
            description
              "RTSP URI value to NOT match";
            uses sensitive-uri-like-string-value;
            max-elements 1;
          }
          list dns-query-name {
            key "value";
            description
              "DNS query value to match";
            uses sensitive-uri-like-string-value;
            max-elements 1;
          }
          list dns-query-name-not {
            key "value";
            description
              "DNS query value to NOT match";
            uses sensitive-uri-like-string-value;
            max-elements 10;
          }
          list and {
            description
              "AND";
            max-elements 1;
            key "name";
            leaf name {
              description
                "AND cardinality";
              mandatory true;
              type uint16 {
                range "1" {
                  error-message "Invalid value for attribute 'name'. Valid values are in range:[1,1]";
                }
              }
            }
            uses matching-condition-group-for-and;
            list or {
              description
                "OR";
              key "name";
              leaf name {
                description
                  "OR cardinality";
                mandatory true;
                type uint16;
              }
              uses matching-condition-group-for-or;
            }
          }
          list or {
            description
              "OR";
            max-elements 1;
            key "name";
            leaf name {
              description
                "OR cardinality";
              mandatory true;
              type uint16 {
                range "1" {
                  error-message "Invalid value for attribute 'name'. Valid values are in range:[1,1]";
                }
              }
            }
            uses matching-condition-group-for-or;
            list and {
              description
                "AND";
              key "name";
              leaf name {
                description
                  "AND cardinality";
                mandatory true;
                type uint16;
              }
              uses matching-condition-group-for-and;
            }
          }
        }
      }
    }
  }

  grouping packet-detection-dns-monitoring {
    container dns-monitoring {
      description
        "DNS Monitoring Settings";
      leaf-list trusted-dns-server {
        description
          "Network Address of Trusted Dns Servers";
        type inet:ip-address;
        max-elements 32;
      }
      leaf ip-server-domain-max-dynamic-rules {
        description
          "Max number of dinamic ip server domain rules";
        type uint32 {
          range "256..512000" {
            error-message "Invalid value for attribute 'ip-server-domain-max-dynamic-rules'. Valid values are in range:[256,512000]";
          }
        }
        default "60000";
      }
    }
  }

  grouping flow-management {
    description
      "Flow settings";
    leaf max-session-flows {
      description
        "Max number of connections for a given session. A zero value means no limit.";
      type uint64;
    }
    container flow-timeout-traffic {
      leaf tcp {
        description
          "Flow timeout for TCP flows";
        type uint16 {
          range "1..3600" {
            error-message "Invalid value for attribute 'flow-timeout-traffic tcp'. Valid values are in range:[1,3600]";
          }
        }
        default "30";
      }
      leaf udp {
        description
          "Flow timeout for UDP flows";
        type uint16 {
          range "1..3600" {
            error-message "Invalid value for attribute 'flow-timeout-traffic udp'. Valid values are in range:[1,3600]";
          }
        }
        default "30";
      }
      leaf http {
        description
          "Flow timeout for HTTP flows";
        type uint16 {
          range "1..3600" {
            error-message "Invalid value for attribute 'flow-timeout-traffic http'. Valid values are in range:[1,3600]";
          }
        }
        default "30";
      }
      leaf tls {
        description
          "Flow timeout for TLS flows";
        type uint16 {
          range "1..3600" {
            error-message "Invalid value for attribute 'flow-timeout-traffic tls'. Valid values are in range:[1,3600]";
          }
        }
        default "30";
      }
      leaf dns {
        description
          "Flow timeout for DNS flows";
        type uint16 {
          range "1..3600" {
            error-message "Invalid value for attribute 'flow-timeout-traffic dns'. Valid values are in range:[1,3600]";
          }
        }
        default "30";
      }
      leaf rtp {
        description
          "Flow timeout for RTP flows";
        type uint16 {
          range "1..3600" {
            error-message "Invalid value for attribute 'flow-timeout-traffic rtp'. Valid values are in range:[1,3600]";
          }
        }
        default "60";
      }
      leaf rtsp {
        description
          "Flow timeout for RTSP flows";
        type uint16 {
          range "1..3600" {
            error-message "Invalid value for attribute 'flow-timeout-traffic rtsp'. Valid values are in range:[1,3600]";
          }
        }
        default "300";
      }
      leaf icmp {
        description
          "Flow timeout for ICMPv4 and ICMPv6 flows";
        type uint16 {
          range "1..3600" {
            error-message "Invalid value for attribute 'flow-timeout-traffic icmp'. Valid values are in range:[1,3600]";
          }
        }
        default "5";
      }
    }
  }

  grouping dhcp-shared-type {
    leaf name {
      description
        "Name of server";
      type string {
        pattern '[.0-9A-Za-z_-]*' {
          error-message "Must contain only letters, numbers, underscores or dashes";
        }
        length "1..64";
      }
    }
    leaf-list address {
      description
        "DHCP server addresses";
      type inet:ipv4-address;
      min-elements 1;
    }
    leaf routing-instance {
      description
        "Routing instance for server";
      type string;
      must "/ctxsipos:contexts/ctxipos:context[ctxipos:context-name=current()]" {
        error-message "Routing instance must be configured under 'managed-element context'";
      }
      default "local";
    }
    choice address-range-choice {
      leaf gi-address-range {
        description
          "Address range used in routing instance";
        type eipv4-prefix-optional;
      }
    }
    leaf timeout {
      description
        "Request timeout period";
      type uint8 {
        range "1..90" {
          error-message "Invalid value for attribute 'timeout'. Valid values are in range:[1,90]";
        }
      }
    }
    leaf retry {
      description
        "Retry attempts";
      type uint8 {
        range "1..10" {
          error-message "Invalid value for attribute 'retry'. Valid values are in range:[1,10]";
        }
      }
    }
  }

  grouping radius-shared-type {
    leaf name {
      description
        "Name of server";
      type string {
        pattern '[.0-9A-Za-z_-]*' {
          error-message "Must contain only letters, numbers, underscores or dashes";
        }
        length "1..64";
      }
    }
    leaf wpp-compatible-encoding {
      description
        "Encode RADIUS attributes in a format compatible with WPP GGSN";
      type empty;
    }
    leaf-list address {
      description
        "RADIUS server addresses";
      type inet:ipv4-address;
      min-elements 1;
      ordered-by user;
    }
    leaf routing-instance {
      description
        "Routing instance for server";
      type string;
      must "/ctxsipos:contexts/ctxipos:context[ctxipos:context-name=current()]" {
        error-message "Routing instance must be configured under 'managed-element context'";
      }
      default "local";
    }
    choice address-range-choice {
      leaf gi-address-range {
        description
          "Address range used in routing instance";
        type eipv4-prefix-optional;
      }
    }
    leaf timeout {
      description
        "Request timeout period";
      type uint8 {
        range "1..90" {
          error-message "Invalid value for attribute 'timeout'. Valid values are in range:[1,90]";
        }
      }
    }
    leaf retry {
      description
        "Retry attempts";
      type uint8 {
        range "1..10" {
          error-message "Invalid value for attribute 'retry'. Valid values are in range:[1,10]";
        }
      }
    }
    leaf port {
      description
        "Port number for RADIUS messages";
      type uint16;
    }
    leaf secret {
      description
        "Shared secret with the RADIUS server";
      type tailf:aes-cfb-128-encrypted-string;
      mandatory true;
    }
    leaf serverdown-timeout {
      description
        "Time before retrying requests to a down server";
      type uint16 {
        range "0..1800" {
          error-message "Invalid value for attribute 'serverdown-timeout'. Valid values are in range:[0,1800]";
        }
      }
    }
    leaf acct-interim-requests-per-second {
      description
        "Accounting interim update request per second";
      type uint16 {
        range "0..65535" {
          error-message "Invalid value for attribute 'acct-interim-requests-per-second'. Valid values are in range:[0,65535]";
        }
      }
    }
    leaf multicast-servers {
      description
        "Number of enabled RADIUS multicast servers";
      type uint8 {
        range "0..9" {
          error-message "Invalid value for attribute 'multicast-servers'. Valid values are in range:[0,9]";
        }
      }
    }
    leaf no-interim-update-multicast {
      description
        "Do not send interim multicast to this RADIUS server";
      type empty;
    }
    leaf no-accounting-on {
      description
        "Do not send accounting on and off messages";
      type empty;
    }
    leaf no-accounting-on-resp-needed {
      description
        "Accounting on response not needed";
      type empty;
    }
    leaf accounting-on-retry {
      description
        "Accounting on request will be continuously sent until Accounting on response is received";
      type empty;
    }
    container accounting-on {
      description
        "Relates only to accounting-on";
      must 'not (/epg/pgw/radius/server[name=current()/../name]/no-accounting-on)' {
        error-message "no-accounting-on can not be set when using this configuration";
      }
      presence "accounting-on need presence";
      leaf no-short-timer {
        description
          "Will disable the short retry-timer for accounting-on";
        type empty;
      }
      leaf long-retry-timer {
        description
          "Define the long retry-timer for accounting-on, default: 60 seconds";
        type uint8 {
          range "5..90" {
            error-message "Invalid value for attribute 'long-retry-timer'. Valid values are in range:[5,90]";
          }
        }
      }
    }
  }

  grouping session-priority-mp-priority-type {
    leaf name {
      description
        "configure the MP index for highPriority";
      type uint8 {
        range "0..15" {
          error-message "Invalid value for attribute 'mp-index'. Valid values are in range:[0,15]";
        }
      }
    }
    leaf high-prio-service {
      description
        "EMPS tag indicates message priority belongs to EMPS session";
      type empty;
    }
  }

  grouping session-priority-arp-priority-type {
    leaf name {
      description
        "configure the ARP index for MP and DRMP table";
      type uint8 {
        range "1..15" {
          error-message "Invalid value for attribute 'arp-index'. Valid values are in range:[1,15]";
        }
      }
    }
    container gtp {
      leaf message-priority {
        description
          "MP (message priority) configuration in the ARP mapping table";
        type uint8 {
          range "0..15" {
            error-message "Invalid value for attribute 'message-priority'. Valid values are in range:[0,15]";
          }
        }
      }
    }
    container diameter {
      leaf routing-message-priority {
        description
          "DRMP (diameter routing message priority) configuration in the ARP mapping table";
        type uint8 {
          range "0..15" {
            error-message "Invalid value for attribute 'routing-message-priority'. Valid values are in range:[0,15]";
          }
        }
      }
    }
    container aaa {
      leaf e-mps {
        description
          "Indicate eMPS session";
        type empty;
      }
    }
  }

  grouping dhcpv6-type {
    leaf link-layer-address {
      description
        "The mac address for the delegate router";
      type string {
        pattern '[0-9a-fA-F]{1,255}' {
          error-message "Link layer address is a string consisting of 1 to 255 hexadecimal digits";
        }
      }
      mandatory true;
    }
    container act-as-server {
      description
        "Configuration for acting as a server";
      leaf default {
        description
          "Reference to the profile in [epg pgw dhcpv6 act-as-server profile]";
        type leafref {
          path "/epg/pgw/dhcpv6/act-as-server/profile/name";
        }
      }
      list profile {
        description
          "Dhcpv6 profile as a server";
        key "name";
        leaf name {
          description
            "Profile identifier";
          type string {
            pattern '[.0-9A-Za-z_-]*' {
              error-message "Must contain only letters, numbers, underscores or dashes";
            }
            length "1..64";
          }
        }
        leaf preferred-lifetime {
          description
            "Preferred lifetime for the ipv6 prefix";
          type uint32;
        }
        leaf valid-lifetime {
          description
            "Valid lifetime for the ipv6 prefix";
          type uint32;
        }
        leaf t1 {
          description
            "T1 for the ipv6 prefix";
          type uint32;
        }
        leaf t2 {
          description
            "T2 for the ipv6 prefix";
          type uint32;
        }
        leaf unicast {
          description
            "Include unicast option in advertise message";
          type empty;
        }
        ordered-by user;
      }
    }
    container act-as-client {
      description
        "Configuration for acting as a client";
      leaf default {
        description
          "Reference to the profile in [epg pgw dhcpv6 act-as-client profile]";
        type leafref {
          path "/epg/pgw/dhcpv6/act-as-client/profile/name";
        }
      }
      list profile {
        description
          "Dhcpv6 profile as a client";
        key "name";
        leaf name {
          description
            "Profile identifier";
          type string {
            pattern '[.0-9A-Za-z_-]*' {
              error-message "Must contain only letters, numbers, underscores or dashes";
            }
            length "1..64";
          }
        }
        leaf logical-interface {
          description
            "Reference to the logical-interface in [epg node logical-interface]";
          type leafref {
            path "/epg/node/logical-interface/name";
          }
          mandatory true;
        }
        leaf user-class-option {
          description
            "Include user class option with msisdn in all request message";
          type empty;
        }
        leaf send-relay-message {
          description
            "Send all request message in relay format";
          type empty;
        }
        leaf retry {
          description
            "Retry attempts";
          type uint8 {
            range "1..3" {
              error-message "Invalid value for attribute 'retry'. Valid values are in range:[1,3]";
            }
          }
        }
        leaf timeout {
          description
            "Request timeout period";
          type uint8 {
            range "1..5" {
              error-message "Invalid value for attribute 'timeout'. Valid values are in range:[1,5]";
            }
          }
        }
        ordered-by user;
      }
    }
    list server {
      description
        "Server Configuration";
      key "name";
      leaf name {
        description
          "Server identifier";
        type string {
          pattern '[.0-9A-Za-z_-]*' {
            error-message "Must contain only letters, numbers, underscores or dashes";
          }
          length "1..64";
        }
      }
      leaf-list ipv6-address {
        description
          "Server address";
        type inet:ipv6-address;
        min-elements 1;
        max-elements 16;
        ordered-by user;
      }
      ordered-by user;
    }
  }

  grouping aaa-node-type {
    list s6b-profile {
      description
        "S6b profiles";
      key "name";
      leaf name {
        description
          "Profile identifier";
        type string {
          pattern '[.0-9A-Za-z_-]*' {
            error-message "Must contain only letters, numbers, underscores or dashes";
          }
          length "1..64";
        }
      }
      leaf diameter-application-system {
        description
          "Diameter application system";
        type leafref {
          path "/epg/pgw/diameter/diameter-application-system/name";
        }
        mandatory true;
        must "/epg/pgw/diameter/diameter-application-system[name=current()]/application-id[text()='s6b']" {
          error-message "Diameter application system must be configured under [epg pgw diameter diameter-application-system] and have application-id s6b";
          tailf:dependency "/epg/pgw/diameter/diameter-application-system/application-id";
        }
      }
    }
    list s6b-auth-profile {
      description
        "S6b authorization profile";
      key "name";
      leaf name {
        description
          "Profile identifier";
        type string {
          pattern '[.0-9A-Za-z_-]*' {
            error-message "Must contain only letters, numbers, underscores or dashes";
          }
          length "1..64";
        }
      }
      leaf diameter-application-system {
        description
          "Diameter application system";
        type leafref {
          path "/epg/pgw/diameter/diameter-application-system/name";
        }
        mandatory true;
        must "/epg/pgw/diameter/diameter-application-system[name=current()]/application-id[text()='16777999']" {
          error-message "Diameter application system must be configured under [epg pgw diameter diameter-application-system] and have application-id 16777999";
          tailf:dependency "/epg/pgw/diameter/diameter-application-system/application-id";
        }
      }
      leaf authorization-life-time {
        description
          "The amount of time in seconds before a re-authorization of the session is needed";
        type uint32 {
          range "0..2147483647" {
            error-message "Invalid value for attribute 'authorization-life-time'. Valid values are in range:[0,2147483647]";
          }
        }
      }
      leaf authorization-grace-period {
        description
          "The amount of time in seconds to wait for a re-authorization after the elapse of the authorization lifetime before closing the session";
        type uint32 {
          range "0..2147483647" {
            error-message "Invalid value for attribute 'authorization-grace-period'. Valid values are in range:[0,2147483647]";
          }
        }
      }
      leaf terminate-pdn-at-update-failure {
        description
          "Session will be terminated when aar-u failed";
        type empty;
      }
      leaf reject-create-at-retry-timeout {
        description
          "Session will be rejected when aar-i timeout";
        type empty;
      }
      leaf priority-service-at-retry-timeout {
        description
          "EMPS session will be continued when aar-i timeout";
        type empty;
      }
      leaf p-cscf-restoration-wlan {
        description
          "HSS based p-cscf restoration for S2b support";
        type empty;
      }
      leaf charging-gateway-function-host {
        description
          "Fully Qualified Domain Name (FQDN) for CDF";
        type string {
          pattern '[.0-9A-Za-z_-]*' {
            error-message "Must contain only letters, numbers, underscores or dashes";
          }
          length "1..255";
        }
      }
      leaf charging-group-id {
        description
          "The charging group that the subscriber belongs to";
        type string {
          pattern '[.0-9A-Za-z_-]*' {
            error-message "Must contain only letters, numbers, underscores or dashes";
          }
          length "1..124";
        }
      }
      container aar-avp {
        description
          "S6b authorization AAR avp configuration";
        leaf auth-session-state {
          description
            "Include auth-session-state AVP";
          type empty;
        }
        leaf add-leading-digit {
          description
            "Add leading digit in user name of s6b auth interface message";
          type empty;
        }
        leaf rat-type {
          description
            "Add rat-type in s6b auth AAR message";
          type empty;
        }
        leaf late-request-handling {
          description
            "Include origination-time-stamp and maximum-wait-time AVPs";
          type empty;
        }
        leaf rat-type-for-ehrpd {
          description
            "Define rat-type for eHRPD access";
          type enumeration {
            enum hrpd {
              description
                "Send HRPD as rat-type for eHRPD access";
            }
            enum ehrpd {
              description
                "Send eHRPD as rat-type for eHRPD access";
            }
          }
          status deprecated;
        }
        container rat-type-map {
          description
            "Defines rat type mapping";
          list from {
            description
              "Original RAT type identifier to map from";
            key "name";
            leaf name {
              description
                "RAT type identifier to be mapped";
              type enumeration {
                enum ehrpd {
                  value 1;
                  description
                    "Evolved high rate packet data radio access network";
                }
              }
            }
            leaf to {
              description
                "RAT type identifier to map to";
              type enumeration {
                enum ehrpd {
                  value 1;
                  description
                    "Evolved high rate packet data radio access network";
                }
                enum hrpd {
                  value 2;
                  description
                    "High rate packet data radio access network";
                }
              }
              mandatory true;
            }
          }
        }
      }
    }
    leaf pgw-identity {
      description
        "PGW hostname for DNS procedure";
      type string {
        pattern '[.A-Za-z0-9-]{6,255}' {
          error-message "PGW Identity is a string consisting of 6 to 255 letters, numbers, hyphens, and periods";
        }
      }
      mandatory true;
    }
  }

  grouping apn-selection-condition-type {
    leaf name {
      description
        "Selection condition name";
      type string {
        pattern '[.0-9A-Za-z_-]*' {
          error-message "Must contain only letters, numbers, underscores or dashes";
        }
        length "1..64";
      }
      mandatory true;
    }
    leaf selected-apn {
      description
        "Name of APN";
      type leafref {
        path "/epg/pgw/apn/name";
      }
      must '(../../../default) or (../charging-characteristics) or (../imsi) or ((../msisdn-range/from) and (../msisdn-range/to)) or (../rat-type) or (../roaming-status) or (../serving-node-address) or (../tac) or (../lac) or (../rac) or (../plmn) or (../imei) or (../pdn-type)' {
        error-message "Invalid configuration: Atleast one parameter type must to be configured or 'default' must be configured under 'logical-apn'";
      }
    }
    leaf reported-apn {
      description
        "Reported access point name identifier";
      type string {
        pattern '[.0-9A-Za-z-]{1,100}' {
          error-message "Must be a string of 100 or fewer characters and may contain letters, numbers, decimals and dashes.";
        }
      }
      must '../selected-apn' {
        error-message "'selected-apn' need to be configured";
      }
    }
    leaf-list charging-characteristics {
      max-elements 1;
      description
        "APN selection based on charging characteristics";
      type enumeration {
        enum profile0 {
          description
            "Profile 0";
        }
        enum profile1 {
          description
            "Profile 1";
        }
        enum profile2 {
          description
            "Profile 2";
        }
        enum profile3 {
          description
            "Profile 3";
        }
        enum profile4 {
          description
            "Profile 4";
        }
        enum profile5 {
          description
            "Profile 5";
        }
        enum profile6 {
          description
            "Profile 6";
        }
        enum profile7 {
          description
            "Profile 7";
        }
        enum profile8 {
          description
            "Profile 8";
        }
        enum profile9 {
          description
            "Profile 9";
        }
        enum profile10 {
          description
            "Profile 10";
        }
        enum profile11 {
          description
            "Profile 11";
        }
        enum profile12 {
          description
            "Profile 12";
        }
        enum profile13 {
          description
            "Profile 13";
        }
        enum profile14 {
          description
            "Profile 14";
        }
        enum profile15 {
          description
            "Profile 15";
        }
      }
      must '../selected-apn' {
        error-message "'selected-apn' need to be configured";
      }
    }
    leaf imsi {
      description
        "APN selection based on imsi range";
      type string;
      must '../selected-apn' {
        error-message "'selected-apn' need to be configured";
      }
    }
    container imsi-based-characteristics {
      description
        "Charging characteristic based on IMSI";
      choice imsi-based-characteristics-choice {
        leaf disable {
          description
            "Disable imsi-based selection of charging characteristics";
          type empty;
        }
        leaf override {
          description
            "Force imsi-based selection of charging characteristics";
          type empty;
        }
      }
    }
    container msisdn-range {
      description
        "APN selection based on MSISDN range";
      leaf from {
        description
          "MSISDN range from";
        type string {
          pattern '([0-9]{5,15})|([0-9]{1,18})' {
            error-message "ERROR: Invalid value for parameter from. Valid values are strings in a specified format. Type: from? for more information on the format to use.";
          }
          length "10..15";
        }
        must '../../selected-apn' {
          error-message "'selected-apn' need to be configured";
        }
      }
      leaf to {
        description
          "MSISDN range to";
        type string {
          pattern '([0-9]{5,15})|([0-9]{1,18})' {
            error-message "ERROR: Invalid value for parameter to. Valid values are strings in a specified format. Type: to? for more information on the format to use.";
          }
          length "10..15";
        }
        must '../../selected-apn' {
          error-message "'selected-apn' need to be configured";
        }
      }
    }
    leaf rat-type {
      description
        "APN selection based on Radio access technology (RAT)";
      type common-rat-type;
      must '../selected-apn' {
        error-message "'selected-apn' need to be configured";
      }
    }
    leaf roaming-status {
      description
        "APN selection based on roaming status";
      type enumeration {
        enum home {
          description
            "In Home network";
        }
        enum roaming {
          description
            "In Roaming";
        }
      }
      must '../selected-apn' {
        error-message "'selected-apn' need to be configured";
      }
    }
    leaf pdn-type {
      description
        "PDN context type";
      type enumeration {
        enum ipv4 {
          description
            "IPv4 PDN context type";
        }
        enum ipv6 {
          description
            "IPv6 PDN context type";
        }
        enum ipv4v6 {
          description
            "IPv4v6 PDN contexts";
        }
        enum non-ip {
          description
            "non-ip PDN context type";
        }
      }
      must
        "((../pdn-type != 'non-ip' and (/epg/pgw/apn[name=current()/../selected-apn]/pdp-context/pdp-type != 'non-ip'))
           and (((../pdn-type = 'ipv4' and (/epg/pgw/apn[name=current()/../selected-apn]/pdp-context/pdp-type != 'ipv6')))
           or ((../pdn-type = 'ipv6' and (/epg/pgw/apn[name=current()/../selected-apn]/pdp-context/pdp-type != 'ipv4')))))
           or (../pdn-type = 'non-ip' and (/epg/pgw/apn[name=current()/../selected-apn]/pdp-context/pdp-type = 'non-ip'))
           or (../pdn-type = 'ipv4v6' and (/epg/pgw/apn[name=current()/../selected-apn]/pdp-context/pdp-type != 'non-ip'))" {
        error-message "pdn-type should match pdp-type under epg pgw apn[name=current()/selected-apn] pdp-context pdp-type";
      }
      must '../selected-apn' {
        error-message "'selected-apn' need to be configured";
      }
    }
    leaf serving-node-address {
      description
        "Serving Node address or address prefix";
      type eip-prefix-optional;
      must '../selected-apn' {
        error-message "'selected-apn' need to be configured";
      }
    }
    leaf tac {
      description
        "APN selection based on TAC";
      type uint16 {
        range "1..65535" {
          error-message "Invalid value for attribute 'TAC'. Valid values are in range:[1,65535]";
        }
      }
      must '../selected-apn' {
        error-message "'selected-apn' need to be configured";
      }
    }
    leaf lac {
      description
        "APN selection based on LAC";
      type uint16 {
        range "1..65535" {
          error-message "Invalid value for attribute 'LAC'. Valid values are in range:[1,65535]";
        }
      }
      must '../selected-apn' {
        error-message "'selected-apn' need to be configured";
      }
    }
    leaf rac {
      description
        "APN selection based on RAC";
      type uint8 {
        range "1..255" {
          error-message "Invalid value for attribute 'RAC'. Valid values are in range:[1,255]";
        }
      }
      must '../selected-apn' {
        error-message "'selected-apn' need to be configured";
      }
    }
    leaf plmn {
      description
        "APN selection based on plmn id";
      type string {
        pattern '[0-9]*' {
          error-message "PLMN identifier is a string of 5 or 6 digits";
        }
        length "5..6";
      }
      must '../selected-apn' {
        error-message "'selected-apn' need to be configured";
      }
    }
    leaf imei {
      description
        "APN selection based on imei or imei-tac";
      type string {
        pattern '[0-9]*' {
          error-message "ERROR: Invalid value for parameter IMEI identifier";
        }
        length "8..16";
      }
      must '../selected-apn' {
        error-message "'selected-apn' need to be configured";
      }
    }
  }

  grouping logical-to-apn-reference-type {
    leaf name {
      description
        "Name of APN";
      type leafref {
        path "/epg/pgw/apn/name";
      }
    }
  }

  grouping logapn-type {
    leaf name {
      description
        "Logical access point name identifier";
      type string {
        pattern '[.0-9A-Za-z-]{1,100}' {
          error-message "Must be a string of 100 or fewer characters and may contain letters, numbers, decimals and dashes.";
        }
      }
    }
    container access-restrictions {
      description
        "Settings for APN access restrictions";
      leaf selection-mode {
        description
          "User access to the APN";
        type enumeration {
          enum public {
            description
              "User does not need to be subscribed for APN";
          }
          enum from-user {
            description
              "Can choose which APN to connect";
          }
          enum from-network {
            description
              "Can connect to default APN for the MME/SGW/SGSN";
          }
          enum restricted {
            description
              "Admit only users subscribed for APN";
          }
        }
      }
      container radius-assisted-apn-selection {
        description
          "Enable RADIUS assisted APN selection";
        presence "radius-assisted-apn-selection need presence";
        leaf default {
          description
            "Default APN name for radius assisted APN selection";
          type leafref {
            path "/epg/pgw/apn/name";
          }
        }
      }
    }
    container pdp-context {
      description
        "PDP context";
      leaf creation {
        description
          "PDP context creation state";
        type enumeration {
          enum unblocked {
            description
              "No restrictions on PDP context creation";
          }
          enum blocked {
            description
              "New PDP context creation fully blocked";
          }
        }
      }
    }
    leaf default {
      description
        "set logical-apn name as default";
      type empty;
    }
    leaf full-username {
      description
        "Set full username in Radius attribute #1 when sending access-request, username = username@<apn>, default username = username";
      type empty;
    }
    container apn {
      description
        "APN selection configuration";
      presence "apn need presence";
      leaf default {
        description
          "APN used when not using cc-based or username-based apn selection";
        type leafref {
          path "/epg/pgw/apn/name";
        }
      }
      list selectable {
        key "name";
        uses logical-to-apn-reference-type;
      }
      list cc-based-apn {
        description
          "APN selection based on charging characteristics";
        max-elements 16;
        key "name";
        leaf name {
          description
            "Name of charging characteristics profile";
          type enumeration {
            enum profile0 {
              description
                "Profile 0";
            }
            enum profile1 {
              description
                "Profile 1";
            }
            enum profile2 {
              description
                "Profile 2";
            }
            enum profile3 {
              description
                "Profile 3";
            }
            enum profile4 {
              description
                "Profile 4";
            }
            enum profile5 {
              description
                "Profile 5";
            }
            enum profile6 {
              description
                "Profile 6";
            }
            enum profile7 {
              description
                "Profile 7";
            }
            enum profile8 {
              description
                "Profile 8";
            }
            enum profile9 {
              description
                "Profile 9";
            }
            enum profile10 {
              description
                "Profile 10";
            }
            enum profile11 {
              description
                "Profile 11";
            }
            enum profile12 {
              description
                "Profile 12";
            }
            enum profile13 {
              description
                "Profile 13";
            }
            enum profile14 {
              description
                "Profile 14";
            }
            enum profile15 {
              description
                "Profile 15";
            }
          }
          mandatory true;
          status deprecated;
        }
        leaf apn-name {
          description
            "Name of APN";
          type leafref {
            path "/epg/pgw/apn/name";
          }
          mandatory true;
          status deprecated;
        }
        must 'not (../selection-condition)' {
          error-message "Incompatible with 'if configured without selection condition'";
        }
        status deprecated;
      }
      container imsi-based-characteristics {
        description
          "Charging characteristic based on IMSI";
        choice imsi-based-characteristics-choice {
          leaf disable {
            description
              "Disable imsi-based selection of charging characteristics";
            type empty;
            must 'not (../../selection-condition)' {
              error-message "Incompatible with 'if configured without selection condition'";
            }
            status deprecated;
          }
          leaf override {
            description
              "Force imsi-based selection of charging characteristics";
            type empty;
            status deprecated;
            must 'not (../../selection-condition)' {
              error-message "Incompatible with 'if configured without selection condition'";
            }
          }
        }
        status deprecated;
      }
      list selection-condition {
        key "name";
        ordered-by user;
        uses apn-selection-condition-type;
      }
      list lzone-based-apn {
        description
          "APN Selection Setting based on GTP PE for lzone";
        key "name";
        leaf name {
          description
            "LTE Zone Information Index (Lzone site id 1 and 2 are reserved for internal use so cannot be used for APN selection)";
          type uint16 {
            range "3..65535" {
              error-message "Invalid value for attribute 'lzone-index'. Valid values are in range:[3,65535]";
            }
          }
        }
        leaf selected-apn {
          description
            "Selected APN mapped to this APN";
          type leafref {
            path "/epg/pgw/apn/name";
          }
          mandatory true;
        }
      }
      list wzone-based-apn {
        description
          "APN Selection Setting based on GTP PE for wzone";
        max-elements 100;
        key "name";
        leaf name {
          description
            "WCDMA Zone Information Index";
          type uint16 {
            range "1..65535" {
              error-message "Invalid value for attribute 'zone-index'. Valid values are in range:[1,65535]";
            }
          }
        }
        leaf zone {
          description
            "WCDMA Zone location setting";
          type enumeration {
            enum in-zone {
              description
                "Inside of the WCDMA Zone";
            }
            enum out-zone {
              description
                "Outside of the WCDMA Zone";
            }
          }
          mandatory true;
        }
        leaf rat-type {
          description
            "Radio access technology (RAT)";
          type common-rat-type;
        }
        leaf sgsn-address {
          description
            "SGSN address or address prefix";
          type eipv4-prefix-optional;
        }
        leaf selected-apn {
          description
            "Selected APN mapped to this APN";
          type leafref {
            path "/epg/pgw/apn/name";
          }
          mandatory true;
        }
      }
    }
  }

  grouping sgsn-type {
    leaf name {
      description
        "SGSN IPv4 or IPv6 address with optional prefix";
      type eip-prefix-optional;
    }
    leaf home-plmn {
      description
        "SGSN is within the home PLMN";
      type empty;
    }
    container pdp-context {
      description
        "PDP context settings";
      leaf creation {
        description
          "PDP context creation state";
        type enumeration {
          enum unblocked {
            description
              "No restrictions on PDP context creation";
          }
          enum blocked {
            description
              "New PDP context creation fully blocked";
          }
        }
      }
    }
    container gtp {
      description
        "GTP configuration";
      leaf no-path-management {
        description
          "SGSN does not support GTP path management";
        type empty;
      }
    }
  }

  grouping rating-group-type {
    leaf description {
      description
        "Free format description";
      type string;
    }
    leaf mscc-profile {
      description
        "MSCC handling profile to use for this rating group";
      type leafref {
        path "/epg/pgw/credit-control/mscc-profile/name";
      }
    }
    leaf quota-holding-time {
      description
        "Quota holding time in seconds of inactivity after which to report the quota";
      type uint32 {
        range "5..4294967295" {
          error-message "Invalid value for attribute 'quota-holding-time'. Valid values are in range:[5,4294967295]";
        }
      }
    }
    leaf user-denied-time {
      description
        "Time in seconds of denied access after quota termination before quota request is allowed";
      type uint32 {
        range "5..86400" {
          error-message "Invalid value for attribute 'user-denied-time'. Valid values are in range:[5,86400]";
        }
      }
    }
    leaf volume-quota-threshold {
      description
        "Default volume quota threshold in percentage of granted volume quota";
      type uint8 {
        range "5..25" {
          error-message "Invalid value for attribute 'volume-quota-threshold'. Valid values are in range:[5,25]";
        }
      }
    }
    leaf time-quota-threshold {
      description
        "Default time quota threshold in percentage of granted time quota";
      type uint8 {
        range "5..25" {
          error-message "Invalid value for attribute 'time-quota-threshold'. Valid values are in range:[5,25]";
        }
      }
    }
    container re-authorization-triggers {
      description
        "Credit re-authorization trigger settings";
      uses rating-group-reauthorization-triggers-type;
    }
    container n40-chargeable-event-triggers {
      status current {
        yexte:preliminary;
      }
      description
        "Support the event triggers configuration for rating group level on N40 interface";
      uses n40-chargeable-event-triggers-type;
    }
    container requested-service-unit {
      description
        "Default requested quota type and amount";
      leaf total-volume {
        description
          "Requested total volume quota in bytes";
        type uint64;
      }
      leaf uplink-volume {
        description
          "Requested uplink volume quota in bytes";
        type uint64;
        must 'not (../total-volume)' {
          error-message "incompatible with 'total-volume'";
        }
      }
      leaf downlink-volume {
        description
          "Requested downlink volume quota in bytes";
        type uint64;
        must 'not (../total-volume)' {
          error-message "incompatible with 'total-volume'";
        }
      }
      leaf time {
        description
          "Requested time quota in seconds";
        type uint32;
      }
    }
    container time-based-measurement {
      description
        "The applicable measurement mechanisms";
      container continuous-time {
        description
          "Continuous time measurement";
        presence "Continuous time measurement without inactivity detection time";
        leaf inactivity-detection-time {
          description
            "Continuous time measurement using an inactivity detection time";
          type uint32 {
            range "1..86400" {
              error-message "Invalid value for attribute 'inactivity-detection-time'. Valid values are in range:[1,86400]";
            }
          }
        }
      }
      container continuous-time-period {
        description
          "Continuous time measurement using a base time interval";
        leaf base-time-interval {
          description
            "Base time interval";
          type uint32 {
            range "1..86400" {
              error-message "Invalid value for attribute 'base-time-interval'. Valid values are in range:[1,86400]";
            }
          }
        }
      }
      container discrete-time-period {
        description
          "Discrete time measurement";
        leaf base-time-interval {
          description
            "Base time interval";
          type uint32 {
            range "1..86400" {
              error-message "Invalid value for attribute 'base-time-interval'. Valid values are in range:[1,86400]";
            }
          }
        }
      }
    }
  }

  grouping pgw-type {
    leaf node {
      description
        "Identifier for PGW node, it must not be equal to 1";
      type string {
        pattern '[A-Za-z2-9]|[.A-Za-z0-9_-]{2,32}' {
          error-message "Node identifier is a string consisting of up to 32 letters, numbers, hyphens, periods, underscores and it must not be equal to 1";
        }
      }
      mandatory true;
    }
    leaf pco-gateway-address {
      description
        "PCO gateway address";
      type enumeration {
        enum apn-gateway-address {
          description
            "Include gateway address in PCO message";
        }
        enum end-user-address {
          description
            "Include end user address in PCO message";
        }
      }
    }
    leaf gngp-default-rat-type {
      description
        "GN/GP default radio access technology (RAT)";
      type enumeration {
        enum keep-value {
          description
            "Keep and use stored RAT type";
        }
        enum geran {
          description
            "GSM/EDGE radio access network";
        }
        enum utran {
          description
            "WCDMA/UMTS terrestrial radio access network";
        }
        enum gan {
          description
            "Generic access network";
        }
      }
      default "keep-value";
    }
    leaf pause-charging-enabled {
      description
        "Enables Pause Charging support in S5/S8 interfaces";
      type empty;
    }
    leaf ni-oi-apn-selection-enabled {
      description
        "Enables NI OI based APN selection";
      type empty;
    }
    container stop {
      yexte:user-group "ericsson-support,epg-admin";
      description
        "Stop the PGW service";
      must '/epg/pgw/stop/node' {
        error-message "When configuring [epg pgw stop], 'node' must be configured";
        tailf:dependency "/epg/pgw/stop/node";
      }
      presence "stop need presence";
      leaf node {
        description
          "Stop on node level";
        type empty;
      }
    }
    list shared-ip-pool {
      max-elements 4000;
      key "name";
      uses sharedippool-type;
    }
    list p-cscf-ip-pool {
      max-elements 3000;
      key "name";
      uses pcscfippool-type;
    }
    list apn {
      max-elements 3000;
      key "name";
      uses apn-type;
    }
    container location {
      description
        "Location area";
      list area {
        max-elements 3000;
        key "name";
        uses locationarea-type;
      }
    }
    container rate-control {
      description
        "Rate control configuration";
      leaf serving-plmn-downlink-rate-control {
        description
          "Enable serving plmn downlink rate control";
        type empty;
      }
    }
    container charging {
      description
        "Charging and CDR configuration";
      uses charging-type;
    }
    container dhcp {
      description
        "DHCP settings";
      list server {
        max-elements 9999;
        key "name";
        uses dhcp-shared-type;
      }
      leaf no-hyphen-in-client-id {
        description
          "Remove hyphens from DHCP client id";
        type empty;
      }
      action statistics {
        description
          "Name of DHCP server";
        input {
          leaf server {
            description
              "Name of DHCP server";
            type string {
              pattern '[.0-9A-Za-z_-]*' {
                error-message "ERROR: Invalid value for parameter server. Valid values are strings in a specified format. Type: server? for more information on the format to use.";
              }
              length "1..64";
            }
            mandatory true;
          }
        }
        output {
          leaf result {
            type string;
            mandatory true;
          }
        }
      }
    }
    container user-plane {
      description
        "User plane settings";
      uses pgw-user-plane-type;
    }
    container user-plane-pool {
      description
        "User Plane pool";
      uses user-plane-pool-type;
    }
    container user-plane-selection {
      description
        "User plane selection";
      uses user-plane-selection-type;
      must '/epg/pgw/interface/sx' {
        error-message "Sx interface must be configured under [epg pgw interface sx].";
      }
    }
    container control-plane {
      description
        "Control plane settings";
      container session {
        description
          "Session settings";
        container block {
          yexte:user-group "ericsson-support,epg-admin";
          description
            "New sessions blocked";
          presence "block need presence";
          uses cp-block-allocation-type;
        }
        action terminate {
          yexte:user-group "ericsson-support,epg-admin";
          description
            "Terminate existing EPS sessions";
          output {
            leaf result {
              type string;
              mandatory true;
            }
          }
        }
        action terminate-stop {
          yexte:user-group "ericsson-support,epg-admin";
          description
            "Stop EPS session deletion process";
          output {
            leaf result {
              type string;
              mandatory true;
            }
          }
        }
        action terminate-imsi {
          yexte:user-group "ericsson-support,epg-admin";
          description
            "Identifier for International Mobile Subscriber Identity";
          input {
            leaf imsi {
              description
                "Identifier for International Mobile Subscriber Identity";
              type string {
                pattern '([0-9]{5,15})|([0-9]{1,14}\*)' {
                  error-message "ERROR: Invalid value for parameter imsi. Valid values are strings in a specified format. Type: imsi? for more information on the format to use.";
                }
                length "2..15";
              }
              mandatory true;
            }
            leaf delete-option {
              description
                "delete option";
              type enumeration {
                enum default-only {
                  description
                    "Delete session with default bearer only";
                }
                enum bearer-released {
                  description
                    "Delete session on last dedicated bearer release";
                }
              }
            }
          }
          output {
            leaf result {
              type string;
              mandatory true;
            }
          }
        }
        action terminate-shared-ip-pool {
          yexte:user-group "ericsson-support,epg-admin";
          description
            "Name of shared ip pool";
          input {
            leaf pool-name {
              description
                "Name of shared ip pool";
              type string {
                pattern '[.0-9A-Za-z_-]*' {
                  error-message "Must contain only letters, numbers, underscores or dashes";
                }
                length "1..64";
              }
              mandatory true;
            }
            leaf delete-option {
              description
                "delete option";
              type enumeration {
                enum default-only {
                  description
                    "Delete session with default bearer only";
                }
                enum bearer-released {
                  description
                    "Delete session on last dedicated bearer release";
                }
              }
            }
          }
          output {
            leaf result {
              type string;
              mandatory true;
            }
          }
        }
        action terminate-sessions-on-serving-node {
          yexte:user-group "ericsson-support,epg-admin";
          description
            "Terminate sessions on serving node";
          input {
            leaf serving-node-address {
              description
                "IP address of serving node";
              type inet:ip-address;
              mandatory true;
            }
            leaf delete-option {
              description
                "delete option";
              type enumeration {
                enum default-only {
                  description
                    "Delete session with default bearer only";
                }
                enum bearer-released {
                  description
                    "Delete session on last dedicated bearer release";
                }
              }
            }
          }
          output {
            leaf result {
              type string;
              mandatory true;
            }
          }
        }
        action terminate-sessions-on-user-plane {
          yexte:user-group "ericsson-support,epg-admin";
          description
            "Terminate sessions on user plane";
          input {
            leaf userplane-address {
              description
                "IP address of user plane ";
              type inet:ip-address;
              mandatory true;
            }
            leaf delete-option {
              description
                "delete option";
              type enumeration {
                enum default-only {
                  description
                    "Delete session with default bearer only";
                }
                enum bearer-released {
                  description
                    "Delete session on last dedicated bearer release";
                }
              }
            }
          }
          output {
            leaf result {
              type string;
              mandatory true;
            }
          }
        }
        action terminate-sessions-on-pcscf {
          yexte:user-group "ericsson-support,epg-admin";
          description
            "Terminate sessions on p-cscf node";
          input {
            leaf pcscf-address {
              description
                "IP address of p-cscf node";
              type inet:ip-address;
              mandatory true;
            }
            leaf delete-option {
              description
                "delete option";
              type enumeration {
                enum default-only {
                  description
                    "Delete session with default bearer only";
                }
                enum bearer-released {
                  description
                    "Delete session on last dedicated bearer release";
                }
              }
            }
          }
          output {
            leaf result {
              type string;
              mandatory true;
            }
          }
        }
        action terminate-failed-policy-control {
          yexte:user-group "ericsson-support,epg-admin";
          description
            "Terminate sessions with the failed policy control";
          input {
            leaf diameter-session-state {
              type enumeration {
                enum temporary-offline {
                  description
                    "Diameter session state is temporarily offline";
                }
                enum permanent-offline {
                  description
                    "Diameter session state is permanently offline";
                }
              }
            }
          }
          output {
            leaf result {
              type string;
              mandatory true;
            }
          }
        }
        action terminate-failed-credit-control {
          yexte:user-group "ericsson-support,epg-admin";
          description
            "Terminate sessions with the failed credit control";
          input {
            leaf diameter-session-state {
              type enumeration {
                enum temporary-offline {
                  description
                    "Diameter session state is temporarily offline";
                }
                enum permanent-offline {
                  description
                    "Diameter session state is permanently offline";
                }
              }
            }
          }
          output {
            leaf result {
              type string;
              mandatory true;
            }
          }
        }
        action terminate-sessions {
          yexte:user-group "ericsson-support,epg-admin";
          description
            "Terminate sessions on diameter host";
          input {
            leaf diameter-host-option {
              description
                "Option for diameter host type";
              type enumeration {
                enum diameter-destination-host {
                  description
                    "Diameter destination host";
                }
                enum diameter-origin-host {
                  description
                    "Diameter origin host";
                }
              }
              mandatory true;
            }
            leaf diameter-host-name {
              description
                "Name of diameter host";
              type string {
                pattern '[.0-9A-Za-z_-]*' {
                  error-message "Must contain only letters, numbers, underscores or dashes";
                }
                length "1..64";
              }
              mandatory true;
            }
            leaf application-type {
              description
                "Type for diameter application";
              type enumeration {
                enum gx {
                  description
                    "Diameter Application Id (gx|pcc)";
                }
                enum gy {
                  description
                    "Diameter Application Id (ro|gy-3gpp)";
                }
                enum s6b {
                  description
                    "Diameter Application Id (s6b)";
                }
                enum rf {
                  description
                    "Diameter Application Id (rf)";
                }
                enum all {
                  description
                    "Diameter Application Id (*)";
                }
              }
              mandatory true;
            }
            leaf delete-option {
              description
                "delete option";
              type enumeration {
                enum default-only {
                  description
                    "Delete session with default bearer only";
                }
                enum bearer-released {
                  description
                    "Delete session on last dedicated bearer release";
                }
              }
            }
          }
          output {
            leaf result {
              type string;
              mandatory true;
            }
          }
        }
        action terminate-idle-session-start {
          yexte:user-group "ericsson-support,epg-admin";
          description
            "Start idle session deletion process";
          input {
            leaf idle-monitor-timer {
              description
                "The idleMonitorTimer is defined as the maximum time in seconds for which a session is allowed with no uplink payload";
              type uint16 {
                range "1..65535" {
                  error-message "Invalid value for attribute 'idle-monitor-timer'. Valid values are in range:[1,65535]";
                }
              }
              mandatory true;
            }
            leaf terminate-condition {
              type enumeration {
                enum imsi {
                  description
                    "Terminate idle session by IMSI or IMSI prefix";
                }
                enum shared-ip-pool {
                  description
                    "Terminate idle session by Shared IP Pool";
                }
                enum serving-node {
                  description
                    "Terminate idle session by Serving Node IP address";
                }
                enum pcscf {
                  description
                    "Terminate idle session by p-cscf IP address";
                }
                enum diameter-destination-host {
                  description
                    "Terminate idle session by Diameter destination-host name";
                }
                enum failed-policy-control {
                  description
                    "Terminate idle session with failed policy control";
                }
                enum failed-credit-control {
                  description
                    "Terminate idle session with failed credit control";
                }
              }
            }
            leaf terminate-parameter {
              description
                "IMSI or IMSI prefix, shared IP pool name, serving node IP, p-cscf IP, diameter host name, temporary-offline or permanent-offline";
              type string {
                pattern '([0-9]{5,15})|([0-9]{1,14}\*)|([._0-9A-Za-z-]{1,121})|((((25[0-5]|2[0-4][0-9]|[01]?[0-9][0-9]?).(25[0-5]|2[0-4][0-9]|[01]?[0-9][0-9]?).(25[0-5]|2[0-4][0-9]|[01]?[0-9][0-9]?).(25[0-5]|2[0-4][0-9]|[01]?[0-9][0-9]?))|(((([A-Fa-f0-9]{1,4}:){7}([A-Fa-f0-9]{1,4}|:))|(([A-Fa-f0-9]{1,4}:){6}(:[A-Fa-f0-9]{1,4}|((25[0-5]|2[0-4][0-9]|1[0-9][0-9]|[1-9]?[0-9])(.(25[0-5]|2[0-4][0-9]|1[0-9][0-9]|[1-9]?[0-9])){3})|:))|(([A-Fa-f0-9]{1,4}:){5}(((:[A-Fa-f0-9]{1,4}){1,2})|:((25[0-5]|2[0-4][0-9]|1[0-9][0-9]|[1-9]?[0-9])(.(25[0-5]|2[0-4][0-9]|1[0-9][0-9]|[1-9]?[0-9])){3})|:))|(([A-Fa-f0-9]{1,4}:){4}(((:[A-Fa-f0-9]{1,4}){1,3})|((:[A-Fa-f0-9]{1,4})?:((25[0-5]|2[0-4][0-9]|1[0-9][0-9]|[1-9]?[0-9])(.(25[0-5]|2[0-4][0-9]|1[0-9][0-9]|[1-9]?[0-9])){3}))|:))|(([A-Fa-f0-9]{1,4}:){3}(((:[A-Fa-f0-9]{1,4}){1,4})|((:[A-Fa-f0-9]{1,4}){0,2}:((25[0-5]|2[0-4][0-9]|1[0-9][0-9]|[1-9]?[0-9])(.(25[0-5]|2[0-4][0-9]|1[0-9][0-9]|[1-9]?[0-9])){3}))|:))|(([A-Fa-f0-9]{1,4}:){2}(((:[A-Fa-f0-9]{1,4}){1,5})|((:[A-Fa-f0-9]{1,4}){0,3}:((25[0-5]|2[0-4][0-9]|1[0-9][0-9]|[1-9]?[0-9])(.(25[0-5]|2[0-4][0-9]|1[0-9][0-9]|[1-9]?[0-9])){3}))|:))|(([A-Fa-f0-9]{1,4}:)(((:[A-Fa-f0-9]{1,4}){1,6})|((:[A-Fa-f0-9]{1,4}){0,4}:((25[0-5]|2[0-4][0-9]|1[0-9][0-9]|[1-9]?[0-9])(.(25[0-5]|2[0-4][0-9]|1[0-9][0-9]|[1-9]?[0-9])){3}))|:))|(:(((:[A-Fa-f0-9]{1,4}){1,7})|((:[A-Fa-f0-9]{1,4}){0,5}:((25[0-5]|2[0-4][0-9]|1[0-9][0-9]|[1-9]?[0-9])(.(25[0-5]|2[0-4][0-9]|1[0-9][0-9]|[1-9]?[0-9])){3}))|:))))))|([.0-9A-Za-z_-]*)' {
                  error-message "ERROR: Invalid value for parameter terminate-parameter. Valid values are strings in a specified format. Type: terminate-parameter? for more information on the format to use.";
                }
              }
            }
            leaf application-type {
              description
                "Type for diameter application";
              type enumeration {
                enum gx {
                  description
                    "Diameter Application Id (gx|pcc)";
                }
                enum gy {
                  description
                    "Diameter Application Id (ro|gy-3gpp)";
                }
                enum s6b {
                  description
                    "Diameter Application Id (s6b)";
                }
                enum rf {
                  description
                    "Diameter Application Id (rf)";
                }
                enum all {
                  description
                    "Diameter Application Id (*)";
                }
              }
            }
          }
          output {
            leaf result {
              type string;
              mandatory true;
            }
          }
        }
        action terminate-idle-session-stop {
          yexte:user-group "ericsson-support,epg-admin";
          description
            "Stop idle session deletion process";
          input {
            leaf terminate-condition {
              type enumeration {
                enum imsi {
                  description
                    "Terminate idle session by IMSI or IMSI prefix";
                }
                enum shared-ip-pool {
                  description
                    "Terminate idle session by Shared IP Pool";
                }
                enum serving-node {
                  description
                    "Terminate idle session by Serving Node IP address";
                }
                enum pcscf {
                  description
                    "Terminate idle session by p-cscf IP address";
                }
                enum diameter-destination-host {
                  description
                    "Terminate idle session by Diameter destination-host name";
                }
                enum failed-policy-control {
                  description
                    "Terminate idle session with failed policy control";
                }
                enum failed-credit-control {
                  description
                    "Terminate idle session with failed credit control";
                }
              }
            }
            leaf terminate-parameter {
              description
                "IMSI or IMSI prefix, shared IP pool name, serving node IP, p-cscf IP, diameter host name, temporary-offline or permanent-offline";
              type string {
                pattern '([0-9]{5,15})|([0-9]{1,14}\*)|([._0-9A-Za-z-]{1,121})|((((25[0-5]|2[0-4][0-9]|[01]?[0-9][0-9]?).(25[0-5]|2[0-4][0-9]|[01]?[0-9][0-9]?).(25[0-5]|2[0-4][0-9]|[01]?[0-9][0-9]?).(25[0-5]|2[0-4][0-9]|[01]?[0-9][0-9]?))|(((([A-Fa-f0-9]{1,4}:){7}([A-Fa-f0-9]{1,4}|:))|(([A-Fa-f0-9]{1,4}:){6}(:[A-Fa-f0-9]{1,4}|((25[0-5]|2[0-4][0-9]|1[0-9][0-9]|[1-9]?[0-9])(.(25[0-5]|2[0-4][0-9]|1[0-9][0-9]|[1-9]?[0-9])){3})|:))|(([A-Fa-f0-9]{1,4}:){5}(((:[A-Fa-f0-9]{1,4}){1,2})|:((25[0-5]|2[0-4][0-9]|1[0-9][0-9]|[1-9]?[0-9])(.(25[0-5]|2[0-4][0-9]|1[0-9][0-9]|[1-9]?[0-9])){3})|:))|(([A-Fa-f0-9]{1,4}:){4}(((:[A-Fa-f0-9]{1,4}){1,3})|((:[A-Fa-f0-9]{1,4})?:((25[0-5]|2[0-4][0-9]|1[0-9][0-9]|[1-9]?[0-9])(.(25[0-5]|2[0-4][0-9]|1[0-9][0-9]|[1-9]?[0-9])){3}))|:))|(([A-Fa-f0-9]{1,4}:){3}(((:[A-Fa-f0-9]{1,4}){1,4})|((:[A-Fa-f0-9]{1,4}){0,2}:((25[0-5]|2[0-4][0-9]|1[0-9][0-9]|[1-9]?[0-9])(.(25[0-5]|2[0-4][0-9]|1[0-9][0-9]|[1-9]?[0-9])){3}))|:))|(([A-Fa-f0-9]{1,4}:){2}(((:[A-Fa-f0-9]{1,4}){1,5})|((:[A-Fa-f0-9]{1,4}){0,3}:((25[0-5]|2[0-4][0-9]|1[0-9][0-9]|[1-9]?[0-9])(.(25[0-5]|2[0-4][0-9]|1[0-9][0-9]|[1-9]?[0-9])){3}))|:))|(([A-Fa-f0-9]{1,4}:)(((:[A-Fa-f0-9]{1,4}){1,6})|((:[A-Fa-f0-9]{1,4}){0,4}:((25[0-5]|2[0-4][0-9]|1[0-9][0-9]|[1-9]?[0-9])(.(25[0-5]|2[0-4][0-9]|1[0-9][0-9]|[1-9]?[0-9])){3}))|:))|(:(((:[A-Fa-f0-9]{1,4}){1,7})|((:[A-Fa-f0-9]{1,4}){0,5}:((25[0-5]|2[0-4][0-9]|1[0-9][0-9]|[1-9]?[0-9])(.(25[0-5]|2[0-4][0-9]|1[0-9][0-9]|[1-9]?[0-9])){3}))|:))))))|([.0-9A-Za-z_-]*)' {
                  error-message "ERROR: Invalid value for parameter terminate-parameter. Valid values are strings in a specified format. Type: terminate-parameter? for more information on the format to use.";
                }
              }
            }
            leaf application-type {
              description
                "Type for diameter application";
              type enumeration {
                enum gx {
                  description
                    "Diameter Application Id (gx|pcc)";
                }
                enum gy {
                  description
                    "Diameter Application Id (ro|gy-3gpp)";
                }
                enum s6b {
                  description
                    "Diameter Application Id (s6b)";
                }
                enum rf {
                  description
                    "Diameter Application Id (rf)";
                }
                enum all {
                  description
                    "Diameter Application Id (*)";
                }
              }
            }
          }
          output {
            leaf result {
              type string;
              mandatory true;
            }
          }
        }
        action terminate-idle-session-show {
          description
            "Show idle session deletion process";
          input {
            leaf terminate-condition {
              type enumeration {
                enum imsi {
                  description
                    "Terminate idle session by IMSI prefix";
                }
                enum shared-ip-pool {
                  description
                    "Terminate idle session by Shared IP Pool";
                }
                enum serving-node {
                  description
                    "Terminate idle session by Serving Node IP address";
                }
                enum pcscf {
                  description
                    "Terminate idle session by p-cscf IP address";
                }
                enum diameter-destination-host {
                  description
                    "Terminate idle session by Diameter destination-host name";
                }
                enum failed-policy-control {
                  description
                    "Terminate idle session with failed policy control";
                }
                enum failed-credit-control {
                  description
                    "Terminate idle session with failed credit control";
                }
              }
            }
            leaf application-type {
              description
                "Type for diameter application";
              type enumeration {
                enum gx {
                  description
                    "Diameter Application Id (gx|pcc)";
                }
                enum gy {
                  description
                    "Diameter Application Id (ro|gy-3gpp)";
                }
                enum s6b {
                  description
                    "Diameter Application Id (s6b)";
                }
                enum rf {
                  description
                    "Diameter Application Id (rf)";
                }
                enum all {
                  description
                    "Diameter Application Id (*)";
                }
              }
            }
          }
          output {
            leaf result {
              type string;
              mandatory true;
            }
          }
        }
        leaf-list no-idle-termination-qci {
          description
            "Session with bearers having configured qciValue should not be terminated during idle session deletion process\\. If nothing configured, 1, 65, 66, 67, 69 are the default values.";
          type uint8 {
            range "1..254" {
              error-message "Invalid value for attribute 'no-idle-termination-qci'. Valid values are in range:[1,254]";
            }
          }
        }
      }
      container signaling {
        description
          "PGW signaling setting";
        container preservation-information {
          description
            "Enable sending RADIUS accounting start or stop message upon UE status change";
          presence "preservation-information need presence";
        }
        action gtp-restart-counter {
          description
            "Show PGW GTP restart counter.";
          output {
            leaf result {
              type string;
              mandatory true;
            }
          }
        }
        action set-gtp-restart-counter {
          description
            "Set PGW GTP restart counter\\. SGW has to be stopped and started before changes take effect\\. The restart will add one (1) to the count.";
          input {
            leaf count {
              description
                "Set PGW GTP restart counter\\. PGW has to be stopped and started before changes take effect\\. The restart will add one (1) to the count.";
              type uint8 {
                range "0..255" {
                  error-message "Invalid value for attribute 'count'. Valid values are in range:[0,255]";
                }
              }
              mandatory true;
            }
          }
          output {
            leaf result {
              type string;
              mandatory true;
            }
          }
        }
        action origin-state-id {
          description
            "Show PGW origin-state id.";
          output {
            leaf result {
              type string;
              mandatory true;
            }
          }
        }
        action set-origin-state-id {
          description
            "Set PGW origin-state id\\. PGW has to be stopped and started before changes take effect\\. The restart will add one (1) to the count.";
          input {
            leaf count {
              description
                "Set origin-state-id\\. PGW has to be stopped and started before changes take effect\\. The restart will add one (1) to the count.";
              type uint32 {
                range "0..4294967295" {
                  error-message "Invalid value for attribute 'count'. Valid values are in range:[0,4294967295]";
                }
              }
              mandatory true;
            }
          }
          output {
            leaf result {
              type string;
              mandatory true;
            }
          }
        }
      }
      action fallback-prepare {
        yexte:user-group "ericsson-support,epg-admin";
        description
          "Prepare for fallback";
        input {
          leaf release {
            description
              "Release";
            type enumeration {
              enum 13a {
                description
                  "Prepare for fallback to 13A";
              }
              enum 13b {
                description
                  "Prepare for fallback to 13B";
              }
              enum none {
                description
                  "Cancel any previous fallback preparation";
              }
            }
            mandatory true;
          }
        }
        output {
          leaf result {
            type string;
            mandatory true;
          }
        }
      }
    }
    container interface {
      description
        "Interface settings";
      uses pgw-interface-type;
    }
    container address-reuse {
      description
        "Address reuse configuration";
      leaf address-reuse-failed-quarantine {
        description
          "Quarantine ip addresses before reuse at pdp-creation failure";
        type empty;
      }
      leaf no-address-release-on-exhausted-ppb {
        description
          "Quarantine addresses before reusing them when PPB is overloaded";
        type empty;
      }
      leaf gsc-recovery-create-quarantine {
        description
          "Block create PDP context at GSC recovery or failover";
        type empty;
      }
      leaf gsc-recovery-quarantine-time {
        description
          "Time in seconds for which PDP context creation and EPS session creation requests shall be blocked after GSC has started up";
        type uint16 {
          range "1..1800" {
            error-message "Invalid value for attribute 'gsc-recovery-quarantine-time'. Valid values are in range:[1,1800]";
          }
        }
      }
    }
    container ipv6-router-advertisement {
      description
        "IPv6 router advertisement parameters";
      uses ipv6-router-advertisement-type;
    }
    list logical-apn {
      must '/epg/pgw/logical-apn[name=current()/name]/apn' {
        error-message "apn is mandatory";
      }
      max-elements 2000;
      key "name";
      uses logapn-type;
    }
    choice ggsn-mcc-plmn {
      leaf ggsn-plmn-id {
        description
          "Public land mobile network identifier";
        type string {
          pattern '[0-9]{5,6}' {
            error-message "PLMN identifier is a string of 5 or 6 digits";
          }
        }
      }
    }
    list plmn {
      key "name";
      uses plmn-type;
    }
    container pdp-context {
      description
        "PDP context settings";
      uses pdp-context-type;
    }
    container radius {
      description
        "RADIUS settings";
      list server {
        max-elements 9999;
        key "name";
        uses radius-shared-type;
      }
      list server-profile {
        max-elements 9999;
        must './authentication/server-address or ./accounting/server-address' {
          error-message "At least one server must be configured";
        }
        key "name";
        leaf name {
          description
            "Name of server profile";
          type string {
            pattern '[.0-9A-Za-z_-]*' {
              error-message "Must contain only letters, numbers, underscores or dashes";
            }
            length "1..64";
          }
        }
        container accounting {
          description
            "Accounting servers";
          list server-address {
            max-elements 9999;
            key "name";
            uses radius-type-accounting-object;
          }
        }
        container authentication {
          description
            "Authentication servers";
          list server-address {
            max-elements 9999;
            key "name";
            uses radius-type;
          }
        }
      }
      list property-profile {
        max-elements 9999;
        key "name";
        leaf name {
          description
            "Name of server profile";
          type string {
            pattern '[.0-9A-Za-z_-]*' {
              error-message "Must contain only letters, numbers, underscores or dashes";
            }
            length "1..64";
          }
          must ". != 'defaultPropertyProfile'" {
            error-message "name shouldn't conflict with defaultPropertyProfile name new on";
          }
        }
        uses radius-common-properties;
        container authentication {
          description
            "RADIUS authentication settings";
          presence "authentication need presence";
          list custom-attribute {
            key "name";
            leaf name {
              description
                "Custom attribute identifier";
              type string {
                length "1..64";
              }
            }
            leaf type {
              description
                "Radius attribute type";
              type uint8;
              must
                "(../type = '26' and ../vendor-id and ../vendor-type) or
                 (../type != '26' and (not (../vendor-id)) and (not (../vendor-type)))" {
                error-message "vendor-id and vendor-type is reqiured for type 26";
              }
            }
            leaf vendor-id {
              description
                "Vendor ID for Vendor specific attribute";
              type uint32;
              tailf:display-when "../type = '26'";
            }
            leaf vendor-type {
              description
                "Type for Vendor specific attribute";
              type uint8;
              tailf:display-when "../type = '26'";
            }
          }
          container ericsson-primary-rulespace-name {
            description
              "Settings for ericsson-primary-rulespace-name";
            leaf custom-attribute {
              description
                "Name of ericsson-primary-rulespace-name custom attribute";
              type string {
                length "1..64";
              }
            }
          }
          leaf wpp-compatible-encoding {
            description
              "Encode RADIUS attributes in a format compatible with WPP GGSN";
            type empty;
          }
          container message-attributes {
            description
              "Attributes in RADIUS messages";
            presence "message-attributes need presence";
            uses radius-authentication-message-attributes-type;
          }
          leaf use-domain-name {
            description
              "Use domain name as username in access request";
            type empty;
          }
          leaf user-name {
            description
              "User name for user authentication towards RADIUS";
            type enumeration {
              enum imsi {
                description
                  "Use IMSI as username";
              }
              enum imsi-at-apn {
                description
                  "Use IMSI@APN as username";
              }
              enum msisdn {
                description
                  "Use MSISDN as username";
              }
              enum msisdn-at-apn {
                description
                  "Use MSISDN@APN as username";
              }
            }
          }
        }
        container accounting {
          description
            "RADIUS accounting settings";
          presence "accounting need presence";
          uses radius-accounting-properties-type;
          container message-attributes {
            description
              "Attributes in RADIUS messages";
            presence "message-attributes need presence";
            uses radius-accounting-message-attributes-type;
          }
        }
      }
      leaf ignore-source-address {
        description
          "Ignore RADIUS source address";
        type empty;
      }
      leaf dscp {
        description
          "DSCP (DiffServ Code Point) for Radius packets";
        type enumeration {
          enum af11 {
            description
              "Assured forwarding class 1, low drop precedence";
          }
          enum af12 {
            description
              "Assured forwarding class 1, medium drop precedence";
          }
          enum af13 {
            description
              "Assured forwarding class 1, high drop precedence";
          }
          enum af21 {
            description
              "Assured forwarding class 2, low drop precedence";
          }
          enum af22 {
            description
              "Assured forwarding class 2, medium drop precedence";
          }
          enum af23 {
            description
              "Assured forwarding class 2, high drop precedence";
          }
          enum af31 {
            description
              "Assured forwarding class 3, low drop precedence";
          }
          enum af32 {
            description
              "Assured forwarding class 3, medium drop precedence";
          }
          enum af33 {
            description
              "Assured forwarding class 3, high drop precedence";
          }
          enum af41 {
            description
              "Assured forwarding class 4, low drop precedence";
          }
          enum af42 {
            description
              "Assured forwarding class 4, medium drop precedence";
          }
          enum af43 {
            description
              "Assured forwarding class 4, high drop precedence";
          }
          enum ef {
            description
              "Expedited forwarding";
          }
          enum be {
            description
              "Best effort forwarding";
          }
          enum cs1 {
            description
              "Class selector 1";
          }
          enum cs2 {
            description
              "Class selector 2";
          }
          enum cs3 {
            description
              "Class selector 3";
          }
          enum cs4 {
            description
              "Class selector 4";
          }
          enum cs5 {
            description
              "Class selector 5";
          }
          enum cs6 {
            description
              "Class selector 6";
          }
          enum cs7 {
            description
              "Class selector 7";
          }
        }
      }
    }
    container aaa {
      presence "aaa need presence";
      description
        "AAA settings";
      uses aaa-node-type;
    }
    container dhcpv6 {
      presence "dhcpv6 need presence";
      description
        "Dhcpv6 settings";
      uses dhcpv6-type;
    }
    container policy-control {
      description
        "Policy control settings";
      uses policy-control-type;
    }
    container packet-enforcement {
      description
        "Packet enforcement settings";
      container service-chaining {
        description
          "Service chaining settings";
        list profile {
          description
            "Service chaining profile";
          key "name";
          uses service-chaining-profile-type;
        }
      }
      container content-enrichment {
        description
          "Content enrichment settings";
        container parameter {
          description
            "Parameter settings";
          list rat-type {
            description
              "RAT type identifier";
            key "value";
            leaf value {
              description
                "RAT type identifier e.g. utran, geran, wlan, gan, hspa, eutran, nb-iot, ehrpd and hrpd";
              type common-rat-type-extend;
            }
            leaf name {
              description
                "User defined name to use for RAT type.";
              type string;
              mandatory true;
            }
          }
        }
        list rule {
          description
            "Content enrichment rule";
          key "name";
          leaf name {
            description
              "Content enrichment rule identifier";
            type common-string-id;
          }
          must '(header) or (user-plane-rule)' {
            error-message "A content enrichment rule must contain a header or a user-plane-rule";
          }
          list header {
            description
              "Content enrichment header settings";
            key "name";
            leaf name {
              description
                "Content enrichment header identifier";
              type common-string-id;
            }
            choice value_or_parameter_choice {
              leaf value {
                description
                  "Content enrichment header custom value";
                type string {
                  length "1..255";
                }
              }
              container parameter {
                description
                  "Content enrichment header parameter value";
                choice parameter_choice {
                  container apn {
                    presence "Enables enrichment with APN value";
                    description
                      "APN";
                    leaf value {
                      description
                        "Select which APN value to use";
                      type enumeration {
                        enum logical {
                          description
                            "Logical APN";
                        }
                        enum requested {
                          description
                            "Requested APN";
                        }
                        enum reported {
                          description
                            "Reported APN";
                        }
                        enum used {
                          description
                            "Used APN";
                        }
                      }
                      default "used";
                    }
                  }
                  container cc {
                    presence "Enables enrichment with Charging characteristics value";
                    description
                      "Charging characteristics";
                    leaf format {
                      description
                        "Format to use";
                      type enumeration {
                        enum decimal {
                          description
                            "Decimal format";
                        }
                        enum hexadecimal {
                          description
                            "Hexadecimal format";
                        }
                      }
                      default "hexadecimal";
                    }
                  }
                  container charging-id {
                    presence "Enables enrichment with Charging id";
                    description
                      "Charging id";
                    leaf format {
                      description
                        "Format to use";
                      type enumeration {
                        enum decimal {
                          description
                            "Decimal format";
                        }
                        enum hexadecimal {
                          description
                            "Hexadecimal format";
                        }
                      }
                      default "decimal";
                    }
                  }
                  list custom-attribute {
                    description
                      "Custom attribute";
                    max-elements 1;
                    key "name";
                    leaf name {
                      description
                        "Custom attribute identifier";
                      type string {
                        length "1..64";
                      }
                    }
                  }
                  container imei {
                    presence "Enables enrichment with IMEI value";
                    description
                      "IMEI";
                  }
                  container imsi {
                    presence "Enables enrichment with IMSI value";
                    description
                      "IMSI";
                  }
                  container msisdn {
                    presence "Enables enrichment with MSISDN value";
                    description
                      "MSISDN";
                  }
                  container pgw-ip-address {
                    presence "Enables enrichment with PGW control plane IP address";
                    description
                      "PGW control plane IP address";
                  }
                  container plmn-id {
                    presence "Enables enrichment with PLMN id";
                    description
                      "Serving node PLMN id";
                  }
                  container rat-type {
                    presence "Enables enrichment with RAT type";
                    leaf format {
                      description
                        "Format to use";
                      type enumeration {
                        enum decimal {
                          description
                            "Decimal format";
                        }
                        enum name {
                          description
                            "Name format";
                        }
                      }
                      default "decimal";
                    }
                  }
                  container roaming {
                    presence "Enables enrichment with roaming status";
                    description
                      "Roaming status";
                  }
                  container serving-node-ip-address {
                    presence "Enables enrichment with serving node control plane IP address";
                    description
                      "Serving node control plane IP address";
                  }
                  container time-zone {
                    presence "Enables enrichment with time zone value";
                    description
                      "User equipment time zone";
                    leaf format {
                      description
                        "Format to use";
                      type enumeration {
                        enum binary-coded-decimal {
                          description
                            "TBCD encoded 3GPP format (ZZDS)";
                        }
                        enum signed-decimal {
                          description
                            "Signed decimal ISO format (+-HHMM)";
                        }
                      }
                      default "signed-decimal";
                    }
                  }
                  container uli {
                    presence "Enables enrichment with ULI value";
                    description
                      "User equipment ULI";
                  }
                }
              }
            }
          }
          leaf user-plane-rule {
            description
              "User plane rule";
            type string {
              length "1..255";
            }
          }
        }
      }
      container traffic-redirection {
        list rule {
          description
            "Traffic redirection rule";
          key "name";
          leaf name {
            description
              "Rule name";
            type common-string-id;
          }
          choice traffic_redirection_rule_choice {
            mandatory true;
            container http {
              leaf location {
                description
                  "HTTP redirection URL";
                type string {
                  length "1..255";
                }
              }
            }
            container destination-nat {
              leaf ipv4-address {
                description
                  "IPv4 address of the destination nat";
                type inet:ipv4-address;
              }
              leaf ipv6-address {
                description
                  "IPv6 address of the destination nat";
                type inet:ipv6-address;
              }
            }
          }
        }
      }
    }
    container credit-control {
      description
        "Credit control settings";
      list gy-profile {
        description
          "Settings for Gy";
        uses gy-profile-type;
        key "name";
      }
      list mscc-profile {
        description
          "Settings for MSCC handling";
        key "name";
        leaf name {
          description
            "Profile name";
          type common-string-id;
        }
        list action {
          key "name";
          leaf name {
            description
              "Action name";
            type common-string-id;
          }
          choice action-choice {
            mandatory true;
            container cc-not-applicable {
              description
                "Disable credit control for the rating group present in the MSCC";
              presence "Credit control is not applicable";
            }
            container success {
              description
                "Treat as an MSCC with result code 2001";
              presence "Treat as Success";
            }
            container service-denied {
              description
                "Deny access for the services associated with the rating group present in the MSCC";
              presence "Service is denied";
              leaf user-denied-time {
                description
                  "Deny access for a time period equal to the rating groups configured user-denied-timer";
                type empty;
              }
              leaf validity-time {
                description
                  "Deny access for a time period equal to the received validity timer. Has priority over 'user-denied-time'";
                type empty;
              }
              leaf traffic-redirection-rule {
                description
                  "Apply a locally configured traffic redirection rule";
                type leafref {
                  path "../../../../../packet-enforcement/traffic-redirection/rule/name";
                }
                must '../../../../../packet-enforcement/traffic-redirection/rule[name=current()]/http/location' {
                  error-message "The referenced traffic-redirection-rule must contain 'http location'";
                }
              }
              leaf used-service-unit {
                description
                  "Send a final report for the rating group with the used service units";
                type empty;
              }
            }
          }
        }
        leaf zero-granted-service-unit-action {
          description
            "Action to be taken on successful reception of granted service unit with value zero";
          type leafref {
            path "../action/name";
          }
          must '../action[name=current()]/service-denied' {
            error-message "Only an action containing service-denied is supported as a zero-granted-service-unit-action";
          }
          must 'not (../action[name=current()]/service-denied/traffic-redirection-rule)' {
            error-message "traffic-redirection-rule is not applicable for a zero-granted-service-unit-action";
          }
        }
        list condition {
          key "name";
          leaf name {
            description
              "Condition name";
            type common-string-id;
          }
          leaf priority {
            description
              "Prioriy value for the condition, where a lower value has precedence";
            type uint8 {
              range "1..128" {
                error-message "Invalid value for attribute 'priority'. Valid values are in range: [1,128]";
              }
            }
            mandatory true;
            must 'count(../../condition[priority=current()])=1' {
              error-message "Priority must be unique among all mscc-profile conditions";
            }
          }
          leaf action {
            description
              "Action to be taken for this condition";
            mandatory true;
            type leafref {
              path "../../action/name";
            }
          }
          leaf final-unit-indication {
            description
              "Condition applies when final unit indication is received";
            type empty;
          }
          leaf-list result-code {
            description
              "Result code or result code range for which the condition applies";
            type string {
              pattern '[0-9]{1,10}([-][0-9]{1,10})?' {
                error-message "Must be a result code of up to 10 digits or a range of result codes.";
              }
              length "1..64";
            }
            min-elements 1;
          }
        }
      }
      list gy-failure-profile {
        description
          "Gy failure profile";
        key "name";
        uses gy-failure-profile-type;
      }
      list gy-retention-profile {
        description
          "Specific settings for action retain";
        key "name";
        uses gy-retention-profile-type;
      }
    }
    container charging-control {
      description
        "Charging control settings";
      list rating-group-template {
        description
          "Rating group template";
        key "name";
        leaf name {
          description
            "Template name";
          type common-string-id;
        }
        uses rating-group-type;
      }
      list rule-scope {
        description
          "Charging control rule scope";
        key "name";
        leaf name {
          description
            "Rule scope name";
          type common-string-id;
        }
        list rating-group {
          description
            "Rating group";
          key "name";
          leaf name {
            description
              "Rating group identifier";
            type uint32;
          }
          uses rating-group-type;
          leaf-list template {
            description
              "Template";
            type leafref {
              path "../../../rating-group-template/name";
            }
            ordered-by user;
          }
        }
        container rating-group-default {
          description
            "Default attributes to apply for undefined rating groups";
          uses rating-group-type;
          leaf-list template {
            description
              "Template";
            type leafref {
              path "../../../rating-group-template/name";
            }
            ordered-by user;
          }
        }
      }
    }
    list policy-charging-rule-scope {
      description
        "Policy and charging rule scope settings";
      key "name";
      must '((     policy-control   and       charging-control) or
            ((not (policy-control)) and (not (charging-control))))' {
        error-message "Either both or neither of policy-control rule-scope and charging-control rule-scope must be configured";
      }
      must '((policy-control and charging-control) or not-allowed)' {
        error-message "A policy-charging-rule-scope that is allowed must have both policy-control rule-scope and charging-control rule-scope configured";
      }
      leaf name {
        description
          "Policy and charging rule scope name";
        type common-string-id;
      }
      leaf policy-control {
        description
          "Policy control rule scope";
        type leafref {
          path "../../policy-control/rule-scope/name";
        }
      }
      leaf charging-control {
        description
          "Charging control rule scope";
        type leafref {
          path "../../charging-control/rule-scope/name";
        }
      }
      leaf predefined-rule-profile {
        description
          "Reference to predefined rule profile";
        type leafref {
          path "../../user-plane/predefined-rule/profile/name";
        }
        must '((../policy-control) and (../charging-control))' {
          error-message "Both of policy-control rule-scope and charging-control rule-scope must be configured";
        }
      }
      leaf not-allowed {
        description
          "Policy charging rule scope is not allowed";
        type empty;
      }
    }
    container diameter {
      presence "diameter need presence";
      description
        "Diameter settings";
      uses diameter-node-type;
    }
    list sgsn {
      key "name";
      uses sgsn-type;
    }
    container feature-activation {
      description
        "Feature activation flags";
      leaf charging-rf {
        description
          "Enable charging Rf functionality";
        type empty;
      }
      leaf qos-based-on-service-detection {
        description
          "Enable QoS Control Based on Service Detection";
        type empty;
      }
      leaf application-detection-and-control {
        description
          "Enable Application Detection and Control";
        type empty;
      }
      leaf handle-intruding-signals {
        status current {
          yexte:preliminary;
        }
        description
          "Enable handling of Intruding Signaling within Bearer Procedures";
        type empty;
      }
      leaf direct-tunnel {
        description
          "Activate 3G direct tunnel";
        type empty;
      }
      leaf ims-based-telephony-mmtel {
        description
          "Enable IMS based telephony - MMTEL";
        type empty;
      }
      leaf usage-monitoring {
        description
          "Enable usage monitoring";
        type empty;
      }
      leaf routing-behind-ms {
        description
          "Enable routing behind MS";
        type empty;
      }
      leaf local-qos-control-with-gx {
        status current {
          yexte:preliminary;
        }
        description
          "A temporary CLI to enable local qos-control with gx without breaking backwards compatibility";
        type empty;
      }
      leaf query-pcrf-information {
        description
          "Enable QueryPCRF function";
        type empty;
      }
      leaf location-change-reporting {
        description
          "Activate the license feature Location Change Reporting";
        type empty;
      }
      leaf integrated-wifi-access {
        description
          "Enable integrated wifi function";
        type empty;
      }
    }
    container fault-management {
      description
        "Fault management settings";
      container alarm {
        description
          "Alarm settings";
        container service-based-charging {
          description
            "service-based-charging related alarms settings";
          leaf no-invalid-service-context-id-ccr {
            description
              "Do not issue alarm on invalid service-context-id in CCR";
            type empty;
          }
          leaf no-invalid-cca {
            description
              "Do not issue alarm on invalid CCA";
            type empty;
          }
        }
      }
    }
    container qos-control {
      description
        "Quality of service settings";
      presence "qos-control need presence";
      uses qos-control-type;
    }
    container dns {
      description
        "DNS settings";
      presence "dns need presence";
      leaf enabled {
        description
          "Enable DNS function";
        type empty;
      }
      leaf ttl-min {
        type uint32 {
          range "0..604800" {
            error-message "Invalid value for attribute 'ttl-min'. Valid values are in range:[0,604800]";
          }
        }
      }
      leaf ttl-max {
        type uint32 {
          range "0..604800" {
            error-message "Invalid value for attribute 'ttl-max'. Valid values are in range:[0,604800]";
          }
        }
      }
      leaf supervision-interval {
        type uint16 {
          range "20..3600" {
            error-message "Invalid value for attribute 'supervision-interval'. Valid values are in range:[20,3600]";
          }
        }
      }
      leaf supervision-timer {
        type uint8 {
          range "1..60" {
            error-message "Invalid value for attribute 'supervision-timer'. Valid values are in range:[1,60]";
          }
        }
      }
      leaf supervision-retry {
        type uint8 {
          range "0..10" {
            error-message "Invalid value for attribute 'supervision-retry'. Valid values are in range:[0,10]";
          }
        }
      }
      leaf supervision-record-name {
        type string {
          pattern '[.0-9A-Za-z_-]+' {
            error-message "Only letters, numbers, underscores, dashes, or dots are allowed";
          }
          length "4..244";
        }
      }
      leaf logical-interface {
        description
          "Reference to the logical-interface in [epg node logical-interface]";
        type leafref {
          path "/epg/node/logical-interface/name";
        }
        mandatory true;
      }
      list server {
        description
          "Specifies a server for DNS function";
        max-elements 10;
        key "name";
        leaf name {
          description
            "DNS server name";
          type string {
            pattern '[.0-9A-Za-z_-]+' {
              error-message "Only letters, numbers, underscores, dashes, or dots are allowed";
            }
            length "1..64";
          }
        }
        leaf address {
          description
            "IP address of the DNS server";
          type inet:ip-address;
          mandatory true;
        }
        leaf port {
          description
            "Port number for DNS server";
          type uint16;
        }
        leaf makeup-time {
          type uint16 {
            range "0..6000" {
              error-message "Invalid value for attribute 'makeup-time'. Valid values are in range:[0,6000]";
            }
          }
        }
      }
      action statistics {
        description
          "Show DNS statistics";
        output {
          leaf result {
            type string;
            mandatory true;
          }
        }
      }
      action status {
        description
          "Show DNS status";
        output {
          leaf result {
            type string;
            mandatory true;
          }
        }
      }
    }
    container service-capability-exposure {
      container query-pcrf {
        description
          "queryPcrf configuration";
        presence "query-pcrf need presence";
        leaf logical-interface {
          description
            "Reference to the logical-interface in [epg node logical-interface]";
          type leafref {
            path "/epg/node/logical-interface/name";
          }
          mandatory true;
        }
        leaf url {
          description
            "QueryPcrf url";
          type string;
          mandatory true;
        }
        leaf port {
          description
            "QueryPcrf port";
          type uint16;
          mandatory true;
        }
      }
    }
    container diagnostics {
      yexte:user-group "ericsson-support";
      description
        "Adaptive services diagnostics settings";
      leaf global-interface {
        description
          "Manually override global interface";
        type string;
      }
      leaf retain-configuration {
        description
          "Retain configuration structures";
        type empty;
      }
    }
    container internal-debug {
      yexte:user-group "ericsson-support";
      description
        "Actions used internally";
      action all {
        description
          "Show aggregated diagnostic information";
        output {
          leaf result {
            type string;
            mandatory true;
          }
        }
      }
      action apn {
        description
          "Show APN diagnostic information";
        input {
          leaf apn-name {
            description
              "APN to show";
            type string {
              pattern '[.0-9A-Za-z-]{1,100}' {
                error-message "Must be a string of 100 or fewer characters and may contain letters, numbers, decimals and dashes.";
              }
            }
            mandatory true;
          }
          leaf board {
            description
              "Service interface name";
            type string {
              pattern '(gc|gu)-0/(30|(1|2)[0-9]|[1-9])/1' {
                error-message "ERROR: Invalid value for parameter board. Valid values are strings in a specified format. Type: board? for more information on the format to use.";
              }
            }
            mandatory true;
          }
        }
        output {
          leaf result {
            type string;
            mandatory true;
          }
        }
      }
      action apn-index {
        description
          "Show list of APN indices";
        output {
          leaf result {
            type string;
            mandatory true;
          }
        }
      }
      action apn-management {
        description
          "Show APN manager module diagnostic information";
        output {
          leaf result {
            type string;
            mandatory true;
          }
        }
      }
      action charging {
        description
          "Show charging diagnostics information";
        output {
          leaf result {
            type string;
            mandatory true;
          }
        }
      }
      action dhcp {
        description
          "Show DHCP statistics";
        output {
          leaf result {
            type string;
            mandatory true;
          }
        }
      }
      action pdd-radius-path-status-all {
        description
          "Show all radius path status";
        output {
          leaf result {
            type string;
            mandatory true;
          }
        }
      }
      action standalone-pfcp-path-status-all {
        description
          "Show all standalone pfcp path status";
        output {
          leaf result {
            type string;
            mandatory true;
          }
        }
      }
      action destroy-ue {
        description
          "Removes a UE from the PGW without external signaling";
        input {
          leaf imsi {
            description
              "The IMSI of the UE to terminate";
            type string;
            mandatory true;
          }
        }
        output {
          leaf result {
            type string;
            mandatory true;
          }
        }
      }
      action export-pm-xml-file {
        description
          "Write a PM XML file with current PGW counters.";
        output {
          leaf result {
            type string;
            mandatory true;
          }
        }
      }
      action gccp {
        description
          "Show GCCP diagnostics information";
        output {
          leaf result {
            type string;
            mandatory true;
          }
        }
      }
      action gtp {
        description
          "Show GTP diagnostics information";
        output {
          leaf result {
            type string;
            mandatory true;
          }
        }
      }
      action gtp-prime {
        description
          "Show GTP Prime diagnostics information";
        output {
          leaf result {
            type string;
            mandatory true;
          }
        }
      }
      action gtpb {
        description
          "Show GTPB module diagnostic information";
        output {
          leaf result {
            type string;
            mandatory true;
          }
        }
      }
      container overload-control-information {
        description
          "PGW overload control information commands";
        action enable {
          description
            "Enable or disable Overload Control Information feature";
          input {
            leaf enable {
              description
                "Must be 1 = enabled or 0 = disabled";
              type uint8 {
                range "0..1" {
                  error-message "Invalid value for attribute 'enable'. Valid values are in range:[0,1]";
                }
              }
              mandatory true;
            }
          }
          output {
            leaf result {
              type string;
              mandatory true;
            }
          }
        }
        action simulate {
          description
            "Simulate PGW Overload Control Information on GTPv2, arguments: <percentage> <time> <time-unit>";
          input {
            leaf percentage {
              description
                "Reduction metric, percentage range 0-100";
              type uint8 {
                range "0..100" {
                  error-message "Invalid value for attribute 'percentage'. Valid values are in range:[0,100]";
                }
              }
              mandatory true;
            }
            leaf time {
              description
                "Period of validity, time (default minutes) range 0-31";
              type uint8 {
                range "0..31" {
                  error-message "Invalid value for attribute 'time'. Valid values are in range:[0,31]";
                }
              }
              mandatory true;
            }
            leaf time-unit {
              description
                "time-unit is an optional argument that specifies the time unit, default is minutes\\. possible values: s=2*seconds, m=minutes, x=10*minutes, h=hours, d=10*hours, i=infinite.";
              type string {
                pattern '(s|m|x|h|d|i)?' {
                  error-message "Argument must be one of following caracters: s=2*seconds, m=minutes, x=10*minutes, h=hours, d=10*hours, i=infinite.";
                }
              }
            }
          }
          output {
            leaf result {
              type string;
              mandatory true;
            }
          }
        }
        action status {
          description
            "Show Overload Control Information in use by PGW";
          output {
            leaf result {
              type string;
              mandatory true;
            }
          }
        }
      }
      action radius {
        description
          "Show RADIUS module diagnostic information";
        output {
          leaf result {
            type string;
            mandatory true;
          }
        }
      }
      action statistics {
        description
          "Show statistics reported by node controller";
        output {
          leaf result {
            type string;
            mandatory true;
          }
        }
      }
      container session-resilience {
        description
          "PGW session resilience commands";
        action ppb-statistics-all {
          description
            "Show PPB resilence diagnostic information";
          output {
            leaf result {
              type string;
              mandatory true;
            }
          }
        }
        action generate-ue-ipaddress-pe {
          description
            "Generate UE IP address(es) based on certain criteria";
          input {
            leaf apn-name {
              description
                "The APN to generate the UE IP address";
              type string {
                pattern '[.0-9A-Za-z-]{1,100}' {
                  error-message "Must be a string of 100 or fewer characters and may contain letters, numbers, decimals and dashes.";
                }
              }
              mandatory true;
            }
            leaf output-type {
              description
                "The UE IP address type should be either ipv4 or ipv6";
              type enumeration {
                enum ipv4 {
                  description
                    "ipv4";
                }
                enum ipv6 {
                  description
                    "ipv6";
                }
              }
              mandatory true;
            }
            leaf count {
              description
                "The number of UE IP address(es) to generate";
              type uint32;
              mandatory true;
            }
            leaf increment {
              description
                "How much to increment UE IP address when searching (examples: 1, 10000 etc)";
              type uint32;
              mandatory true;
            }
            leaf primary-u-pe {
              description
                "The primary U(ser plane) process entity for the UE IP address\\. Should be in the format: U:3:2 (boardgroup 3 and board 2) or 'any'";
              type string {
                pattern '(U:[0-9]:[0-9]+){0,3}' {
                  error-message "Invalid process entiy, must be U:[0-9]:[0-9] or any";
                }
              }
              mandatory true;
            }
            leaf secondary-u-pe {
              description
                "The secondary U(ser plane) process entity for the UE IP address\\. Should be in the format: U:3:2 (boardgroup 3 and board 2) or 'any'";
              type string {
                pattern '(any|(U:[0-9]:[0-9]+){0,3})' {
                  error-message "Invalid process entiy, must be U:[0-9]:[0-9] or any";
                }
              }
              mandatory true;
            }
          }
          output {
            leaf result {
              type string;
              mandatory true;
            }
          }
        }
        action generate-ue-ipaddress-li {
          description
            "Generate UE IP address(es) based on certain criteria";
          input {
            leaf apn-name {
              description
                "The APN to generate the UE IP address";
              type string {
                pattern '[.0-9A-Za-z-]{1,100}' {
                  error-message "Must be a string of 100 or fewer characters and may contain letters, numbers, decimals and dashes.";
                }
              }
              mandatory true;
            }
            leaf output-type {
              description
                "The UE IP address type should be either ipv4 or ipv6";
              type enumeration {
                enum ipv4 {
                  description
                    "ipv4";
                }
                enum ipv6 {
                  description
                    "ipv6";
                }
              }
              mandatory true;
            }
            leaf count {
              description
                "The number of UE IP address(es) to generate";
              type uint32;
              mandatory true;
            }
            leaf increment {
              description
                "How much to increment UE IP address when searching (examples: 1, 10000 etc)";
              type uint32;
              mandatory true;
            }
            leaf load-index {
              description
                "The load index to generate the UE IP address for";
              type uint16 {
                range "0..4095" {
                  error-message "Invalid value for attribute 'load-index'. Valid values are in range:[0,4095]";
                }
              }
              mandatory true;
            }
          }
          output {
            leaf result {
              type string;
              mandatory true;
            }
          }
        }
        container lim {
          description
            "PGW LIM session resilience commands";
          action history-pe {
            description
              "Show the LIM history in pgw-c";
            input {
              leaf load-indices {
                description
                  "Load indices to print, might be either a comma-separated list, a range or both, for example 1,3,5-7,9";
                type string;
                mandatory true;
              }
              leaf process-entity {
                description
                  "Identifies the pgw-c process entity that should answer the command, for example 'all' or 'PC:0:5:0'";
                type string {
                  pattern '(all|(PC(:[0-9][0-9]?){0,3}))' {
                    error-message "Invalid process entity";
                  }
                }
                mandatory true;
              }
            }
            output {
              leaf result {
                type string;
                mandatory true;
              }
            }
          }
          action status {
            description
              "Show the LIM status in pgw-c";
            input {
              leaf process-entity {
                description
                  "Identifies the pgw-c process entity that should answer the command, for example 'all' or 'PC:2:2:0'";
                type string {
                  pattern '(all|((PC)(:[0-9][0-9]?){0,3}))' {
                    error-message "Invalid process entity";
                  }
                }
                mandatory true;
              }
            }
            output {
              leaf result {
                type string;
                mandatory true;
              }
            }
          }
          action status-li {
            description
              "Show the LIM status in pgw-c for specific load indices";
            input {
              leaf load-indices {
                description
                  "Load indices to print, might be either a comma-separated list, a range or both, for example 1,3,5-7,9";
                type string;
                mandatory true;
              }
              leaf process-entity {
                description
                  "Identifies the pgw-c process entity that should answer the command, for example 'all' or 'PC:2:2:0'";
                type string {
                  pattern '(all|((PC)(:[0-9][0-9]?){0,3}))' {
                    error-message "Invalid process entity";
                  }
                }
                mandatory true;
              }
            }
            output {
              leaf result {
                type string;
                mandatory true;
              }
            }
          }
        }
      }
    }
    container ebm {
      yexte:user-group "ericsson-support,epg-tracing-admin";
      description
        "Event based monitoring settings";
      list profile {
        must '/epg/pgw/ebm/profile[name=current()/name]/event' {
          error-message "event is mandatory";
        }
        max-elements 16;
        key "name";
        uses pgw-ebm-profile-type;
      }
      action statistics {
        description
          "PGW EBM statistics";
        output {
          leaf result {
            type string;
            mandatory true;
          }
        }
      }
    }
    action show-trace {
      yexte:user-group "ericsson-support,epg-tracing-admin";
      description
        "Identifier for IMSI";
      input {
        leaf identifier-type {
          type enumeration {
            enum imsi {
              description
                "International Mobile Subscriber Identity";
            }
            enum msisdn {
              description
                "Mobile Station Integrated Services Digital Network";
            }
            enum imei {
              description
                "International Mobile Equipment Identity";
            }
          }
          mandatory true;
        }
        leaf value {
          description
            "Identifier for IMSI or Identifier for MSISDN";
          type string {
            pattern '([0-9]{5,15})|([0-9]{1,18})' {
              error-message "ERROR: Invalid value for parameter value. Valid values are strings in a specified format. Type: value? for more information on the format to use.";
            }
          }
          mandatory true;
        }
      }
      output {
        leaf result {
          type string;
          mandatory true;
        }
      }
    }
    action show-trace-all {
      yexte:user-group "ericsson-support,epg-tracing-admin";
      description
        "Show all trace information";
      output {
        leaf result {
          type string;
          mandatory true;
        }
      }
    }
    action start-trace {
      yexte:user-group "ericsson-support,epg-tracing-admin";
      description
        "Identifier for IMSI";
      input {
        leaf identifier-type {
          type enumeration {
            enum imsi {
              description
                "International Mobile Subscriber Identity";
            }
            enum msisdn {
              description
                "Mobile Station Integrated Services Digital Network";
            }
            enum imei {
              description
                "International Mobile Equipment Identity";
            }
          }
          mandatory true;
        }
        leaf value {
          description
            "Identifier for IMSI or Identifier for MSISDN";
          type string {
            pattern '([0-9]{5,15})|([0-9]{1,18})' {
              error-message "ERROR: Invalid value for parameter value. Valid values are strings in a specified format. Type: value? for more information on the format to use.";
            }
          }
          mandatory true;
        }
      }
      output {
        leaf result {
          type string;
          mandatory true;
        }
      }
    }
    action stop-trace {
      yexte:user-group "ericsson-support,epg-tracing-admin";
      description
        "Identifier for IMSI";
      input {
        leaf identifier-type {
          type enumeration {
            enum imsi {
              description
                "International Mobile Subscriber Identity";
            }
            enum msisdn {
              description
                "Mobile Station Integrated Services Digital Network";
            }
            enum imei {
              description
                "International Mobile Equipment Identity";
            }
          }
          mandatory true;
        }
        leaf value {
          description
            "Identifier for IMSI or Identifier for MSISDN";
          type string {
            pattern '([0-9]{5,15})|([0-9]{1,18})' {
              error-message "ERROR: Invalid value for parameter value. Valid values are strings in a specified format. Type: value? for more information on the format to use.";
            }
          }
          mandatory true;
        }
      }
      output {
        leaf result {
          type string;
          mandatory true;
        }
      }
    }
    action stop-trace-all {
      yexte:user-group "ericsson-support,epg-tracing-admin";
      description
        "Stop all tracing";
      output {
        leaf result {
          type string;
          mandatory true;
        }
      }
    }
    action statistics {
      description
        "Show PGW statistics";
      input {
        leaf of {
          type enumeration {
            enum brief {
              description
                "Show GGSN/PGW statistics";
            }
            enum gtp {
              description
                "Show GPRS tunneling protocol statistics";
            }
            enum charging {
              description
                "Show charging statistics";
            }
            enum radius {
              description
                "Show RADIUS statistics";
            }
            enum pmip {
              description
                "Show PMIPv6 statistics";
            }
            enum gre {
              description
                "Show GRE statistics";
            }
            enum gtp-prime {
              description
                "Show GPRS Tunneling Protocol Prime statistics";
            }
            enum l2tp-tunnel {
              description
                "Show L2TP tunnel statistics";
            }
            enum shared-ip-pool {
              description
                "Show shared ip pool statistics";
            }
            enum dhcp {
              description
                "Show DHCP statistics";
            }
            enum dns {
              description
                "Show DNS statistics";
            }
            enum ppb {
              description
                "Show PPB statistics";
            }
            enum pisc-flows {
              description
                "Show PISC flow statistics";
            }
            enum high-availability {
              description
                "Show High Availability statistics";
            }
            enum qci {
              status current {
                yexte:preliminary;
              }
              description
                "Show PGW statistics qci";
            }
            enum xlat {
              description
                "Show XLAT statistics";
            }
            enum cause-code {
              description
                "Show Cause Code statistics";
            }
            enum dbp-peer {
              description
                "Show diameter peer statistics";
            }
            enum twamp {
              description
                "Show twamp statistics";
            }
            enum service {
              description
                "Show service statistics";
            }
          }
          mandatory true;
        }
      }
      output {
        leaf result {
          type string;
          mandatory true;
        }
      }
    }
    action statistics-serving-node {
      description
        "Show PGW statistics per Serving Node";
      input {
        leaf serving-node {
          description
            "IP address of the serving node";
          type inet:ip-address;
        }
      }
      output {
        leaf result {
          type string;
          mandatory true;
        }
      }
    }
    action statistics-plmn-id {
      description
        "Show PGW statistics per PLMN ID";
      input {
        leaf plmn-id {
          description
            "Public Land Mobile Network identifier";
          type string {
            pattern '([0-9]{5,15})|([0-9]{1,18})' {
              error-message "PLMN identifier is a string of 5 or 6 digits";
            }
            length "5..6";
          }
        }
      }
      output {
        leaf result {
          type string;
          mandatory true;
        }
      }
    }
    action statistics-pcscf {
      description
        "Show PGW statistics per p-cscf";
      input {
        leaf pcscf-node {
          description
            "IP address of the p-cscf node";
          type inet:ip-address;
        }
      }
      output {
        leaf result {
          type string;
          mandatory true;
        }
      }
    }
    action statistics-ocs {
      description
        "Show PGW statistics per OCS DiameterHost";
      input {
        leaf ocs-host-name {
          description
            "Name of the diameter host";
          type string {
            pattern '[.0-9A-Za-z_-]*' {
              error-message "Must contain only letters, numbers, underscores or dashes";
            }
            length "1..64";
          }
        }
      }
      output {
        leaf result {
          type string;
          mandatory true;
        }
      }
    }
    action statistics-pcrf {
      description
        "Show PGW statistics per PCRF DiameterHost";
      input {
        leaf pcrf-host-name {
          description
            "Name of the diameter host";
          type string {
            pattern '[.0-9A-Za-z_-]*' {
              error-message "Must contain only letters, numbers, underscores or dashes";
            }
            length "1..64";
          }
        }
      }
      output {
        leaf result {
          type string;
          mandatory true;
        }
      }
    }
    action statistics-upf {
      description
        "Show PGW statistics per Upf Node Name";
      input {
        leaf upf-node-name {
          description
            "Name of the Upf Node";
          type string {
            pattern '[.0-9A-Za-z_-]*' {
              error-message "Must contain only letters, numbers, underscores or dashes";
            }
            length "1..64";
          }
        }
      }
      output {
        leaf result {
          type string;
          mandatory true;
        }
      }
    }
    action statistics-origin-host {
      description
        "Show PGW statistics per diameter originHost";
      input {
        leaf origin-host-name {
          description
            "Name of the diameter origin host";
          type string {
            pattern '[.0-9A-Za-z_-]*' {
              error-message "Must contain only letters, numbers, underscores or dashes";
            }
            length "1..64";
          }
        }
      }
      output {
        leaf result {
          type string;
          mandatory true;
        }
      }
    }
    leaf-list imsi-prefix-statistics {
      description
        "Prefix of IMSI (1~15 digits) for command epg pgw statistics-imsi-prefix";
      type string {
        pattern '([0-9]{1,15})' {
          error-message "ERROR: Invalid value for parameter imsi-prefix-statistics. Valid values are strings in a specified format. Type: imsi-prefix-statistics? for more information on the format to use.";
        }
        length "1..15";
      }
      max-elements 200;
    }
    action statistics-imsi-prefix {
      description
        "Show PGW statistics per IMSI prefix";
      input {
        leaf imsi-prefix {
          description
            "Prefix of IMSI (1~15 digits)";
          type string {
            pattern '([0-9]{1,15})' {
              error-message "ERROR: Invalid value for parameter imsi-prefix. Valid values are strings in a specified format. Type: imsi-prefix? for more information on the format to use.";
            }
            length "1..15";
          }
        }
      }
      output {
        leaf result {
          type string;
          mandatory true;
        }
      }
    }
    action user-info {
      yexte:user-group "ericsson-support,epg-tracing-admin,epg-admin";
      description
        "Identifier for IMSI";
      input {
        leaf identifier-type {
          type enumeration {
            enum imsi {
              description
                "International Mobile Subscriber Identity";
            }
            enum msisdn {
              description
                "Mobile Station Integrated Services Digital Network";
            }
            enum imei {
              description
                "International Mobile Equipment Identity";
            }
          }
          mandatory true;
        }
        leaf value {
          description
            "Identifier for IMSI or Identifier for MSISDN";
          type string {
            pattern '([0-9]{5,15})|([0-9]{1,18})' {
              error-message "ERROR: Invalid value for parameter value. Valid values are strings in a specified format. Type: value? for more information on the format to use.";
            }
          }
          mandatory true;
        }
      }
      output {
        leaf result {
          type string;
          mandatory true;
        }
      }
    }
    container ecm {
      description
        "show ECM statistics";
      action statistics {
        description
          "PGW ECM statistics";
        output {
          leaf result {
            type string;
            mandatory true;
          }
        }
      }
      action statistics-apn {
        description
          "Show PGW ECM statistics per APN";
        input {
          leaf apn-name {
            description
              "APN to show";
            type string {
              pattern '[.0-9A-Za-z-]{1,100}' {
                error-message "Must be a string of 100 or fewer characters and may contain letters, numbers, decimals and dashes.";
              }
            }
            mandatory true;
          }
        }
        output {
          leaf result {
            type string;
            mandatory true;
          }
        }
      }
      action statistics-serving-node {
        description
          "Show PGW ECM statistics per Serving Node";
        input {
          leaf ecm-serving-node {
            description
              "IP address of the serving node";
            type inet:ip-address;
          }
        }
        output {
          leaf result {
            type string;
            mandatory true;
          }
        }
      }
      action statistics-plmn-id {
        description
          "Show PGW ECM statistics per PLMN ID";
        input {
          leaf ecm-plmn-id {
            description
              "Public Land Mobile Network identifier";
            type string {
              pattern '([0-9]{5,15})|([0-9]{1,18})' {
                error-message "PLMN identifier is a string of 5 or 6 digits";
              }
              length "5..6";
            }
          }
        }
        output {
          leaf result {
            type string;
            mandatory true;
          }
        }
      }
      action statistics-pcscf {
        description
          "Show PGW ECM statistics per p-cscf";
        input {
          leaf ecm-pcscf-node {
            description
              "IP address of the p-cscf node";
            type inet:ip-address;
          }
        }
        output {
          leaf result {
            type string;
            mandatory true;
          }
        }
      }
      action statistics-ocs {
        description
          "Show PGW ECM statistics per OCS DiameterHost";
        input {
          leaf ecm-ocs-host-name {
            description
              "Name of the diameter host";
            type string {
              pattern '[.0-9A-Za-z_-]*' {
                error-message "Must contain only letters, numbers, underscores or dashes";
              }
              length "1..64";
            }
          }
        }
        output {
          leaf result {
            type string;
            mandatory true;
          }
        }
      }
      action statistics-pcrf {
        description
          "Show PGW ECM statistics per PCRF DiameterHost";
        input {
          leaf ecm-pcrf-host-name {
            description
              "Name of the diameter host";
            type string {
              pattern '[.0-9A-Za-z_-]*' {
                error-message "Must contain only letters, numbers, underscores or dashes";
              }
              length "1..64";
            }
          }
        }
        output {
          leaf result {
            type string;
            mandatory true;
          }
        }
      }
    }
    container lawful-intercept {
      yexte:user-group "epg-lawful-intercept-admin";
      description
        "Configuration for lawful-interception in PGW";
      container provisioning {
        description
          "To configure PGW specific administration";
        presence "provisioning need presence";
        must '(/epg/pgw/lawful-intercept/provisioning/mode) and (/epg/pgw/lawful-intercept/provisioning/shared-secret)' {
          error-message "[epg pgw lawful-intercept provisioning mode ] and [epg pgw lawful-intercept  provisioning shared-secret] must be configured";
          tailf:dependency "/epg/pgw/lawful-intercept/provisioning/mode";
          tailf:dependency "/epg/pgw/lawful-intercept/provisioning/shared-secret";
        }
        leaf mode {
          description
            "To specify the source of target administration";
          type enumeration {
            enum gx {
              description
                "Use Gx for Target administration";
            }
          }
          mandatory true;
        }
        leaf shared-secret {
          description
            "The shared secret used for Gx Target administration";
          type string;
          mandatory true;
        }
      }
    }
    container session-priority {
      description
        "Configure Enhanced Multimedia Priority Services";
      container default {
        description
          "default MP (message priority) configuration";
        container gtp {
          leaf message-priority {
            description
              "MP (message priority) configuration in the ARP mapping table";
            type uint8 {
              range "0..15" {
                error-message "Invalid value for attribute 'message-priority'. Valid values are in range:[0,15]";
              }
            }
          }
        }
      }
      list arp-priority-level {
        max-elements 15;
        key "name";
        uses session-priority-arp-priority-type;
      }
      list message-priority-level {
        max-elements 15;
        key "name";
        uses session-priority-mp-priority-type;
      }
    }
  }

  grouping gy-failure-profile-type {
    leaf name {
      description
        "Gy failure profile name";
      type string;
    }
    container session-handling {
      description
        "Session handling settings";
      leaf retention-profile {
        description
          "Retention profile to use for action retain";
        type leafref {
          path "../../../gy-retention-profile/name";
        }
      }
      leaf default-ccr-initial-failure-action {
        description
          "Action to be taken by default for CCR-Initial failures";
        type leafref {
          path "../action/name";
        }
        must 'not (../action[name=current()]/success)' {
          error-message "action containing 'success' is not supported as a default-ccr-initial-failure-action";
        }
      }
      leaf default-ccr-update-failure-action {
        description
          "Action to be taken by default for CCR-Update failures";
        type leafref {
          path "../action/name";
        }
        must 'not (../action[name=current()]/success)' {
          error-message "action containing 'success' is not supported as a default-ccr-update-failure-action";
        }
      }
      leaf ccfh-continue-action {
        description
          "Action to be taken for CCFH continue cases";
        type leafref {
          path "../action/name";
        }
        must '(../action[name=current()]/continue)' {
          error-message "The only supported action type for ccfh-continue-action is 'continue'";
        }
      }
      leaf ccfh-terminate-action {
        description
          "Action to be taken for CCFH terminate cases";
        type leafref {
          path "../action/name";
        }
        must '(../action[name=current()]/terminate)' {
          error-message "The only supported action type for ccfh-terminate-action is 'terminate'";
        }
      }
      leaf ccfh-retry-and-terminate-action {
        description
          "Action to be taken for CCFH retry-and-terminate cases";
        type leafref {
          path "../action/name";
        }
        must '(../action[name=current()]/terminate)' {
          error-message "The only supported action type for ccfh-retry-and-terminate-action is 'terminate'";
        }
      }
      leaf server-restart-action {
        description
          "Action to be taken for all the sessions affected by a server restart";
        type leafref {
          path "../action/name";
        }
        must 'not (../action[name=current()]/success)' {
          error-message "action containing 'success' is not supported as a server-restart-action";
        }
        must 'not (../action[name=current()]/continue/retain)' {
          error-message "action containing 'continue/retain' is not supported as a server-restart-action";
        }
        must 'not (../action[name=current()]/*/send-ccr-termination)' {
          error-message "action containing 'send-ccr-termination' is not supported as a server-restart-action";
        }
      }
      container fallback-to-file {
        description
          "Configuration for writing failed CCR messages to disk";
        leaf ccr-termination {
          description
            "Write failed CCR-Termination messages to disk";
          type empty;
        }
      }
      list condition {
        must 'message-type' {
          error-message "message-type is mandatory";
        }
        key "name";
        uses gy-failure-condition-type;
      }
      list action {
        key "name";
        uses gy-failure-action-type;
      }
    }
  }

  grouping gy-failure-action-type {
    leaf name {
      description
        "Action name";
      type string;
    }
    choice action {
      container terminate {
        description
          "Terminate the user session";
        presence "terminate need presence";
        leaf send-ccr-termination {
          description
            "Gracefully terminate the credit control session";
          type empty;
        }
        leaf send-reactivation-requested {
          description
            "Use cause 'Reactivation Requested' in the GTP deletion message";
          type empty;
        }
        leaf report-retry-in-condition-change {
          description
            "Report RetryAndTerminate in condition change fields of offline charging";
          type empty;
        }
        leaf gtpv1-cause {
          description
            "Cause code used for the GTPv1 rejection";
          type uint8 {
            range "129..240" {
              error-message "Invalid value for attribute 'gtpv1-cause'. Valid values are in range:[129,240]";
            }
          }
          default "209";
        }
        leaf gtpv2-cause {
          description
            "Cause code used for the GTPv2 rejection";
          type uint8 {
            range "64..239" {
              error-message "Invalid value for attribute 'gtpv2-cause'. Valid values are in range:[64,239]";
            }
          }
          default "92";
        }
      }
      container continue {
        description
          "Continue the user session";
        presence "continue need presence";
        leaf send-ccr-termination {
          description
            "Gracefully terminate the credit control session";
          type empty;
        }
        leaf continue-time {
          description
            "Maximum time, in seconds, to continue without credit control";
          type uint32 {
            range "1..4294967" {
              error-message "Invalid value for attribute 'continue-time'. Valid values are in range:[1,4294967]";
            }
          }
        }
        container reestablish {
          description
            "Reestablish the credit control session";
          must 'not (../retain)' {
            error-message "Reestablish is not compatible with Retain";
          }
          presence "reestablish need presence";
        }
        container retain {
          description
            "Retain the credit control session";
          must '../../../retention-profile' {
            error-message "A retention profile must be referenced under [epg pgw credit-control gy-failure-profile <name> session-handling]";
          }
          presence "retain need presence";
        }
      }
      container success {
        description
          "Treat the failure as if it was successful";
        presence "success need presence";
      }
    }
  }

  grouping gy-failure-condition-type {
    leaf name {
      description
        "Request failure condition name";
      type string;
    }
    leaf priority {
      description
        "Priority value for the request failure condition, where a lower value has precedence";
      type uint8 {
        range "1..128" {
          error-message "Invalid value for attribute 'priority'. Valid values are in range:[1,128]";
        }
      }
      mandatory true;
      must 'count(../../condition[priority=current()])=1' {
        error-message "Priority must be unique among all session handling conditions that are part of a gy failure profile";
      }
    }
    leaf action {
      description
        "Action to be taken for this condition";
      mandatory true;
      type leafref {
        path "../../action/name";
      }
    }
    list message-type {
      description
        "Message type for which the request failure condition applies";
      key "name";
      leaf name {
        description
          "Message type name";
        type enumeration {
          enum ccr-initial {
            description
              "Credit Control Request Initial";
          }
          enum ccr-update {
            description
              "Credit Control Request Update";
          }
        }
      }
      leaf timeout {
        description
          "Failure condition applies when message times out";
        type empty;
      }
      leaf connection-failure {
        description
          "Failure condition applies when the request cannot be sent due to a connection failure";
        type empty;
      }
      leaf-list result-code {
        description
          "Result code or result code range for which the request failure condition applies";
        type string {
          pattern '[0-9]{1,10}([-][0-9]{1,10})?' {
            error-message "Must be a result code or a range of result codes.";
          }
          length "1..64";
        }
        max-elements 64;
      }
    }
  }

  grouping gy-retention-profile-type {
    leaf name {
      description
        "Retention profile name";
      type string;
    }
    leaf max-number-of-restoration-attempts {
      description
        "Maximum number of attempts to restore a retained credit control session before the user session is deleted";
      type uint8 {
        range "1..254" {
          error-message "Invalid value for attribute 'max-number-of-restoration-attempts'. Valid values are in range:[1,254]";
        }
      }
      mandatory true;
    }
    leaf increment-cc-request-number {
      description
        "Increment the CC request number in each CCR-Update message sent as credit control restoration attempt";
      type empty;
    }
    leaf discard-usage-for-5002 {
      status current {
        yexte:preliminary;
      }
      description
        "Discard the reported usage for result code 5002 and skip writing to disk any CCR-Termination failed with result code 5002";
      type empty;
    }
    leaf update-after-initial-failure {
      description
        "Send CCR-Update as restoration attempt after a CCR-Initial failure";
      type empty;
    }
    container quota-handling {
      description
        "Settings related to retention quota handling";
      leaf use-last-granted {
        description
          "If existing, use the volume quota and validity time last granted by the OCS";
        type empty;
      }
      leaf volume-quota {
        description
          "Define the volume quota, in bytes, to use for a retained credit control session";
        type uint32 {
          range "10000..1000000000" {
            error-message "Invalid value for attribute 'volume-quota'. Valid values are in range:[10000,1000000000]";
          }
        }
        mandatory true;
      }
      leaf volume-threshold {
        description
          "Define the volume threshold, in bytes, to use for a retained credit control session";
        type uint32 {
          range "1..999990000" {
            error-message "Invalid value for attribute 'volume-threshold'. Valid values are in range:[1,999990000]";
          }
        }
      }
      leaf validity-time {
        description
          "Define the quota validity time, in seconds, to use for a retained credit control session";
        type uint32 {
          range "1..86400" {
            error-message "Invalid value for attribute 'validity-time'. Valid values are in range:[1,86400]";
          }
        }
        mandatory true;
      }
    }
  }

  grouping pgw-ebm-profile-type {
    leaf name {
      description
        "Event based monitoring profile name";
      type string {
        pattern '[0-9A-Za-z][0-9A-Za-z_-]*' {
          error-message "Must be a string beginning with a number or letter and consisting of letters, numbers, dashes and underscores.";
        }
        length "1..63";
      }
    }
    container selector {
      description
        "User selection settings";
      uses pgw-ebm-profile-selector-type;
    }
    container limit {
      description
        "User selection limits settings";
      uses pgw-ebm-profile-limit-type;
    }
    container event {
      description
        "Monitoring events settings";
      presence "event need presence";
      uses pgw-ebm-profile-event-type;
    }
  }

  grouping pgw-ebm-profile-selector-type {
    leaf apn {
      description
        "Select users based on APN";
      type leafref {
        path "/epg/pgw/apn/name";
      }
    }
    leaf imsi {
      description
        "Select users based on IMSI regular expression";
      type string;
    }
    leaf cause-code {
      description
        "Filter event based on cause code";
      type uint16 {
        range "0..65535" {
          error-message "Invalid value for attribute 'cause-code'. Valid values are in range:[0,65535]";
        }
      }
    }
  }

  grouping pgw-ebm-profile-limit-type {
    leaf users {
      description
        "Limit selection to number of users";
      type uint32 {
        range "100..1000000" {
          error-message "Invalid value for attribute 'users'. Valid values are in range:[100,1000000]";
        }
      }
    }
  }

  grouping pgw-ebm-profile-event-type {
    leaf bearer-creation {
      description
        "Monitor pgw bearer-creation events";
      type empty;
    }
    leaf bearer-deletion {
      description
        "Monitor pgw bearer-deletion events";
      type empty;
    }
    leaf bearer-modification {
      description
        "Monitor pgw bearer-modification events";
      type empty;
    }
    leaf bearer-update {
      description
        "Monitor pgw bearer-update events";
      type empty;
    }
    leaf session-creation {
      description
        "Monitor pgw session-creation events";
      type empty;
    }
    leaf session-deletion {
      description
        "Monitor pgw session-deletion events";
      type empty;
    }
    leaf s6b-authorization {
      description
        "Monitor pgw s6b-authorization events";
      type empty;
    }
    leaf s6b-termination {
      description
        "Monitor pgw s6b-termination events";
      type empty;
    }
    leaf gx-init {
      description
        "Monitor pgw gx-init events";
      type empty;
    }
    leaf gx-update {
      description
        "Monitor pgw gx-update events";
      type empty;
    }
    leaf gx-terminate {
      description
        "Monitor pgw gx-terminate events";
      type empty;
    }
    leaf gx-reauthorize {
      description
        "Monitor pgw gx-reauthorize events";
      type empty;
    }
    leaf gy-cc-init {
      description
        "Monitor pgw gy-cc-init events";
      type empty;
    }
    leaf gy-cc-update {
      description
        "Monitor pgw gy-cc-update events";
      type empty;
    }
    leaf gy-cc-terminate {
      description
        "Monitor pgw gy-cc-terminate events";
      type empty;
    }
    leaf gy-cc-event {
      description
        "Monitor pgw gy-cc-event events";
      type empty;
    }
    leaf session-suspension {
      description
        "Monitor pgw session-suspend events";
      type empty;
    }
    leaf session-resume {
      description
        "Monitor pgw session-resume events";
      type empty;
    }
    leaf pdp-context-creation {
      description
        "Monitor pgw pdp-context-creation events";
      type empty;
    }
    leaf pdp-context-deletion {
      description
        "Monitor pgw pdp-context-deletion events";
      type empty;
    }
    leaf pdp-context-update {
      description
        "Monitor pgw pdp-context-update events";
      type empty;
    }
    leaf secondary-pdp-context-activation {
      description
        "Monitor pgw secondary-pdp-context-activation events";
      type empty;
    }
    leaf change-notification {
      description
        "Monitor pgw change-notification events";
      type empty;
    }
    leaf ue-ip-address-allocation {
      description
        "Monitor pgw ue-ip-address-allocation events";
      type empty;
    }
    leaf ue-ip-address-deallocation {
      description
        "Monitor pgw ue-ip-address-deallocation events";
      type empty;
    }
  }

  grouping n40-chargeable-event-triggers-type {
    list trigger {
      key "name";
      leaf name {
        type enumeration {
          enum qos-change {
            description
              "Indicate that OoS change has happened";
          }
          enum uli-change {
            description
              "Indicate that User location has been changed";
          }
          enum serving-node-change {
            description
              "A serving node (AMF) change has happened";
          }
        }
      }
      list method {
        key "name";
        leaf name {
          type enumeration {
            enum online {
              description
                "Online charging with quota management control";
            }
          }
        }
        leaf category {
          type enumeration {
            enum immediate {
              description
                "SMF generates the charging data and triggers a Charging Event towards CHF when trigger occurred";
            }
            enum deferred {
              description
                "SMF generates the charging data and does not trigger a Charging Event towards the CHF when trigger occurred";
            }
          }
          default "immediate";
        }
      }
    }
  }

  grouping rating-group-reauthorization-triggers-type {
    leaf-list rating-condition-change {
      description
        "Locally armed rating condition change triggers";
      type enumeration {
        enum cell-id {
          description
            "Trigger credit re-authorization at cell identity change";
        }
        enum ecgi {
          description
            "Trigger credit re-authorization at e-utran cell global identifier change";
        }
        enum lac {
          description
            "Trigger credit re-authorization at location area code change";
        }
        enum location {
          description
            "Trigger credit re-authorization at user location change";
        }
        enum mcc {
          description
            "Trigger credit re-authorization at mobile country code change";
        }
        enum mnc {
          description
            "Trigger credit re-authorization at mobile network code change";
        }
        enum presence {
          description
            "Trigger credit re-authorization at presence reporting area change";
        }
        enum qos {
          description
            "Trigger credit re-authorization at quality of service change";
        }
        enum rac {
          description
            "Trigger credit re-authorization at routing area code change";
        }
        enum rat-type {
          description
            "Trigger credit re-authorization at radio access technology type change";
        }
        enum sgsn-address {
          description
            "Trigger credit re-authorization at serving node address change";
        }
        enum tac {
          description
            "Trigger credit re-authorization at tracking area code change";
        }
        enum time-zone {
          description
            "Trigger credit re-authorization at time zone change";
        }
      }
    }
    leaf ignore-external {
      description
        "Ignore externally armed rating condition change triggers";
      type empty;
    }
  }

  grouping diameter-host-type {
    leaf name {
      description
        "Host identifier";
      type string {
        pattern '[.0-9A-Za-z_-]*' {
          error-message "Must contain only letters, numbers, dot, underscores or dashes";
        }
        length "1..64";
      }
    }
    leaf host-name {
      description
        "DIAMETER host specified as fully qualified domain name";
      type string {
        pattern '[.0-9A-Za-z_-]*' {
          error-message "Must contain only letters, numbers, dot, underscores or dashes";
        }
        length "1..128";
      }
      mandatory true;
    }
  }

  grouping diameter-peer-type {
    leaf name {
      description
        "Peer identifier";
      type string {
        pattern '[.0-9A-Za-z_-]*' {
          error-message "Must contain only letters, numbers, dot, underscores or dashes";
        }
        length "1..64";
      }
    }
    leaf-list address {
      description
        "Peer address";
      type inet:ip-address;
      min-elements 1;
      max-elements 16;
      ordered-by user;
    }
    leaf host {
      description
        "Diameter host identifier associated with the peer";
      type leafref {
        path "/epg/pgw/diameter/host/name";
      }
    }
    leaf port {
      description
        "Peer port number";
      type uint16;
      mandatory true;
    }
    leaf logical-interface {
      description
        "Logical interface";
      type leafref {
        path "/epg/node/logical-interface/name";
      }
    }
    container watchdog {
      description
        "Watchdog settings";
      leaf timeout {
        description
          "Period between device watch dog requests";
        type uint16 {
          range "3..300" {
            error-message "Invalid value for attribute 'timeout'. Valid values are in range:[3,300]";
          }
        }
      }
    }
    list message-type {
      description
        "Message type settings";
      key "name";
      leaf name {
        description
          "Message type name";
        type enumeration {
          enum ccr-initial {
            description
              "Credit Control Request initial";
          }
          enum ccr-update {
            description
              "Credit Control Request update";
          }
        }
      }
      leaf requests-per-second {
        description
          "Maximum requests per second";
        type uint16 {
          range "0..5000" {
            error-message "Invalid value for attribute 'requests-per-second'. Valid values are in range:[0,5000]";
          }
        }
      }
    }
    leaf transport-protocol {
      description
        "Transport protocol to use";
      type enumeration {
        enum tcp {
          description
            "Use TCP as the transport protocol";
        }
        enum sctp {
          description
            "Use SCTP as the transport protocol";
        }
      }
    }
    container sctp {
      description
        "SCTP association parameter configuration";
      must "/epg/pgw/diameter/peer[name=current()/../name]/transport-protocol[text()='sctp']" {
        error-message "The peer must be configured with SCTP as the transport protocol";
        tailf:dependency "/epg/pgw/diameter/peer/transport-protocol";
      }
      presence "sctp need presence";
      leaf additional-logical-interface {
        description
          "Additional logical interface used for local multihoming";
        type string;
        must '/epg/node/logical-interface[name=current()]' {
          error-message "The additional SCTP logical interface must be configured under [epg node logical-interface]";
        }
        must '((/epg/pgw/diameter/peer[name=current()/../../name]/logical-interface) and (not (/epg/pgw/diameter/peer[name=current()/../../name][logical-interface=current()]))) or ((not (/epg/pgw/diameter/peer[name=current()/../../name]/logical-interface)) and (not (/epg/node/interface/gom-c[logical-interface=current()])))' {
          error-message "The additional SCTP logical interface can not be the same as the logical interface";
        }
      }
      leaf disable-cross-paths {
        description
          "Disable cross paths for local multihoming";
        type empty;
        must '/epg/pgw/diameter/peer[name=current()/../../name]/sctp/additional-logical-interface' {
          error-message "Requires additionalLogicalInterface to be configured";
        }
        must '/epg/pgw/diameter/number-of-hosts' {
          error-message "Requires numberOfHosts to be configured";
          tailf:dependency "/epg/pgw/diameter/number-of-hosts";
        }
      }
      leaf rto-max {
        description
          "Maximum retransmission timeout in milliseconds";
        type uint32 {
          range "0..4294967295" {
            error-message "Invalid value for attribute 'rto-max'. Valid values are in range:[0,4294967295]";
          }
        }
      }
      leaf rto-min {
        description
          "Minimum retransmission timeout in milliseconds";
        type uint32 {
          range "0..4294967295" {
            error-message "Invalid value for attribute 'rto-min'. Valid values are in range:[0,4294967295]";
          }
        }
      }
      leaf rto-initial {
        description
          "Initial retransmission timeout in milliseconds";
        type uint32 {
          range "0..4294967295" {
            error-message "Invalid value for attribute 'rto-initial'. Valid values are in range:[0,4294967295]";
          }
        }
      }
      leaf hb-interval {
        description
          "Heartbeat interval in milliseconds";
        type uint32 {
          range "0..4294967295" {
            error-message "Invalid value for attribute 'hb-interval'. Valid values are in range:[0,4294967295]";
          }
        }
      }
      leaf path-max-retrans {
        description
          "Maximum number of retransmission attempts on path";
        type uint16 {
          range "0..65535" {
            error-message "Invalid value for attribute 'path-max-retrans'. Valid values are in range:[0,65535]";
          }
        }
      }
      leaf association-max-retrans {
        description
          "Maximum number of retransmission attempts on association";
        type uint16 {
          range "0..65535" {
            error-message "Invalid value for attribute 'association-max-retrans'. Valid values are in range:[0,65535]";
          }
        }
      }
      leaf max-init-retransmits {
        description
          "Maximum number of initial retransmission attempts on path";
        type uint16 {
          range "0..65535" {
            error-message "Invalid value for attribute 'max-init-retransmits'. Valid values are in range:[0,65535]";
          }
        }
      }
      leaf sack-timeout {
        description
          "Maximum time to wait before sending a SACK upon receiving a DATA chunk, in milliseconds";
        type uint16 {
          range "0..500" {
            error-message "Invalid value for attribute 'sack-timeout'. Valid values are in range:[0,500]";
          }
        }
      }
      leaf path-mtu {
        description
          "Maximum transmission unit used for the path in bytes, setting this will disable Path MTU Discovery";
        type uint16 {
          range "512..65535" {
            error-message "Invalid value for attribute 'path-mtu'. Valid values are in range:[512,65535]";
          }
        }
      }
    }
    action status {
      description
        "Show diameter status information for a specific peer";
      output {
        leaf result {
          type string;
          mandatory true;
        }
      }
    }
    action statistics {
      description
        "Show diameter peer statistics";
      output {
        leaf result {
          type string;
          mandatory true;
        }
      }
    }
  }

  grouping diameter-application-system-type {
    leaf name {
      description
        "Diameter application system identifier";
      type string {
        pattern '[.0-9A-Za-z_-]*' {
          error-message "Must contain only letters, numbers, dot, underscores or dashes";
        }
        length "1..64";
      }
    }
    leaf destination-realm {
      description
        "Destination realm";
      type string;
      mandatory true;
    }
    leaf origin-realm {
      description
        "Origin realm";
      type string;
    }
    leaf application-id {
      description
        "vendor-specific application identity";
      type union {
        type enumeration {
          enum gy-ericsson {
            description
              "Online charging protocols based on Ericsson enhanced DCCA application";
          }
          enum gy-3gpp {
            description
              "Online charging protocols based on the DCCA application\\. No support for Ericsson enhanced Gy";
          }
          enum pcc {
            description
              "Policy and charging control over Gx";
          }
          enum s6b {
            description
              "S6b authorization";
          }
          enum rf {
            description
              "Charging over Rf";
          }
        }
        type application-id-application-identifier-choice;
      }
      mandatory true;
    }
    leaf distribution {
      description
        "Request distribution";
      type enumeration {
        enum load-balance {
          description
            "Use load balance to distribute request";
        }
        enum round-robin {
          description
            "Use round robin to distribute request";
        }
        enum weight-based {
          description
            "Use weight based to distribute request";
        }
      }
    }
    leaf-list supported-vendor-id {
      description
        "Supported Vendor Identity";
      type string {
        pattern '((3gpp)|(3gpp2)|(ericsson)|([1-9][0-9]{0,9}))' {
          error-message "Must be of form <3gpp>|<3gpp2>|<ericsson>|<1~4294967295>";
        }
        length "1..10";
      }
      max-elements 64;
    }
    list peer {
      description
        "Diameter peers and priorities";
      key "name";
      leaf name {
        description
          "Diameter peer id";
        type leafref {
          path "/epg/pgw/diameter/peer/name";
        }
        mandatory true;
      }
      leaf priority {
        description
          "Priority of the peer\\. A value from 0 to 255, where a higher value takes precedence.";
        type uint8 {
          range "0..255" {
            error-message "Invalid value for attribute 'priority'. Valid values are in range:[0,255]";
          }
        }
      }
      leaf weight {
        description
          "Weight of the peer\\. A value from 0 to 10, where a higher value takes higher load.";
        type uint8 {
          range "0..10" {
            error-message "Invalid value for attribute 'weight'. Valid values are in range:[0,10]";
          }
        }
      }
    }
    leaf timeout {
      description
        "Communication timeout";
      type string {
        pattern '((0.[1-9])|([1-9])|([1-9].[0-9])|([1-5][0-9])|([1-5][0-9].[0-9])|(60)|(60.0))' {
          error-message "Value must be a number from 0.1 to 60.0";
        }
      }
    }
    leaf request-window-size {
      description
        "Maximum number of outstanding requests";
      type uint16 {
        range "10..32000" {
          error-message "Invalid value for attribute 'request-window-size'. Valid values are in range:[10,32000]";
        }
      }
    }
    leaf requests-per-second {
      description
        "Maximum requests per second";
      type uint16 {
        range "0..5000" {
          error-message "Invalid value for attribute 'requests-per-second'. Valid values are in range:[0,5000]";
        }
      }
    }
    leaf minimum-rtt {
      description
        "Minimum round trip time for diameter request message";
      type string {
        pattern '((0.[1-9])|([1-9])|([1-9].[0-9])|([1-5][0-9])|([1-5][0-9].[0-9]))' {
          error-message "Value must be a number from 0.1 to 59.9";
        }
      }
      must '/epg/pgw/diameter/diameter-application-system[name=current()/../name]/requests-per-second' {
        error-message "Requires requestPerSecond to be configured";
      }
    }
    leaf access-type {
      description
        "Connection type";
      type enumeration {
        enum direct {
          description
            "Direct access to the diameter application server";
        }
        enum agent {
          description
            "The diameter application server is accessed via an agent";
        }
      }
    }
    leaf allow-dynamic-realm {
      description
        "Allow dynamic realm update based on server response";
      type empty;
    }
    leaf ignore-origin-state-id {
      description
        "Ignore origin state id";
      type empty;
    }
    leaf allow-first-non-zero-restart {
      description
        "Allow first non zero origin state id as restart";
      type empty;
    }
    leaf override-avp-flag {
      description
        "Override default M-bit setting in AVP flags";
      type empty;
    }
    leaf use-pecfn-as-destination-host {
      description
        "Use primary-event-charging-function-name as destination-host at OCS selection with agent access";
      type empty;
      must "not (/epg/pgw/diameter/diameter-application-system[name=current()/../name]/access-type[text()='direct'])" {
        error-message "Incompatible with 'access-type direct'";
        tailf:dependency "/epg/pgw/diameter/diameter-application-system/access-type";
      }
      must '/epg/pgw/diameter/diameter-application-system[name=current()/../name]/online-charging-system' {
        error-message "Missing mandatory 'online-charging-system'";
      }
    }
    container diameter-path {
      description
        "Settings for diameter path handling";
      presence "diameter-path need presence";
      leaf failure-threshold {
        description
          "Failure threshold value";
        type uint32 {
          range "1..4294967295" {
            error-message "Invalid value for attribute 'failure-threshold'. Valid values are in range:[1,4294967295]";
          }
        }
        mandatory true;
      }
      leaf recovery-threshold {
        description
          "Recovery threshold value";
        type uint8 {
          range "0..100" {
            error-message "Invalid value for attribute 'recovery-threshold'. Valid values are in range:[0,100]";
          }
        }
        mandatory true;
      }
      leaf failure-timer {
        description
          "Failure timer value";
        type uint32 {
          range "1..86400" {
            error-message "Invalid value for attribute 'failure-timer'. Valid values are in range:[1,86400]";
          }
        }
        mandatory true;
      }
      leaf failure-increment-threshold {
        description
          "Failure increment threshold value";
        type uint32 {
          range "1..10000" {
            error-message "Invalid value for attribute 'failure-increment-threshold'. Valid values are in range:[1,10000]";
          }
        }
      }
      leaf trigger-increment-timer {
        description
          "Trigger increment timer value";
        type uint32 {
          range "1..86400" {
            error-message "Invalid value for attribute 'trigger-increment-timer'. Valid values are in range:[1,86400]";
          }
        }
      }
      leaf failure-increment {
        description
          "Failure increment value";
        type uint32 {
          range "1..3600" {
            error-message "Invalid value for attribute 'failure-increment'. Valid values are in range:[1,3600]";
          }
        }
      }
      leaf monitor-timer {
        description
          "Monitor timer value";
        type uint32 {
          range "61..86400" {
            error-message "Invalid value for attribute 'monitor-timer'. Valid values are in range:[61,86400]";
          }
        }
      }
      leaf-list result-codes {
        description
          "Result codes treated as errors";
        type string {
          pattern '[0-9]{1,10}([-][0-9]{1,10})?' {
            error-message "Must be a result code or a range of result codes.";
          }
          length "1..64";
        }
        max-elements 64;
      }
    }
    leaf routing-message-priority {
      description
        "Enable diameter routing message priority (DRMP) handling of messages";
      type empty;
    }
    list message-type {
      description
        "Message type settings";
      key "name";
      leaf name {
        description
          "Message type name";
        type enumeration {
          enum ccr-initial {
            description
              "Credit Control Request initial";
          }
          enum ccr-update {
            description
              "Credit Control Request update";
          }
          enum ccr-termination {
            description
              "Credit Control Request termination";
          }
          enum ccr-event {
            description
              "Credit Control Request event";
          }
          enum aar {
            description
              "Authentication Authorization Request";
          }
          enum str {
            description
              "Session Termination Request";
          }
          enum acr-start {
            description
              "Accounting Request start";
          }
          enum acr-interim {
            description
              "Accounting Request interim";
          }
          enum acr-stop {
            description
              "Accounting Request stop";
          }
        }
      }
      container retry {
        description
          "Settings for retry of multiple diameter peers";
        presence "retry need presence";
        leaf-list result-code {
          description
            "Result code or result code range to trigger a retry";
          type string {
            pattern '[0-9]{1,10}([-][0-9]{1,10})?' {
              error-message "Must be a result code or a range of result codes.";
            }
            length "1..64";
          }
          max-elements 64;
        }
        leaf max-number-of-retry {
          description
            "Maximum number of times a retry is performed";
          type uint8 {
            range "1..4" {
              error-message "Invalid value for attribute 'max-number-of-retry'. Valid values are in range:[1,4]";
            }
          }
          default "1";
        }
        leaf timeout {
          description
            "Communication failure caused by timeout";
          type empty;
        }
        leaf connection-failure {
          description
            "Communication failure caused by connection-failure";
          type empty;
        }
        leaf use-configured-realm {
          description
            "Use configured destination realm";
          type empty;
        }
      }
    }
    leaf online-charging-system {
      description
        "The FQDN name of the OCS sent from PCRF in AVP 619, that this DAS uses";
      type string;
    }
    action reset-diameter-queue-statistics {
      description
        "Reset max and mean values for Diameter queue statistics towards a DAS.";
      output {
        leaf result {
          type string;
          mandatory true;
        }
      }
    }
    action reset-diameter-paths {
      yexte:user-group "ericsson-support,epg-admin";
      description
        "Reset Diameter paths failure counters, alarms, and timers on this DAS.";
      output {
        leaf result {
          type string;
          mandatory true;
        }
      }
    }
    action status {
      description
        "Show Diameter path failure counters on this DAS.";
      output {
        leaf result {
          type string;
          mandatory true;
        }
      }
    }
    action queue-statistics {
      description
        "Show traffic shaper queue statistics on this DAS.";
      input {
        leaf destination-host {
          description
            "destination hostname";
          type string {
            pattern '[.0-9A-Za-z_-]*' {
              error-message "Must contain only letters, numbers, dot, underscores or dashes";
            }
            length "1..64";
          }
        }
      }
      output {
        leaf result {
          type string;
          mandatory true;
        }
      }
    }
    action path-statistics {
      description
        "Show path statistics towards this DAS\\. A path consists of DAS, peer and destination host.";
      input {
        leaf peer-id {
          description
            "peer identifier";
          type string {
            pattern '[.0-9A-Za-z_-]*' {
              error-message "Must contain only letters, numbers, dot, underscores or dashes";
            }
            length "1..64";
          }
        }
        leaf destination-host {
          description
            "destination hostname";
          type string {
            pattern '[.0-9A-Za-z_-]*' {
              error-message "Must contain only letters, numbers, dot, underscores or dashes";
            }
            length "1..64";
          }
        }
      }
      output {
        leaf result {
          type string;
          mandatory true;
        }
      }
    }
  }

  grouping diameter-node-type {
    container rf {
      description
        "RF Diameter configuration";
      list avp-profile {
        description
          "AVP Profile Name";
        key "name";
        leaf name {
          description
            "AVP Profile Name";
          type string;
        }
        container acr-start {
          description
            "ACR Start Message AVP:s";
          presence "acr-start need presence";
          leaf event-timestamp {
            description
              "Configures the event-timestamp AVP to be included";
            type boolean;
            default "true";
          }
          leaf service-context-id {
            description
              "Configures the service-context-id AVP to be included";
            type boolean;
            default "true";
          }
          leaf subscription-id {
            description
              "Configures the subscription-id AVP to be included";
            type boolean;
            default "true";
          }
          leaf charging-id {
            description
              "Configures the 3GPP-Charging-Id AVP to be included";
            type boolean;
            default "true";
          }
          leaf node-id {
            description
              "Configures the node-id AVP to be included";
            type boolean;
            default "true";
          }
          leaf pdp-type {
            description
              "Configures the 3GPP-PDP-Type AVP to be included";
            type boolean;
            default "true";
          }
          leaf pdp-address {
            description
              "Configures the pdp-address AVP to be included";
            type boolean;
            default "true";
          }
          leaf dynamic-address-flag {
            description
              "Configures the dynamic-address-flag AVP to be included";
            type boolean;
            default "true";
          }
          leaf sgsn-address {
            description
              "Configures the sgsn-address AVP under ps-information to be included";
            type boolean;
            default "true";
          }
          leaf qos-information {
            description
              "Configures the qos-information AVP under ps-information to be included";
            type boolean;
            default "true";
          }
          container qos-information-detail {
            leaf extended-bitrates {
              description
                "Configures the extended-bitrate AVP(s) under qos-information to be included";
              type boolean;
              default "true";
            }
          }
          leaf ggsn-address {
            description
              "Configures the ggsn-address AVP under ps-information to be included";
            type boolean;
            default "true";
          }
          leaf serving-node-type {
            description
              "Configures the serving-node-type AVP to be included";
            type boolean;
            default "true";
          }
          leaf imsi-mcc-mnc {
            description
              "Configures the 3GPP-IMSI-MCC-MNC AVP to be included";
            type boolean;
            default "true";
          }
          leaf ggsn-mcc-mnc {
            description
              "Configures the 3GPP-GGSN-MCC-MNC AVP to be included";
            type boolean;
            default "true";
          }
          leaf called-station-id {
            description
              "Configures the called-station-id AVP to be included";
            type boolean;
            default "true";
          }
          leaf selection-mode {
            description
              "Configures the 3GPP-Selection-Mode AVP to be included";
            type boolean;
            default "true";
          }
          leaf charging-characteristics {
            description
              "Configures the 3GPP-Charging-Characteristics AVP to be included";
            type boolean;
            default "true";
          }
          leaf cc-selection-mode {
            description
              "Configures the charging-characteristics-selection-mode AVP to be included";
            type boolean;
            default "true";
          }
          leaf sgsn-mcc-mnc {
            description
              "Configures the 3GPP-SGSN-MCC-MNC AVP to be included";
            type boolean;
            default "true";
          }
          leaf ms-time-zone {
            description
              "Configures the 3GPP-MS-TimeZone AVP to be included";
            type boolean;
            default "true";
          }
          leaf ims-information {
            description
              "Configures the ims-information AVP to be included";
            type boolean;
            default "true";
          }
          leaf user-location-info {
            description
              "Configures the 3GPP-User-Location-Info AVP to be included";
            type boolean;
            default "true";
          }
          leaf rat-type {
            description
              "Configures the 3GPP-RAT-Type AVP to be included";
            type boolean;
            default "true";
          }
          leaf bs-id {
            description
              "Configures the 3GPP2-BSID under ps-information AVP to be included";
            type boolean;
            default "true";
          }
          leaf imsi-unauthenticated-flag {
            description
              "Configures the imsi-unauthenticated-flag AVP to be included";
            type boolean;
            default "true";
          }
          leaf user-equipment-info {
            description
              "Configures the user-equipment-info AVP to be included";
            type boolean;
            default "true";
          }
          leaf start-time {
            description
              "Configures the start-time AVP to be included";
            type boolean;
            default "true";
          }
          leaf charging-gateway-function-host {
            description
              "Configures the charging-gateway-function-host AVP to be included";
            type boolean;
            default "true";
          }
          leaf charging-group-id {
            description
              "Configures the charging-group-id AVP to be included";
            type boolean;
            default "true";
          }
          leaf uni-pdu-cp-only-flag {
            description
              "Configure UNI PDU CP Only Flag AVP to be included";
            type boolean;
          }
          leaf charging-rule-base-name {
            description
              "Configures the charging-rule-base-name AVP to be included";
            type boolean;
          }
          leaf sgi-ptp-tunneling-method {
            description
              "Configure sgi-ptp-tunneling-method to be included with ACRs";
            type boolean;
          }
          leaf scs-as-address {
            description
              "Configure scs-as-address to be included with ACRs";
            type boolean;
          }
          leaf user-csg-information {
            description
              "Configure User CSG information AVP to be included under PS-Information in ACR-start";
            type boolean;
            default "true";
          }
          leaf credit-control-session-id {
            description
              "Configures the session-id AVP to be included";
            type boolean;
          }
          leaf credit-control-destination-realm {
            description
              "Configures the destination-realm AVP to be included";
            type boolean;
          }
          leaf credit-control-failure-report {
            description
              "Configures the credit-control-failure-report AVP to be included";
            type boolean;
          }
        }
        container acr-interim {
          description
            "ACR Interim Message AVP:s";
          presence "acr-interim need presence";
          leaf event-timestamp {
            description
              "Configures the event-timestamp AVP to be included";
            type boolean;
            default "true";
          }
          leaf service-context-id {
            description
              "Configures the service-context-id AVP to be included";
            type boolean;
            default "true";
          }
          leaf subscription-id {
            description
              "Configures the subscription-id AVP to be included";
            type boolean;
            default "true";
          }
          leaf charging-id {
            description
              "Configures the 3GPP-Charging-Id AVP to be included";
            type boolean;
            default "true";
          }
          leaf node-id {
            description
              "Configures the node-id AVP to be included";
            type boolean;
            default "true";
          }
          leaf pdp-type {
            description
              "Configures the 3GPP-PDP-Type AVP to be included";
            type boolean;
            default "true";
          }
          leaf pdp-address {
            description
              "Configures the pdp-address AVP to be included";
            type boolean;
            default "true";
          }
          leaf dynamic-address-flag {
            description
              "Configures the dynamic-address-flag AVP to be included";
            type boolean;
            default "true";
          }
          leaf sgsn-address {
            description
              "Configures the sgsn-address AVP under ps-information to be included";
            type boolean;
            default "true";
          }
          leaf qos-information {
            description
              "Configures the qos-information AVP under ps-information to be included";
            type boolean;
            default "true";
          }
          container qos-information-detail {
            leaf extended-bitrates {
              description
                "Configures the extended-bitrate AVP(s) under qos-information to be included";
              type boolean;
              default "true";
            }
          }
          leaf ggsn-address {
            description
              "Configures the ggsn-address AVP under ps-information to be included";
            type boolean;
            default "true";
          }
          leaf serving-node-type {
            description
              "Configures the serving-node-type AVP to be included";
            type boolean;
            default "true";
          }
          leaf imsi-mcc-mnc {
            description
              "Configures the 3GPP-IMSI-MCC-MNC AVP to be included";
            type boolean;
            default "true";
          }
          leaf ggsn-mcc-mnc {
            description
              "Configures the 3GPP-GGSN-MCC-MNC AVP to be included";
            type boolean;
            default "true";
          }
          leaf called-station-id {
            description
              "Configures the called-station-id AVP to be included";
            type boolean;
            default "true";
          }
          leaf selection-mode {
            description
              "Configures the 3GPP-Selection-Mode AVP to be included";
            type boolean;
            default "true";
          }
          leaf charging-characteristics {
            description
              "Configures the 3GPP-Charging-Characteristics AVP to be included";
            type boolean;
            default "true";
          }
          leaf cc-selection-mode {
            description
              "Configures the charging-characteristics-selection-mode AVP to be included";
            type boolean;
            default "true";
          }
          leaf sgsn-mcc-mnc {
            description
              "Configures the 3GPP-SGSN-MCC-MNC AVP to be included";
            type boolean;
            default "true";
          }
          leaf ms-time-zone {
            description
              "Configures the 3GPP-MS-TimeZone AVP to be included";
            type boolean;
            default "true";
          }
          leaf ims-information {
            description
              "Configures the ims-information AVP to be included";
            type boolean;
            default "true";
          }
          leaf user-location-info {
            description
              "Configures the 3GPP-User-Location-Info AVP to be included";
            type boolean;
            default "true";
          }
          leaf rat-type {
            description
              "Configures the 3GPP-RAT-Type AVP to be included";
            type boolean;
            default "true";
          }
          leaf bs-id {
            description
              "Configures the 3GPP2-BSID under ps-information AVP to be included";
            type boolean;
            default "true";
          }
          leaf imsi-unauthenticated-flag {
            description
              "Configures the imsi-unauthenticated-flag AVP to be included";
            type boolean;
            default "true";
          }
          leaf user-csg-information {
            description
              "Configure User CSG information AVP to be included under PS-Information in ACR-Interim ";
            type boolean;
            default "true";
          }
          container service-data-container {
            presence "service-data-container need presence";
            leaf accounting-input-octets {
              description
                "Configures the accounting-input-octets AVP to be included";
              type boolean;
              default "true";
            }
            leaf accounting-output-octets {
              description
                "Configures the accounting-output-octets AVP to be included";
              type boolean;
              default "true";
            }
            leaf qos-information {
              description
                "Configures the qos-information AVP under service-data-container to be included";
              type boolean;
              default "true";
            }
            container qos-information-detail {
              leaf apn-ambr {
                description
                  "Configures the apn-ambr AVP under service-data-container/qos-information to be included";
                type boolean;
                default "true";
              }
              leaf extended-bitrates {
                description
                  "Configures the extended-bitrate AVP(s) under service-data-container/qos-information to be included";
                type boolean;
                default "true";
              }
            }
            leaf time-first-usage {
              description
                "Configures the time-first-usage AVP to be included";
              type boolean;
              default "true";
            }
            leaf time-last-usage {
              description
                "Configures the time-last-usage AVP to be included";
              type boolean;
              default "true";
            }
            leaf time-usage {
              description
                "Configures the time-usage AVP to be included";
              type boolean;
            }
            leaf change-time {
              description
                "Configures the change-time AVP to be included";
              type boolean;
              default "true";
            }
            leaf sgsn-address {
              description
                "Configures the sgsn-address AVP under service-data-container to be included";
              type boolean;
              default "true";
            }
            leaf change-condition {
              description
                "Configures the change-condition AVP under service-data-container to be included";
              type boolean;
              default "true";
            }
            leaf user-location-info {
              description
                "Configures the 3GPP-User-Location-Info AVP to be included";
              type boolean;
              default "true";
            }
            leaf cc-request-number {
              description
                "Configures the cc-request-number AVP to be included";
              type boolean;
            }
            leaf credit-control-failure-handling {
              description
                "Configures the credit-control-failure-handling AVP to be included";
              type boolean;
            }
            leaf bs-id {
              description
                "Configures the 3GPP2-BSID AVP under service-data-container to be included";
              type boolean;
              default "true";
            }
            leaf charging-id {
              description
                "Configures the 3GPP-Charging-Id AVP under service-data-container to be included";
              type boolean;
            }
            leaf transaction-report {
              description
                "Include transaction report information.";
              type boolean;
            }
            leaf user-csg-information {
              description
                "Configure User CSG information AVP to be included under SDC in ACR-Interim ";
              type boolean;
              default "true";
            }
          }
          leaf change-condition {
            description
              "Configures the change-condition AVP under ps-information to be included";
            type boolean;
            default "true";
          }
          leaf charging-gateway-function-host {
            description
              "Configures the charging-gateway-function-host AVP to be included";
            type boolean;
            default "true";
          }
          leaf charging-group-id {
            description
              "Configures the charging-group-id AVP to be included";
            type boolean;
            default "true";
          }
          leaf uni-pdu-cp-only-flag {
            description
              "Configure UNI PDU CP Only Flag AVP to be included";
            type boolean;
          }
          leaf user-equipment-info {
            description
              "Configures the user-equipment-info AVP to be included";
            type boolean;
          }
          leaf charging-rule-base-name {
            description
              "Configures the charging-rule-base-name AVP to be included";
            type boolean;
          }
          leaf sgi-ptp-tunneling-method {
            description
              "Configure sgi-ptp-tunneling-method to be included with ACRs";
            type boolean;
          }
          leaf scs-as-address {
            description
              "Configure scs-as-address to be included with ACRs";
            type boolean;
          }
          leaf credit-control-session-id {
            description
              "Configures the session-id AVP to be included";
            type boolean;
          }
          leaf credit-control-destination-realm {
            description
              "Configures the destination-realm AVP to be included";
            type boolean;
          }
          leaf credit-control-failure-report {
            description
              "Configures the credit-control-failure-report AVP to be included";
            type boolean;
          }
          leaf list-of-ran-secondary-rat-usage-reports {
            description
              "Configures the List of RAN Secondary RAT Usage Reports AVP to be included in ACR-interim";
            type boolean;
          }
        }
        container acr-stop {
          description
            "ACR Stop Message AVP:s";
          presence "acr-stop need presence";
          leaf event-timestamp {
            description
              "Configures the event-timestamp AVP to be included";
            type boolean;
            default "true";
          }
          leaf service-context-id {
            description
              "Configures the service-context-id AVP to be included";
            type boolean;
            default "true";
          }
          leaf subscription-id {
            description
              "Configures the subscription-id AVP to be included";
            type boolean;
            default "true";
          }
          leaf charging-id {
            description
              "Configures the 3GPP-Charging-Id AVP to be included";
            type boolean;
            default "true";
          }
          leaf node-id {
            description
              "Configures the node-id AVP to be included";
            type boolean;
            default "true";
          }
          leaf pdp-type {
            description
              "Configures the 3GPP-PDP-Type AVP to be included";
            type boolean;
            default "true";
          }
          leaf pdp-address {
            description
              "Configures the pdp-address AVP to be included";
            type boolean;
            default "true";
          }
          leaf dynamic-address-flag {
            description
              "Configures the dynamic-address-flag AVP to be included";
            type boolean;
            default "true";
          }
          leaf sgsn-address {
            description
              "Configures the sgsn-address AVP under ps-information to be included";
            type boolean;
            default "true";
          }
          leaf qos-information {
            description
              "Configures the qos-information AVP under ps-information to be included";
            type boolean;
            default "true";
          }
          container qos-information-detail {
            leaf extended-bitrates {
              description
                "Configures the extended-bitrate AVP(s) under qos-information to be included";
              type boolean;
              default "true";
            }
          }
          leaf ggsn-address {
            description
              "Configures the ggsn-address AVP under ps-information to be included";
            type boolean;
            default "true";
          }
          leaf serving-node-type {
            description
              "Configures the serving-node-type AVP to be included";
            type boolean;
            default "true";
          }
          leaf imsi-mcc-mnc {
            description
              "Configures the 3GPP-IMSI-MCC-MNC AVP to be included";
            type boolean;
            default "true";
          }
          leaf ggsn-mcc-mnc {
            description
              "Configures the 3GPP-GGSN-MCC-MNC AVP to be included";
            type boolean;
            default "true";
          }
          leaf called-station-id {
            description
              "Configures the called-station-id AVP to be included";
            type boolean;
            default "true";
          }
          leaf selection-mode {
            description
              "Configures the 3GPP-Selection-Mode AVP to be included";
            type boolean;
            default "true";
          }
          leaf charging-characteristics {
            description
              "Configures the 3GPP-Charging-Characteristics AVP to be included";
            type boolean;
            default "true";
          }
          leaf cc-selection-mode {
            description
              "Configures the charging-characteristics-selection-mode AVP to be included";
            type boolean;
            default "true";
          }
          leaf sgsn-mcc-mnc {
            description
              "Configures the 3GPP-SGSN-MCC-MNC AVP to be included";
            type boolean;
            default "true";
          }
          leaf ms-time-zone {
            description
              "Configures the 3GPP-MS-TimeZone AVP to be included";
            type boolean;
            default "true";
          }
          leaf ims-information {
            description
              "Configures the ims-information AVP to be included";
            type boolean;
            default "true";
          }
          leaf user-location-info {
            description
              "Configures the 3GPP-User-Location-Info AVP to be included";
            type boolean;
            default "true";
          }
          leaf rat-type {
            description
              "Configures the 3GPP-RAT-Type AVP to be included";
            type boolean;
            default "true";
          }
          leaf bs-id {
            description
              "Configures the 3GPP2-BSID under ps-information AVP to be included";
            type boolean;
            default "true";
          }
          leaf imsi-unauthenticated-flag {
            description
              "Configures the imsi-unauthenticated-flag AVP to be included";
            type boolean;
            default "true";
          }
          leaf user-csg-information {
            description
              "Configure User CSG information AVP to be included under PS-Information in ACR-stop ";
            type boolean;
            default "true";
          }
          container service-data-container {
            presence "service-data-container need presence";
            leaf accounting-input-octets {
              description
                "Configures the accounting-input-octets AVP to be included";
              type boolean;
              default "true";
            }
            leaf accounting-output-octets {
              description
                "Configures the accounting-output-octets AVP to be included";
              type boolean;
              default "true";
            }
            leaf qos-information {
              description
                "Configures the qos-information AVP under service-data-container to be included";
              type boolean;
              default "true";
            }
            container qos-information-detail {
              leaf apn-ambr {
                description
                  "Configures the apn-ambr AVP under service-data-container/qos-information to be included";
                type boolean;
                default "true";
              }
              leaf extended-bitrates {
                description
                  "Configures the extended-bitrate AVP(s) under service-data-container/qos-information to be included";
                type boolean;
                default "true";
              }
            }
            leaf time-first-usage {
              description
                "Configures the time-first-usage AVP to be included";
              type boolean;
              default "true";
            }
            leaf time-last-usage {
              description
                "Configures the time-last-usage AVP to be included";
              type boolean;
              default "true";
            }
            leaf time-usage {
              description
                "Configures the time-usage AVP to be included";
              type boolean;
            }
            leaf change-time {
              description
                "Configures the change-time AVP to be included";
              type boolean;
              default "true";
            }
            leaf sgsn-address {
              description
                "Configures the sgsn-address AVP under service-data-container to be included";
              type boolean;
              default "true";
            }
            leaf change-condition {
              description
                "Configures the change-condition AVP under service-data-container to be included";
              type boolean;
              default "true";
            }
            leaf user-location-info {
              description
                "Configures the 3GPP-User-Location-Info AVP to be included";
              type boolean;
              default "true";
            }
            leaf cc-request-number {
              description
                "Configures the cc-request-number AVP to be included";
              type boolean;
            }
            leaf credit-control-failure-handling {
              description
                "Configures the credit-control-failure-handling AVP to be included";
              type boolean;
            }
            leaf bs-id {
              description
                "Configures the 3GPP2-BSID AVP under service-data-container to be included";
              type boolean;
              default "true";
            }
            leaf charging-id {
              description
                "Configures the 3GPP-Charging-Id AVP under service-data-container to be included";
              type boolean;
            }
            leaf transaction-report {
              description
                "Include transaction report information.";
              type boolean;
            }
            leaf user-csg-information {
              description
                "Configure User CSG information AVP to be included under SDC in ACR-Stop ";
              type boolean;
              default "true";
            }
          }
          leaf stop-time {
            description
              "Configures the stop-time AVP to be included";
            type boolean;
            default "true";
          }
          leaf diagnostics {
            description
              "Configures the Diagnostics AVP to be included";
            type boolean;
            default "true";
          }
          leaf change-condition {
            description
              "Configures the change-condition AVP under ps-information to be included";
            type boolean;
            default "true";
          }
          leaf charging-gateway-function-host {
            description
              "Configures the charging-gateway-function-host AVP to be included";
            type boolean;
            default "true";
          }
          leaf charging-group-id {
            description
              "Configures the charging-group-id AVP to be included";
            type boolean;
            default "true";
          }
          leaf uni-pdu-cp-only-flag {
            description
              "Configure UNI PDU CP Only Flag AVP to be included";
            type boolean;
          }
          leaf user-equipment-info {
            description
              "Configures the user-equipment-info AVP to be included";
            type boolean;
          }
          leaf charging-rule-base-name {
            description
              "Configures the charging-rule-base-name AVP to be included";
            type boolean;
          }
          leaf sgi-ptp-tunneling-method {
            description
              "Configure sgi-ptp-tunneling-method to be included with ACRs";
            type boolean;
          }
          leaf scs-as-address {
            description
              "Configure scs-as-address to be included with ACRs";
            type boolean;
          }
          leaf credit-control-session-id {
            description
              "Configures the session-id AVP to be included";
            type boolean;
          }
          leaf credit-control-destination-realm {
            description
              "Configures the destination-realm AVP to be included";
            type boolean;
          }
          leaf credit-control-failure-report {
            description
              "Configures the credit-control-failure-report AVP to be included";
            type boolean;
          }
          leaf list-of-ran-secondary-rat-usage-reports {
            description
              "Configures the List of RAN Secondary RAT Usage Reports AVP to be included in ACR-stop";
            type boolean;
          }
        }
      }
    }
    leaf realm {
      description
        "Origin realm for Diameter messages";
      type string;
      mandatory true;
    }
    leaf host-name {
      description
        "Host name for Diameter messages";
      type string {
        pattern '[.0-9A-Za-z_-]*' {
          error-message "Must contain only letters, numbers, dot, underscores or dashes";
        }
        length "1..128";
      }
      mandatory true;
    }
    list host {
      description
        "Diameter host table";
      max-elements 63;
      key "name";
      uses diameter-host-type;
    }
    list peer {
      description
        "Diameter peer";
      max-elements 64;
      key "name";
      uses diameter-peer-type;
    }
    list diameter-application-system {
      description
        "Diameter application system";
      must '/epg/pgw/diameter/diameter-application-system[name=current()/name]/peer' {
        error-message "peer is mandatory";
      }
      max-elements 32;
      key "name";
      uses diameter-application-system-type;
    }
    action reset-paths {
      yexte:user-group "ericsson-support,epg-admin";
      description
        "Reset all diameter path counters";
      output {
        leaf result {
          type string;
          mandatory true;
        }
      }
    }
    action status-paths {
      description
        "Show diameter path status information";
      output {
        leaf result {
          type string;
          mandatory true;
        }
      }
    }
    leaf short-session-id {
      description
        "No start time in the optional part of session id";
      type empty;
    }
    leaf number-of-hosts {
      description
        "Number of hosts";
      type uint8 {
        range "1..64" {
          error-message "Invalid value for attribute 'number-of-hosts'. Valid values are in range:[1,64]";
        }
      }
    }
    leaf block-number-of-hosts {
      description
        "Amount of blocked [epg pgw diameter] number-of-hosts";
      type uint8 {
        range "0..63" {
          error-message "Invalid value for attribute 'block-number-of-hosts'. Valid values are in range:[0,63]";
        }
      }
      must '/epg/pgw/diameter/number-of-hosts' {
        error-message "Number of hosts must be configured under [epg pgw diameter number-of-hosts]";
        tailf:dependency "/epg/pgw/diameter/number-of-hosts";
      }
    }
    leaf ignore-origin-state-id-decrease {
      description
        "Ignore origin state id decrease";
      type empty;
    }
    leaf dscp {
      description
        "DiffServ DSCP for Diameter packets";
      type enumeration {
        enum af11 {
          description
            "Assured forwarding class 1, low drop precedence";
        }
        enum af12 {
          description
            "Assured forwarding class 1, medium drop precedence";
        }
        enum af13 {
          description
            "Assured forwarding class 1, high drop precedence";
        }
        enum af21 {
          description
            "Assured forwarding class 2, low drop precedence";
        }
        enum af22 {
          description
            "Assured forwarding class 2, medium drop precedence";
        }
        enum af23 {
          description
            "Assured forwarding class 2, high drop precedence";
        }
        enum af31 {
          description
            "Assured forwarding class 3, low drop precedence";
        }
        enum af32 {
          description
            "Assured forwarding class 3, medium drop precedence";
        }
        enum af33 {
          description
            "Assured forwarding class 3, high drop precedence";
        }
        enum af41 {
          description
            "Assured forwarding class 4, low drop precedence";
        }
        enum af42 {
          description
            "Assured forwarding class 4, medium drop precedence";
        }
        enum af43 {
          description
            "Assured forwarding class 4, high drop precedence";
        }
        enum ef {
          description
            "Expedited forwarding";
        }
        enum be {
          description
            "Best effort forwarding";
        }
        enum cs1 {
          description
            "Class selector 1";
        }
        enum cs2 {
          description
            "Class selector 2";
        }
        enum cs3 {
          description
            "Class selector 3";
        }
        enum cs4 {
          description
            "Class selector 4";
        }
        enum cs5 {
          description
            "Class selector 5";
        }
        enum cs6 {
          description
            "Class selector 6";
        }
        enum cs7 {
          description
            "Class selector 7";
        }
      }
    }
  }

  grouping service-function-adaptor-type {
    leaf name {
      description
        "Adaptor identifier";
      type string {
        pattern '[0-9A-Za-z][0-9A-Za-z_-]*' {
          error-message "Must be a string beginning with a number or letter and consisting of letters, numbers, dashes and underscores.";
        }
        length "1..31";
      }
    }
    leaf type {
      description
        "Adaptor type";
      type enumeration {
        enum network-l2 {
          description
            "L2 adaptor";
        }
      }
      default "network-l2";
      must "not ((../../adaptor[name=current()/../name]/type[text()='network-l2']) and (not (../../adaptor[name=current()/../name]/interface-io)))" {
        error-message "interface-io must be configured.";
        tailf:dependency "../../adaptor/type";
      }
    }
    container interface-io {
      description
        "Adaptor's interface settings";
      must "../../adaptor[name=current()/../name]/type[text()='network-l2']" {
        error-message "interface-io can only be configured if adaptor is network-l2 type";
        tailf:dependency "../../adaptor/type";
      }
      presence "interface-io need presence";
      leaf type {
        description
          "Interface type";
        type enumeration {
          enum rts {
            description
              "Return to sender adaptor";
          }
          enum dual-transparent {
            description
              "Dual port adaptor.";
          }
        }
        default "rts";
        must "not ((../../../adaptor[name=current()/../../name]/interface-io/type[text()='rts']) and (not (../../../adaptor[name=current()/../../name]/interface-io/single)))" {
          error-message "single interface must be configured";
          tailf:dependency "../../../adaptor/interface-io/type";
        }
        must "not ((../../../adaptor[name=current()/../../name]/interface-io/type[text()='dual-transparent']) and (not ((../../../adaptor[name=current()/../../name]/interface-io/ran) and (../../../adaptor[name=current()/../../name]/interface-io/internet))))" {
          error-message "Both ran and internet interfaces must be configured";
          tailf:dependency "../../../adaptor/interface-io/type";
        }
      }
      leaf single {
        description
          "Single port identifier";
        type string;
        must "../../../adaptor[name=current()/../../name]/interface-io/type[text()='rts']" {
          error-message "Single port identifier can only be set if interface-io is rts";
          tailf:dependency "../../../adaptor/interface-io/type";
        }
      }
      leaf ran {
        description
          "RAN port identifier";
        type string;
        must "../../../adaptor[name=current()/../../name]/interface-io/type[text()='dual-transparent']" {
          error-message "RAN port identifier can only be set if interface-io is dual-transparent";
          tailf:dependency "../../../adaptor/interface-io/type";
        }
      }
      leaf internet {
        description
          "Internet port identifier";
        type string;
        must "../../../adaptor[name=current()/../../name]/interface-io/type[text()='dual-transparent']" {
          error-message "Internet port identifier can only be set if interface-io is dual-transparent";
          tailf:dependency "../../../adaptor/interface-io/type";
        }
      }
    }
    container vlan {
      description
        "vlan tags";
      presence "vlan need presence";
      leaf ran {
        description
          "RAN side vlan tag value";
        type uint16 {
          range "1..4094" {
            error-message "Invalid value for attribute 'ran'. Valid values are in range:[1,4094]";
          }
        }
        mandatory true;
      }
      leaf internet {
        description
          "Internet side vlan tag value";
        type uint16 {
          range "1..4094" {
            error-message "Invalid value for attribute 'internet'. Valid values are in range:[1,4094]";
          }
        }
        mandatory true;
      }
      must "not (../interface-io/type='dual-transparent')" {
        error-message "vlan traffic shall be defined at sfi level (not adaptor) when dual-transparent interface-io adaptor is used";
      }
    }
    container monitoring {
      leaf type {
        description
          "Monitoring mode";
        type enumeration {
          enum arp {
            description
              "ARP monitoring";
          }
          enum udp {
            description
              "UDP monitoring";
          }
          enum custom-traffic {
            description
              "Custom traffic monitoring";
          }
        }
        default "arp";
        must "not ((../../../adaptor[name=current()/../../name]/monitoring/type[text()='arp']) and (../../../adaptor[name=current()/../../name]/interface-io/type[text()='dual-transparent']))" {
          error-message "arp monitoring type can't be set if interface-io is dual-transparent";
          tailf:dependency "../../monitoring/type";
          tailf:dependency "../../interface-io/type";
        }
        must "not ((../../../adaptor[name=current()/../../name]/monitoring/type[text()='udp']) and (../../../adaptor[name=current()/../../name]/interface-io/type[text()='dual-transparent']))" {
          error-message "udp monitoring type can't be set if interface-io is dual-transparent";
          tailf:dependency "../../monitoring/type";
          tailf:dependency "../../interface-io/type";
        }
        must "not ((../../../adaptor[name=current()/../../name]/monitoring/type[text()='udp']) and (not (../../../adaptor[name=current()/../../name]/monitoring/port)))" {
          error-message "port must be configured if monitoring type is udp";
          tailf:dependency "../../monitoring/type";
        }
        must "not ((../../../adaptor[name=current()/../../name]/monitoring/type[text()='custom-traffic']) and (not (../../../adaptor[name=current()/../../name]/monitoring/port)))" {
          error-message "port must be configured if monitoring type is custom-traffic";
          tailf:dependency "../../monitoring/type";
        }
      }
      leaf port {
        description
          "Monitoring port";
        type uint16;
        must "(../../../adaptor[name=current()/../../name]/monitoring/type[text()='udp']) or (../../../adaptor[name=current()/../../name]/monitoring/type[text()='custom-traffic'])" {
          error-message "Port can only be set if monitoring type is udp";
          tailf:dependency "../../monitoring/type";
        }
      }
      leaf interval {
        description
          "Monitoring interval time";
        type uint8 {
          range "1..30" {
            error-message "Invalid value for attribute 'interval'. Valid values are in range:[1,30]";
          }
        }
        default "5";
      }
      container vlan {
        description
          "vlan tags for monitoring";
        presence "vlan need presence";
        leaf ran {
          description
            "RAN side vlan tag value";
          type uint16 {
            range "1..4094" {
              error-message "Invalid value for attribute 'ran'. Valid values are in range:[1,4094]";
            }
          }
          mandatory true;
        }
        leaf internet {
          description
            "Internet side vlan tag value";
          type uint16 {
            range "1..4094" {
              error-message "Invalid value for attribute 'internet'. Valid values are in range:[1,4094]";
            }
          }
          mandatory true;
        }
      }
      container custom-traffic {
        description
          "Custom traffic monitoring settings";
        must "(../../../adaptor[name=current()/../../name]/monitoring/type[text()='custom-traffic']) and (../../../adaptor[name=current()/../../name]/monitoring/port)" {
          error-message "Custom traffic monitoring settings can only be set if monitoring type is custom-traffic and port is set";
          tailf:dependency "../../monitoring/type";
        }
        presence "custom-traffic need presence";
        leaf src-network-address {
          description
            "Source network address";
          type inet:ip-address;
        }
        leaf dst-network-address {
          description
            "Destination network address";
          type inet:ip-address;
        }
      }
    }
  }

  grouping service-function-instance-type {
    leaf name {
      description
        "Service function instance identifier";
      type string {
        pattern '[0-9A-Za-z][0-9A-Za-z_-]*' {
          error-message "Must be a string beginning with a number or letter and consisting of letters, numbers, dashes and underscores.";
        }
        length "1..31";
      }
    }
    leaf group {
      description
        "Group identifier";
      type string {
        pattern '[0-9A-Za-z][0-9A-Za-z_-]*' {
          error-message "Must be a string beginning with a number or letter and consisting of letters, numbers, dashes and underscores.";
        }
        length "1..31";
      }
      mandatory true;
      must '../../../service-function[name=current()/../../name]/group[name=current()]' {
        error-message "Group id must be configured under [epg user-plane service-chaining service-function group]";
      }
    }
    leaf network-address {
      description
        "Service function instance ipv4 network address";
      type inet:ip-address;
    }
    leaf ipv6-network-address {
      status current {
        yexte:preliminary;
      }
      description
        "Service function instance ipv6 network address";
      type inet:ipv6-address;
    }
    container vlan {
      description
        "vlan settings";
      presence "vlan need presence";
      leaf ran {
        description
          "RAN side vlan tag value";
        type uint16 {
          range "1..4094" {
            error-message "Invalid value for attribute 'ran'. Valid values are in range:[1,4094]";
          }
        }
        mandatory true;
      }
      leaf internet {
        description
          "Internet side vlan tag value";
        type uint16 {
          range "1..4094" {
            error-message "Invalid value for attribute 'internet'. Valid values are in range:[1,4094]";
          }
        }
        mandatory true;
      }
      must "../../../adaptor[name=current()/../../group[name=current()/../group]/adaptor]/interface-io/type='dual-transparent'" {
        error-message "vlan traffic shall be defined at sfi level (not adaptor) when dual-transparent interface-io adaptor is used";
      }
    }
  }

  grouping service-function-group-type {
    leaf name {
      description
        "Group identifier";
      type string {
        pattern '[0-9A-Za-z][0-9A-Za-z_-]*' {
          error-message "Must be a string beginning with a number or letter and consisting of letters, numbers, dashes and underscores.";
        }
        length "1..31";
      }
    }
    leaf adaptor {
      description
        "Adaptor identifier";
      type string {
        pattern '[0-9A-Za-z][0-9A-Za-z_-]*' {
          error-message "Must be a string beginning with a number or letter and consisting of letters, numbers, dashes and underscores.";
        }
        length "1..31";
      }
      mandatory true;
      must '../../../adaptor[name=current()]' {
        error-message "Adaptor id must be configured under [epg user-plane service-chaining adaptor]";
      }
    }
    leaf-list network-prefix {
      description
        "Network ip prefix";
      type eipv4-prefix-optional;
      max-elements 1;
      must '(count(../../sfi/group=current()/../name) = 0)' {
        error-message "Multiple ways of identification of service function instance. Only one method shall be used: specific network address, specific vlan, or service function network range.";
        tailf:dependency "../../sfi";
      }
    }
    leaf-list ipv6-network-prefix {
      status current {
        yexte:preliminary;
      }
      description
        "Network ipv6 prefix";
      type eipv6-prefix-optional;
      max-elements 1;
    }
    leaf failure-handling-instance {
      description
        "Failure handling mode";
      type enumeration {
        enum drop {
          description
            "Drop packets";
        }
        enum bypass {
          description
            "Bypass packets";
        }
        enum rebalance {
          description
            "Rebalance";
        }
      }
      default "bypass";
    }
    container load-balancer {
      description
        "Load balancer settings";
      leaf mode {
        description
          "Load balancer mode";
        type enumeration {
          enum subscriber {
            description
              "per-subscriber load-balancing";
          }
          enum session {
            description
              "Per pdu-connection load-balancing";
          }
        }
        default "session";
      }
      leaf weight {
        status current {
          yexte:preliminary;
        }
        description
          "Load balancer instance weight (percentage)";
        type uint8 {
          range "1..100" {
            error-message "Invalid value for attribute 'weight'. Valid values are in range:[1,100]";
          }
        }
        default "100";
      }
    }
  }

  grouping service-function-name-type {
    leaf name {
      description
        "Service function identifier";
      type string {
        pattern '[0-9A-Za-z][0-9A-Za-z_-]*' {
          error-message "Must be a string beginning with a number or letter and consisting of letters, numbers, dashes and underscores.";
        }
        length "1..31";
      }
    }
    leaf failure-handling {
      description
        "Failure handling mode";
      type enumeration {
        enum drop {
          description
            "Drop packets";
        }
        enum bypass {
          description
            "Bypass packets";
        }
      }
      default "bypass";
    }
    list group {
      max-elements 1;
      key "name";
      uses service-function-group-type;
    }
    list sfi {
      max-elements 256;
      key "name";
      uses service-function-instance-type;
    }
    action status {
      description
        "Show Service Function status";
      input {
        leaf level {
          description
            "Detailing level for the information.";
          type enumeration {
            enum brief {
              description
                "Show brief information (default).";
            }
            enum detail {
              description
                "Show detailed information.";
            }
          }
          default "brief";
        }
        leaf board {
          description
            "Show status only from board (e.g. gu-0/5/1)";
          type string {
            pattern '(gu-0/(30|(1|2)[0-9]|[1-9])/1)' {
              error-message "Invalid board name";
            }
          }
        }
      }
      output {
        leaf result {
          type string;
          mandatory true;
        }
      }
    }
    container unknown-flows {
      status current {
        yexte:preliminary;
      }
      description
        "DNAT proxy configuration";
      list via {
        status current {
          yexte:preliminary;
        }
        description
          "Network Instance to which matched dest-ip traffic will be sent.";
        must '(./default) or (./dst-ip)' {
          error-message "default or dst-ip list must be configured";
        }
        key "name";
        max-elements 64;
        leaf name {
          status current {
            yexte:preliminary;
          }
          description
            "Network Instance to which traffic will be sent.";
          type string {
            pattern '[.0-9A-Za-z-]{1,100}' {
              error-message "Must be a string of 100 or fewer characters and may contain letters, numbers, decimals and dashes.";
            }
          }
          must '/epg/user-plane/network-instance[name=current()]' {
            error-message "Network instance must be configured under epg user-plane network-instance";
          }
        }
        leaf default {
          status current {
            yexte:preliminary;
          }
          description
            "Default network instance for all unknown uplink flows.";
          type empty;
          must ' not (../dst-ip)' {
            error-message "Default NI cannot have dst-ip list";
          }
        }
        leaf-list dst-ip {
          status current {
            yexte:preliminary;
          }
          description
            "Range of addresses for link network endpoints";
          type eipv4-prefix-optional;
        }
      }
    }
  }

  grouping service-chaining-profile-type {
    leaf name {
      description
        "Service chaining profile identifier";
      type string {
        length "1..64";
      }
    }
    list action {
      description
        "Profile action settings";
      max-elements 64;
      must '(service-chain/uplink) or (service-chain/downlink)' {
        error-message "Action must contain at least 'service-chain uplink' or 'service-chain downlink'";
      }
      key "name";
      leaf name {
        description
          "Profile action identifier";
        type string {
          length "1..64";
        }
      }
      container service-chain {
        leaf uplink {
          description
            "Default uplink service chain identifier";
          type string {
            length "1..255";
          }
        }
        leaf downlink {
          description
            "Default downlink service chain identifier";
          type string {
            length "1..255";
          }
        }
      }
    }
    leaf default-action {
      description
        "Profile default action";
      type leafref {
        path "../action/name";
      }
    }
    list condition {
      description
        "Profile condition settings";
      max-elements 64;
      must 'custom-attribute' {
        error-message "custom-attribute must be configured for condition";
      }
      key "name";
      leaf name {
        description
          "Profile condition identifier";
        type string {
          length "1..64";
        }
      }
      leaf priority {
        description
          "Priority value for the condition, where a lower value has precedence";
        type uint8 {
          range "1..64" {
            error-message "Invalid value for attribute 'priority'. Valid values are in range:[1,64]";
          }
        }
        mandatory true;
        must 'count(/epg/pgw/packet-enforcement/service-chaining/profile[name=current()/../../name]/condition[priority=current()])=1' {
          error-message "Priority must be unique among all conditions that are part of a service-chaining profile";
        }
      }
      leaf action {
        description
          "Action to be taken when condition is met";
        type leafref {
          path "../../action/name";
        }
        mandatory true;
      }
      list custom-attribute {
        description
          "Custom attribute match criteria";
        max-elements 1;
        key "name";
        leaf name {
          description
            "Custom attribute identifier";
          type string {
            length "1..64";
          }
        }
        choice matcher {
          mandatory true;
          leaf is {
            description
              "Custom attribute value equals";
            type string {
              length "1..255";
            }
          }
          leaf contains {
            description
              "Custom attribute value contains";
            type string {
              length "1..255";
            }
          }
          leaf any {
            description
              "Custom attribute value is present";
            type empty;
          }
        }
      }
    }
  }

  grouping service-chain-name-type {
    leaf name {
      description
        "Service chain identifier";
      type string {
        pattern '[0-9A-Za-z][0-9A-Za-z_-]*' {
          error-message "Must be a string beginning with a number or letter and consisting of letters, numbers, dashes and underscores.";
        }
        length "1..31";
      }
    }
    leaf-list service-function {
      description
        "Service function id.";
      type string {
        length "1..31";
      }
      min-elements 1;
      max-elements 16;
      ordered-by user;
      must '../../service-function[name=current()]' {
        error-message "Service function must be configured under [epg user-plane service-chaining service-function]";
      }
    }
    action status {
      description
        "Show status of the service functions within this service chain";
      input {
        leaf level {
          description
            "Detailing level for the information.";
          type enumeration {
            enum brief {
              description
                "Show brief information (default).";
            }
            enum detail {
              description
                "Show detailed information.";
            }
          }
          default "brief";
        }
        leaf board {
          description
            "Show status only from board (e.g. gu-0/5/1)";
          type string {
            pattern '(gu-0/(30|(1|2)[0-9]|[1-9])/1)' {
              error-message "Invalid board name";
            }
          }
        }
      }
      output {
        leaf result {
          type string;
          mandatory true;
        }
      }
    }
  }

  grouping service-chaining-type {
    list service-chain {
      max-elements 32;
      key "name";
      uses service-chain-name-type;
    }
    list service-function {
      must '../service-function[name=current()/name]/group' {
        error-message "group is mandatory";
      }
      max-elements 32;
      key "name";
      uses service-function-name-type;
      list filter {
        status current;
        max-elements 32;
        key "name";
        leaf name {
          status current;
          description
            "Filter name";
          type string {
            pattern '[0-9A-Za-z][0-9A-Za-z_-]*' {
              error-message "Must be a string beginning with a number or letter and consisting of letters, numbers, dashes and underscores.";
            }
            length "1..63";
          }
        }
        leaf-list network-port {
          status current;
          description
            "Match network port";
          type string {
            pattern '((([1-9](([0-9]){0,3}))|([1-5](([0-9]){0,4}))|(6[0-4]([0-9]{3}))|(65[0-4]([0-9]{2}))|(655[0-2][0-9])|6553[0-5]))' {
              error-message "Value must be a number from 1 to 65535";
            }
          }
          max-elements 10;
        }
        container protocol {
          status current;
          description
            "Protocol to match";
          presence "protocol need presence";
          choice proto-choice {
            leaf tcp {
              status current;
              description
                "Transmission control protocol";
              type empty;
            }
            leaf udp {
              status current;
              description
                "User datagram protocol";
              type empty;
            }
          }
        }
      }
    }
    list adaptor {
      max-elements 16;
      key "name";
      uses service-function-adaptor-type;
    }
    list interface-io {
      description
        "HMS routing-instance definitions.";
      leaf name {
        description
          "interface-io identifier.";
        type string {
          pattern '[0-9A-Za-z][0-9A-Za-z_-]*' {
            error-message "Must be a string beginning with a number or letter and consisting of letters, numbers, dashes and underscores.";
          }
          length "1..63";
        }
        must 'not (/epg/node/direct-io/routing-instance[name=current()])' {
          error-message "interface-io identifier is already used as direct-io routing-instance";
        }
      }
      key "name";
      max-elements 32;
      leaf link-network-address-range {
        description
          "Range of addresses for link network endpoints";
        type eipv4-prefix-optional;
        mandatory true;
      }
      leaf-list port {
        description
          "List of physical ports that should be grouped in this interface-io";
        type uint8 {
          range "0..7" {
            error-message "Invalid value for attribute 'port'. Valid values are in range:[0,7]";
          }
        }
        min-elements 1;
        max-elements 1;
      }
      leaf internal {
        description
          "Port is used for internal (tight) service functions";
        type empty;
      }
    }
    container default {
      leaf downlink {
        description
          "Default service chain identifier for downlink initiated traffic.";
        type string {
          pattern '[0-9A-Za-z][0-9A-Za-z_-]*' {
            error-message "Must be a string beginning with a number or letter and consisting of letters, numbers, dashes and underscores.";
          }
          length "1..31";
        }
        must '../../service-chain[name=current()]' {
          error-message "Service chain identifier must be configured under [epg user-plane service-chaining service-chain]";
        }
      }
    }
    action statistics {
      description
        "Show Service Chaining statistics";
      input {
        leaf network-instance {
          description
            "Network Instance";
          type string {
            pattern '[.0-9A-Za-z_-]*' {
              error-message "Must contain only letters, numbers, underscores or dashes";
            }
            length "1..255";
          }
        }
      }
      output {
        leaf result {
          type string;
          mandatory true;
        }
      }
    }
    action show-neighbors {
      description
        "Show neighbor cache that maps L3 to L2 addresses";
      input {
        leaf board {
          description
            "Show statistics only from board (e.g\\. gu-0/5/1)";
          type string {
            pattern '(gu-0/(30|(1|2)[0-9]|[1-9])/1)' {
              error-message "Invalid board name";
            }
          }
        }
      }
      output {
        leaf result {
          type string;
          mandatory true;
        }
      }
    }
    action status {
      description
        "Show status of all service functions";
      input {
        leaf level {
          description
            "Detailing level for the information.";
          type enumeration {
            enum brief {
              description
                "Show brief information (default).";
            }
            enum detail {
              description
                "Show detailed information.";
            }
          }
          default "brief";
        }
        leaf board {
          description
            "Show status only from board (e.g. gu-0/5/1)";
          type string {
            pattern '(gu-0/(30|(1|2)[0-9]|[1-9])/1)' {
              error-message "Invalid board name";
            }
          }
        }
      }
      output {
        leaf result {
          type string;
          mandatory true;
        }
      }
    }
  }

  grouping rf-charging-configuration-type {
    leaf diameter-application-system {
      description
        "Diameter application system";
      type leafref {
        path "/epg/pgw/diameter/diameter-application-system/name";
      }
      mandatory true;
    }
    leaf avp-profile {
      description
        "Reference to an Avp Profile configured under the Diameter Interface";
      type leafref {
        path "/epg/pgw/diameter/rf/avp-profile/name";
      }
    }
    leaf acr-interim-interval {
      description
        "Interval in minutes for generating ACR interim";
      type uint16 {
        range "1..1440" {
          error-message "Invalid value for attribute 'acr-interim-interval'. Valid values are in range:[1,1440]";
        }
      }
    }
  }

  grouping deprecated-tariff-type {
    leaf name {
      description
        "Tariff time index";
      type uint8 {
        range "1..24" {
          error-message "Invalid value for attribute 'index'. Valid values are in range:[1,24]";
        }
      }
    }
    leaf starts {
      description
        "Local time that the new tariff is activated";
      type string {
        pattern '(((0|1)[0-9])|(2[0-3])):(00|15|30|45)' {
          error-message "Must be a twenty-four hour local time given in 15-minute increments";
        }
      }
    }
  }

  grouping rat-data-type {
    leaf name {
      description
        "Radio access technology (RAT) identifier";
      type common-rat-type-extend;
      mandatory true;
      must '(../../../../../../charging/characteristics/*/rat/rat-type[name=current()/../name]/limit-profile)' {
        error-message "( \"limit-profile needs to be configured\" )";
        tailf:dependency "../../../../../../charging/characteristics";
      }
    }
    leaf limit-profile {
      description
        "Limit profile to be used for the RAT";
      type leafref {
        path "../../../../limit-profile/name";
      }
    }
  }

  grouping limit-profile-type {
    leaf name {
      description
        "Limit profile identifier";
      type string {
        pattern '[.0-9A-Za-z_-]*' {
          error-message "Must contain only letters, numbers, underscores or dashes";
        }
        length "1..64";
      }
      mandatory true;
      must '(../../limit-profile[name=current()/../name]/volume-limit) or (../../limit-profile[name=current()/../name]/time-limit)' {
        error-message "( \"volume-limit or time-limit needs to be configured\" )";
      }
    }
    leaf volume-limit {
      description
        "Limit of number of kilobytes for generating partial CDR";
      type uint32 {
        range "100..2097152" {
          error-message "Invalid value for attribute 'volume-limit'. Valid values are in range:[100,2097152]";
        }
      }
    }
    leaf time-limit {
      description
        "Limit of number of minutes for generating partial CDR";
      type uint16 {
        range "5..1440" {
          error-message "Invalid value for attribute 'time-limit'. Valid values are in range:[5,1440]";
        }
      }
    }
  }

  grouping charging-profile-common {
    leaf name {
      description
        "Profile identifier";
      mandatory true;
      type string {
        pattern '[.0-9A-Za-z_-]*' {
          error-message "Must contain only letters, numbers, underscores or dashes";
        }
        length "1..64";
      }
    }
    leaf charging-profile {
      description
        "Mapped charging profile - profile0...profile15";
      mandatory true;
      type enumeration {
        enum profile0 {
          description
            "Profile 0";
        }
        enum profile1 {
          description
            "Profile 1";
        }
        enum profile2 {
          description
            "Profile 2";
        }
        enum profile3 {
          description
            "Profile 3";
        }
        enum profile4 {
          description
            "Profile 4";
        }
        enum profile5 {
          description
            "Profile 5";
        }
        enum profile6 {
          description
            "Profile 6";
        }
        enum profile7 {
          description
            "Profile 7";
        }
        enum profile8 {
          description
            "Profile 8";
        }
        enum profile9 {
          description
            "Profile 9";
        }
        enum profile10 {
          description
            "Profile 10";
        }
        enum profile11 {
          description
            "Profile 11";
        }
        enum profile12 {
          description
            "Profile 12";
        }
        enum profile13 {
          description
            "Profile 13";
        }
        enum profile14 {
          description
            "Profile 14";
        }
        enum profile15 {
          description
            "Profile 15";
        }
      }
    }
  }

  grouping charging-attr-type {
    leaf volume-limit {
      description
        "Limit of number of kilobytes for generating partial CDR";
      type uint32 {
        range "100..2097152" {
          error-message "Invalid value for attribute 'volume-limit'. Valid values are in range:[100,2097152]";
        }
      }
    }
    leaf time-limit {
      description
        "Limit of number of minutes for generating partial CDR";
      type uint16 {
        range "5..1440" {
          error-message "Invalid value for attribute 'time-limit'. Valid values are in range:[5,1440]";
        }
      }
    }
    container rf {
      presence "rf need presence";
      description
        "Rf charging configuration";
      uses rf-charging-configuration-type;
    }
    leaf no-call-detail {
      description
        "Do not generate call data records";
      type empty;
    }
    leaf change-limit {
      description
        "Limit of number of condition changes for generating partial CDR";
      type uint8 {
        range "1..5" {
          error-message "Invalid value for attribute 'change-limit'. Valid values are in range:[1,5]";
        }
      }
    }
    leaf sgsn-change-limit {
      description
        "Limit of number of SGSN changes for generating partial CDR";
      type uint8 {
        range "1..5" {
          error-message "Invalid value for attribute 'sgsn-change-limit'. Valid values are in range:[1,5]";
        }
      }
    }
    leaf transfer-type {
      description
        "Method used to transfer charging data";
      type enumeration {
        enum ftp-pull {
          description
            "Charging data transfer uses FTP pull only";
        }
        enum gtp-prime {
          description
            "Charging data transfer uses GTP Prime only";
        }
        enum gtpp-ftp {
          description
            "Charging data transfer uses both FTP pull and GTP Prime";
        }
        enum rf {
          description
            "Charging data transfer uses rf only";
        }
      }
      must "not ((/epg/pgw/charging/characteristics/*/transfer-type[text()='ftp-pull']) and (/epg/pgw/charging/characteristics/transfer-type[text()='rf']))" {
        error-message "Transfer type FTP pull can not be configured on the profile if rf is configured on the characteristics level";
        tailf:dependency "/epg/pgw/charging/characteristics";
      }
      must "not ((/epg/pgw/charging/characteristics/*/transfer-type[text()='gtp-prime']) and (/epg/pgw/charging/characteristics/transfer-type[text()='rf']))" {
        error-message "Transfer type GTP Prime can not be configured on the profile if rf is configured on the characteristics level";
        tailf:dependency "/epg/pgw/charging/characteristics";
      }
      must "not ((/epg/pgw/charging/characteristics/*/transfer-type[text()='gtpp-ftp']) and (/epg/pgw/charging/characteristics/transfer-type[text()='rf']))" {
        error-message "Transfer type FTP pull and Prime can not be configured on the profile if rf is configured on the characteristics level";
        tailf:dependency "/epg/pgw/charging/characteristics";
      }
      must "not ((/epg/pgw/charging/characteristics/*/transfer-type[text()='rf']) and (not (/epg/pgw/charging/characteristics/transfer-type[text()='rf'])))" {
        error-message "Transfer type rf can only be configured on the profile if rf is configured on the characteristics level as well";
        tailf:dependency "/epg/pgw/charging/characteristics";
      }
    }
    container gtp-prime {
      description
        "Characteristic specific GTP Prime configuration";
      must '(/epg/node/interface/gom-c) or (/epg/pgw/interface/ga)' {
        error-message "At least one of [epg node interface gom-c] or [epg pgw interface ga] must be configured";
        tailf:dependency "/epg/node/interface/gom-c";
        tailf:dependency "/epg/pgw/interface/ga";
      }
      presence "gtp-prime need presence";
      leaf-list gateway {
        description
          "Address of billing gateway";
        type inet:ipv4-address;
        max-elements 3;
      }
    }
    container service-data {
      description
        "Service data configuration";
      leaf change-limit {
        description
          "Limit of number of service condition changes for generating partial CDR";
        type uint8 {
          range "1..15" {
            error-message "Invalid value for attribute 'change-limit'. Valid values are in range:[1,15]";
          }
        }
      }
      leaf charge-event-limit {
        description
          "Limit of number of charged events for generating partial CDR";
        type uint8 {
          range "1..50" {
            error-message "Invalid value for attribute 'charge-event-limit'. Valid values are in range:[1,50]";
          }
        }
      }
      leaf uri-limit {
        description
          "Limit of number of URIs for generating partial CDR";
        type uint8 {
          range "5..50" {
            error-message "Invalid value for attribute 'uri-limit'. Valid values are in range:[5,50]";
          }
        }
        must "not (/epg/pgw/charging/characteristics/transfer-type[text()='rf'])" {
          error-message "Uri-limit can not be configured together with transfer-type rf";
          tailf:dependency "/epg/pgw/charging/characteristics/transfer-type";
        }
      }
      leaf transaction-report-limit {
        description
          "Limit of number of completed transactions for generating partial CDR";
        type uint8 {
          range "1..10" {
            error-message "Invalid value for attribute 'transaction-report-limit'. Valid values are in range:[1,10]";
          }
        }
      }
    }
    container rat {
      description
        "RAT specific charging profile configuration";
      list rat-type {
        key "name";
        uses rat-data-type;
      }
    }
  }

  grouping charging-log-type {
    leaf maximum-size {
      description
        "Maximum size of charging data file";
      type uint32 {
        range "1024..102400" {
          error-message "Invalid value for attribute 'maximum-size'. Valid values are in range:[1024,102400]";
        }
      }
      default "102400";
    }
    leaf maximum-age {
      description
        "Maximum age of charging data file";
      type uint16 {
        range "5..1440" {
          error-message "Invalid value for attribute 'maximum-age'. Valid values are in range:[5,1440]";
        }
      }
    }
    leaf compression {
      description
        "Compress all CDR data files";
      type empty;
    }
    container local-data-file {
      description
        "CDRs meant for normal offline transfer";
      leaf force-empty-files {
        description
          "Generate empty CDR data files if no CDRs are received";
        type empty;
      }
    }
    container gtp-prime-data-file {
      description
        "GTP Prime CDRs saved on disk on failure in reaching charging gateways";
      leaf activate-on-failure {
        description
          "Store GTP Prime CDRs on disk if all charging gateways are down";
        type empty;
      }
      leaf use-gtpp-for-gyccr {
        status deprecated;
        description
          "Use gtppcdr or pgw_gtppcdr directory for gy-ccr written to disk";
        type empty;
      }
    }
    leaf cdr-data-rate {
      description
        "Average CDR data transfer rate between PGWCD and FSAD";
      type uint16 {
        range "147..512" {
          error-message "Invalid value for attribute 'cdr-data-rate'. Valid values are in range:[147,512]";
        }
      }
    }
  }

  grouping imsi-charac-type {
    leaf-list imsi {
      description
        "Specify IMSI patterns using regular expressions";
      type string;
      max-elements 512;
    }
  }

  grouping charging-type {
    container characteristics {
      description
        "account-type charging characteristics";
      leaf default-complete-cc {
        description
          "Default charging characteristics value in 4 hexadecimal digits";
        type string {
          pattern '[0-9a-fA-F]*' {
            error-message "Invalid value for attribute 'default-complete-cc'. Valid values are in range:[0000,FFFF]";
          }
          length "4";
        }
      }
      leaf diameter-application-system {
        description
          "Diameter application system";
        type leafref {
          path "/epg/pgw/diameter/diameter-application-system/name";
        }
      }
      leaf transfer-type {
        description
          "Method used to transfer charging data";
        type enumeration {
          enum ftp-pull {
            description
              "Charging data transfer uses FTP pull only";
          }
          enum gtp-prime {
            description
              "Charging data transfer uses GTP Prime only";
          }
          enum gtpp-ftp {
            description
              "Charging data transfer uses both FTP pull and GTP Prime";
          }
          enum rf {
            description
              "Charging data transfer uses rf only";
          }
        }
        must "not ((/epg/pgw/charging/characteristics/transfer-type[text()='rf']) and (not (/epg/pgw/feature-activation/charging-rf)))" {
          error-message "Transfer type rf needs feature-activation charging-rf to use";
          tailf:dependency "/epg/pgw/charging/characteristics";
          tailf:dependency "/epg/pgw/feature-activation/charging-rf";
        }
      }
      leaf ignore-profile-from-serving-node {
        description
          "Ignore profile received from serving node";
        type empty;
      }
      leaf acr-interim-interval {
        description
          "Interval in minutes for generating ACR interim";
        type uint16 {
          range "1..1440" {
            error-message "Invalid value for attribute 'acr-interim-interval'. Valid values are in range:[1,1440]";
          }
        }
      }
      container profile8 {
        description
          "Profile 8 clients";
        presence "profile8 need presence";
        uses charging-attr-type;
      }
      container profile4 {
        description
          "Profile 4 clients";
        presence "profile4 need presence";
        uses charging-attr-type;
      }
      container profile1 {
        description
          "Profile 1 clients";
        presence "profile1 need presence";
        uses charging-attr-type;
      }
      container profile2 {
        description
          "Profile 2 clients";
        presence "profile2 need presence";
        uses charging-attr-type;
      }
      container profile0 {
        description
          "Profile 0 clients";
        presence "profile0 need presence";
        uses charging-attr-type;
      }
      container profile3 {
        description
          "Profile 3 clients";
        presence "profile3 need presence";
        uses charging-attr-type;
      }
      container profile5 {
        description
          "Profile 5 clients";
        presence "profile5 need presence";
        uses charging-attr-type;
      }
      container profile6 {
        description
          "Profile 6 clients";
        presence "profile6 need presence";
        uses charging-attr-type;
      }
      container profile7 {
        description
          "Profile 7 clients";
        presence "profile7 need presence";
        uses charging-attr-type;
      }
      container profile9 {
        description
          "Profile 9 clients";
        presence "profile9 need presence";
        uses charging-attr-type;
      }
      container profile10 {
        description
          "Profile 10 clients";
        presence "profile10 need presence";
        uses charging-attr-type;
      }
      container profile11 {
        description
          "Profile 11 clients";
        presence "profile11 need presence";
        uses charging-attr-type;
      }
      container profile12 {
        description
          "Profile 12 clients";
        presence "profile12 need presence";
        uses charging-attr-type;
      }
      container profile13 {
        description
          "Profile 13 clients";
        presence "profile13 need presence";
        uses charging-attr-type;
      }
      container profile14 {
        description
          "Profile 14 clients";
        presence "profile14 need presence";
        uses charging-attr-type;
      }
      container profile15 {
        description
          "Profile 15 clients";
        presence "profile15 need presence";
        uses charging-attr-type;
      }
      list limit-profile {
        key "name";
        uses limit-profile-type;
      }
    }
    container time-limit-measurement {
      description
        "Settings for time limit measurement";
      leaf ctx-creation {
        description
          "Measure time limit condition in increments since bearer creation";
        type empty;
      }
    }
    container user-location-change-trigger {
      description
        "Applicable charging triggers bsid,cgi,ecgi,rai,sai or tai";
      leaf bsid {
        description
          "Set that BSID will trigger a User Location Change";
        type empty;
      }
      leaf cgi-sai {
        description
          "Set that cgi-sai will trigger a User Location Change";
        type empty;
      }
      leaf ecgi {
        description
          "Set that ECGI will trigger a User Location Change";
        type empty;
      }
      leaf rai {
        description
          "Set that RAI will trigger a User Location Change";
        type empty;
      }
      leaf tai {
        description
          "Set that TAI will trigger a User Location Change";
        type empty;
      }
    }
    container triggers {
      description
        "Applicable charging triggers";
      container service-condition-change-trigger {
        description
          "Gy service condition change triggers";
        leaf tariff-time-switch {
          description
            "The tariff period provided by the OCS changes for the service";
          type empty;
        }
        leaf reauthorization-request {
          description
            "The service is reauthorized by the OCS";
          type empty;
        }
        leaf service-idled-out {
          description
            "The quota holding time provided by the OCS expires for the service";
          type empty;
        }
        leaf service-unit-exhausted {
          description
            "The event quota provided by the OCS is exhausted for the service";
          type empty;
        }
        leaf service-unit-threshold-reached {
          description
            "The event quota threshold provided by the OCS is reached for the service";
          type empty;
        }
        leaf service-stop {
          description
            "The service is stopped by the OCS";
          type empty;
        }
        leaf time-exhausted {
          description
            "The time quota provided by the OCS is exhausted for the service";
          type empty;
        }
        leaf timeout {
          description
            "The validity time provided by the OCS expires for the service";
          type empty;
        }
        leaf time-threshold-reached {
          description
            "The time quota threshold provided by the OCS is reached for the service";
          type empty;
        }
        leaf volume-exhausted {
          description
            "The volume quota provided by the OCS is exhausted for the service";
          type empty;
        }
        leaf volume-threshold-reached {
          description
            "The volume quota threshold provided by the OCS is reached for the service";
          type empty;
        }
        leaf continue-ongoing-session {
          description
            "Configures the continue-ongoing-session value to be included";
          type empty;
        }
        leaf final {
          description
            "The service has stopped";
          type empty;
        }
        leaf rating-condition-change {
          description
            "A trigger-type armed by OCS has been hit";
          type empty;
        }
        leaf quota-holding-time {
          description
            "The quota holding time has been hit";
          type empty;
        }
      }
      container user-csg-information {
        description
          "Triggers applicable for User CSG information";
        leaf use-pcrf-subscribed-triggers {
          description
            "Use reporting action subscribed by PCRF for offline charging";
          type boolean;
          default "true";
        }
      }
      container rate-control-trigger {
        description
          "Rate Control triggers";
        leaf apn-rate-control {
          description
            "Enable inclusion of APN rate control information and triggers";
          type empty;
        }
        leaf serving-plmn-rate-control {
          description
            "Enable inclusion of Serving PLMN rate control information and triggers";
          type empty;
        }
      }
      container container-closure {
        description
          "Triggers applicable for data container closure";
        leaf serving-node-change {
          description
            "Close a data container due to a serving node change";
          type empty;
        }
      }
    }
    container cdr-encoding {
      description
        "Configuration for CDR encoding";
      leaf charging-format {
        description
          "Format of charging records";
        type enumeration {
          enum 6 {
            description
              "Version 6";
          }
          enum 7 {
            description
              "Version 7";
          }
          enum 8 {
            description
              "Version 8";
          }
          enum 13 {
            description
              "Version 13";
          }
          enum 15 {
            description
              "Version 15";
          }
        }
      }
      choice cdr-size-choice {
        leaf maximum-size-64-kilo-bytes {
          description
            "Maximum size of CDR is limited to 64 Kilobytes";
          type empty;
        }
      }
      container resilience {
        description
          "Configurations used for CDRs during resilience scenarios";
        leaf cause-for-record-closing {
          description
            "CDR closing reason used in resilience failovers";
          type enumeration {
            enum 0 {
              description
                "Close reason normalRelease";
            }
            enum 4 {
              description
                "Close reason abnormalRelease";
            }
          }
          default "4";
        }
      }
      leaf service-condition-change-size {
        description
          "Number of bits that makes up the octet-string that represents the service condition change";
        type enumeration {
          enum 32;
          enum 64;
        }
        default "32";
      }
      must "(((service-condition-change-size = '64') and (not((charging-format[text()='6']) or (charging-format[text()='7']) or (charging-format[text()='8']))) and (charging-format))) or (service-condition-change-size = '32')" {
        error-message "Service-condition-change-size 64 is only supported in charging-format 13 and above.";
        tailf:dependency "charging-format";
      }
      container service-data {
        leaf use-service-id-in-rating-group {
          description
            "Report service identifier value in rating group id field";
          type empty;
        }
        leaf no-service-identifier {
          description
            "Do not include service identifier field in the list of service data";
          type empty;
        }
      }
    }
    container cdr-attribute {
      description
        "Attributes in charging data records";
      leaf no-reduced-partial {
        description
          "Generate fully qualified partial CDRs only";
        type empty;
      }
      leaf no-node-identifier {
        description
          "Don't include node identifier";
        type empty;
      }
      leaf no-local-record-sequence-number {
        description
          "Don't include local record sequence number";
        type empty;
      }
      choice msisdn-choice {
        leaf no-msisdn {
          description
            "Don't include MSISDN";
          type empty;
        }
        leaf msisdn-always {
          description
            "Always include MSISDN even if there is no change";
          type empty;
        }
      }
      leaf no-msisdn-number-plan-indicator {
        description
          "Don't include the number plan indicator in MSISDN.";
        type empty;
      }
      leaf no-apn-network-identifier {
        description
          "Don't include network identifier of APN";
        type empty;
      }
      leaf no-pdp-type {
        description
          "Don't include PDP type";
        type empty;
      }
      leaf no-pdp-pdn-type {
        description
          "Don't include cdr attribute pdpPDNType";
        type empty;
      }
      leaf no-uni-pdu-cp-only-flag {
        description
          "Don't include UNI PDU CP Only Flag";
        type empty;
      }
      leaf no-pdp-address-ipv4 {
        description
          "Don't include IPv4 PDP address";
        type empty;
        must "not (../../cdr-encoding/charging-format[text()='8'])" {
          error-message "No support for charging-format 8";
          tailf:dependency "../../cdr-encoding/charging-format";
        }
      }
      leaf no-pdp-address-ipv6 {
        description
          "Don't include IPv6 PDP address";
        type empty;
        must "not (../../cdr-encoding/charging-format[text()='8'])" {
          error-message "No support for charging-format 8";
          tailf:dependency "../../cdr-encoding/charging-format";
        }
      }
      leaf no-pdp-pdn-address-ipv4 {
        description
          "Don't include IPv4 servedPDPPDNAddress";
        type empty;
        must "not((../../cdr-encoding/charging-format[text()='6']) or (../../cdr-encoding/charging-format[text()='7']))" {
          error-message "no-pdp-pdn-address-ipv4 requires charging-format 8 or higher";
          tailf:dependency "../../cdr-encoding/charging-format";
        }
      }
      leaf no-pdp-pdn-address-ipv6 {
        description
          "Don't include IPv6 servedPDPPDNAddress";
        type empty;
        must "not((../../cdr-encoding/charging-format[text()='6']) or (../../cdr-encoding/charging-format[text()='7']))" {
          error-message "no-pdp-pdn-address-ipv6 requires charging-format 8 or higher";
          tailf:dependency "../../cdr-encoding/charging-format";
        }
      }
      leaf no-pgw-plmn-id {
        description
          "Don't include p-gwplmnidentifier";
        type empty;
      }
      leaf no-start-time {
        description
          "Don't include startTime";
        type empty;
      }
      leaf start-time-always {
        description
          "Always include startTime in all CDRs";
        type empty;
      }
      leaf no-dynamic-address-flag {
        description
          "Don't include indication if served PDP address is dynamic";
        type empty;
      }
      leaf no-stop-time {
        description
          "Don't include stopTime";
        type empty;
      }
      leaf no-pdn-connection-id {
        description
          "Don't include pDNConnectionID";
        type empty;
      }
      leaf no-serv-node-plmn-id {
        description
          "Don't include servingNodePLMNIdentifier";
        type empty;
      }
      choice t-volume-choice {
        leaf no-traffic-volumes {
          description
            "Don't include list of traffic volumes";
          type empty;
        }
        container traffic-volumes {
          description
            "Include list of traffic volumes";
          presence "traffic-volumes need presence";
          leaf qos-always {
            description
              "Always include QoS information even if there is no change";
            type empty;
          }
          leaf no-user-location-information {
            description
              "Don't include user location information";
            type empty;
          }
          leaf no-user-csg-information {
            description
              "Don't include user CSG information";
            type empty;
          }
          leaf no-serving-plmn-rate-control {
            description
              "Don't include Serving PLMN Rate control";
            type empty;
          }
          leaf no-apn-rate-control {
            description
              "Don't include APN rate control";
            type empty;
          }
        }
      }
      leaf no-apn-selection-mode {
        description
          "Don't include index indicating how the APN was selected";
        type empty;
      }
      leaf no-cc-selection-mode {
        description
          "Don't include information about how charging characteristics were selected";
        type empty;
      }
      leaf record-extension {
        description
          "Include record extension";
        type empty;
      }
      leaf no-sgsn-plmn-id {
        description
          "Don't include the SGSN PLMN identifier";
        type empty;
      }
      leaf no-pdn-type-extension {
        description
          "Don't include cdr attribute pdpPDNType extension";
        type empty;
      }
      leaf no-sgi-ptp-tunneling-method {
        description
          "Don't include sgi ptp tunneling method";
        type empty;
      }
      leaf no-scs-as-address {
        description
          "Don't include scs-as-address";
        type empty;
      }
      leaf apn-encoding {
        description
          "Method of ASN.1 encoding of the APN field in g-cdr";
        type enumeration {
          enum dot-notation {
            description
              "Encode dot as '.'";
          }
          enum digit-notation {
            description
              "Encode dot as digit";
          }
        }
      }
      leaf no-user-csg-information {
        description
          "Don't include user CSG information";
        type empty;
      }
      container record-extension-attributes {
        description
          "Record extension CDR attributes";
        must '../record-extension' {
          error-message "record-extension inclusion must be enabled";
          tailf:dependency "../record-extension";
        }
        presence "record-extension-attributes need presence";
        leaf credit-status {
          status current {
            yexte:preliminary;
          }
          description
            "Include credit status";
          type empty;
        }
        container include-uri {
          description
            "Include URI level information";
          presence "include-uri need presence";
          leaf count {
            description
              "Include URI event count";
            type empty;
          }
          leaf identifier {
            description
              "Include numerical URI identifier";
            type empty;
          }
          leaf volume {
            description
              "Include URI volume data";
            type empty;
          }
          leaf timestamp {
            description
              "Include URI event timestamp";
            type empty;
          }
          leaf max-uri-length {
            description
              "URI longer than this will be truncated";
            type uint16 {
              range "10..1025" {
                error-message "Invalid value for attribute 'max-uri-length'. Valid values are in range:[10,1025]";
              }
            }
          }
        }
        container service-id {
          description
            "Settings for service identifier attributes";
          leaf cc-request-number {
            description
              "Include credit control request number";
            type empty;
          }
        }
        container include-ip-flow {
          description
            "Include IP Flow level information";
          must 'not (/epg/pgw/charging/cdr-attribute/record-extension-attributes/include-uri)' {
            error-message "URI Level Reporting and IP Flow Level Reporting are incompatible";
            tailf:dependency "/epg/pgw/charging/cdr-attribute/record-extension-attributes/include-uri";
          }
          presence "include-ip-flow need presence";
          leaf max-flows {
            description
              "Maximum number of flows per cdr";
            type uint16 {
              range "1..1000" {
                error-message "Invalid value for attribute 'max-flows'. Valid values are in range:[1,1000]";
              }
            }
          }
        }
        leaf rule-space-id {
          description
            "Send value of currently selected parameter as used rule-space-id";
          type enumeration {
            enum policy-charging-rule-scope {
              description
                "Policy and Charging rule scope";
            }
          }
        }
      }
      leaf no-ms-time-zone {
        description
          "Don't include ms time zone";
        type empty;
      }
      leaf no-user-location-information {
        description
          "Don't include user location information";
        type empty;
      }
      leaf no-threegpp2-uli {
        description
          "Don't include 3GPP2 user location information";
        type empty;
      }
      leaf qos-bitrate-for-nongbr {
        description
          "Include qos-bitrate for the default bearer";
        type empty;
      }
      container enhanced-cdr {
        description
          "Attribute settings for enhanced CDR";
        presence "enhanced-cdr need presence";
        leaf no-ps-furnish-charging-information {
          description
            "Don't include PS furnish charging information";
          type empty;
        }
        leaf no-ps-fci-dedicated-bearer-rec-level {
          description
            "Don't include PS furnish charging information for dedicated bearers on record level.";
          type empty;
          must 'not (/epg/pgw/charging/cdr-attribute/enhanced-cdr/no-ps-furnish-charging-information)' {
            error-message "incompatible with no-ps-furnish-charging-information";
            tailf:dependency "/epg/pgw/charging/cdr-attribute/enhanced-cdr/no-ps-furnish-charging-information";
          }
        }
        choice traffic-volumes-choice {
          leaf traffic-volumes {
            description
              "Include list of traffic volumes";
            type empty;
          }
          leaf no-traffic-volumes {
            description
              "Don't include list of traffic volumes";
            type empty;
          }
        }
        leaf no-service-data {
          description
            "Don't include list of service data";
          type empty;
        }
        leaf keep-ps-fci-after-recording {
          description
            "Keep PS furnish charging information after recording";
          type empty;
        }
        leaf remove-ps-fci-offline {
          description
            "Remove PS furnish charging information when failure action continue is applied";
          type empty;
        }
        container service-data-attributes {
          description
            "Settings for service data attributes";
          presence "service-data-attributes need presence";
          leaf continuous-local-seq-number {
            description
              "Increment local sequence number for every generated service data container during lifetime of bearer";
            type empty;
            must 'not (../no-continuous-local-seq-number)' {
              error-message "incompatible with no-continuous-local-seq-number";
              tailf:dependency "../no-continuous-local-seq-number";
            }
          }
          leaf no-continuous-local-seq-number {
            description
              "Don't increment local sequence number for every generated service data container during lifetime of bearer";
            type empty;
          }
          leaf no-rat-type {
            description
              "Don't include radio access technology (RAT) type";
            type empty;
          }
          leaf no-sgsn-plmn-id {
            description
              "Don't include SGSN PLMN ID";
            type empty;
          }
          leaf no-sgsn-address {
            description
              "Don't include SGSN address";
            type empty;
          }
          leaf no-serv-node-address {
            description
              "Don't include serving node address";
            type empty;
          }
          leaf no-qos-information {
            description
              "Don't include QoS information";
            type empty;
          }
          leaf no-user-location-information {
            description
              "Don't include user location information";
            type empty;
          }
          leaf no-threegpp2-uli {
            description
              "Don't include 3GPP2 user location information";
            type empty;
            must '/epg/pgw/charging/cdr-attribute/enhanced-cdr/service-data-attributes/service-id/no-threegpp2-uli' {
              error-message "service-id level no-threegpp2-uli must be set";
              tailf:dependency "/epg/pgw/charging/cdr-attribute/enhanced-cdr/service-data-attributes/service-id/no-threegpp2-uli";
            }
          }
          leaf no-qos-extended-bitrates {
            description
              "Don't include QoS extended bitrates fields";
            type empty;
          }
          leaf no-qos-apn-ambr {
            description
              "Don't include QoS APN AMBR fields";
            type empty;
          }
          leaf no-user-csg-information {
            description
              "Don't include user CSG information";
            type empty;
          }
          leaf no-serving-plmn-rate-control {
            description
              "Don't include Serving PLMN Rate Control";
            type empty;
          }
          leaf no-apn-rate-control {
            description
              "Don't include APN Rate Control";
            type empty;
          }
          leaf no-charging-rule-base-name {
            description
              "Don't include charging rule base name";
            type empty;
          }
          container service-id {
            description
              "Settings for service identifier attributes";
            leaf result-code {
              description
                "Include credit control answer result code";
              type empty;
            }
            leaf qos-information {
              description
                "Include QoS information";
              type empty;
              must 'not (../../no-qos-information)' {
                error-message "incompatible with no-qos-information";
                tailf:dependency "../../no-qos-information";
              }
            }
            leaf sgsn-address {
              description
                "Include SGSN address";
              type empty;
              must 'not (../../no-sgsn-address)' {
                error-message "incompatible with no-sgsn-address";
                tailf:dependency "../../no-sgsn-address";
              }
            }
            leaf serv-node-address {
              description
                "Include serving node address";
              type empty;
              must 'not (../../no-serv-node-address)' {
                error-message "incompatible with no-serv-node-address";
                tailf:dependency "../../no-serv-node-address";
              }
            }
            leaf sgsn-plmn-id {
              description
                "Include SGSN PLMN ID";
              type empty;
              must 'not (../../no-sgsn-plmn-id)' {
                error-message "incompatible with no-sgsn-plmn-id";
                tailf:dependency "../../no-sgsn-plmn-id";
              }
            }
            leaf rat-type {
              description
                "Include radio access technology (RAT) type";
              type empty;
              must 'not (../../no-rat-type)' {
                error-message "incompatible with no-rat-type";
                tailf:dependency "../../no-rat-type";
              }
            }
            leaf user-location-information {
              description
                "Include user location information";
              type empty;
              must 'not (../../no-user-location-information)' {
                error-message "incompatible with no-user-location-information";
                tailf:dependency "../../no-user-location-information";
              }
            }
            leaf failure-handling-cont {
              description
                "Include failure handling continue attribute";
              type empty;
            }
            leaf no-threegpp2-uli {
              description
                "Don't include 3GPP2 user location information";
              type empty;
            }
            leaf user-csg-information {
              description
                "Include user CSG information";
              type empty;
            }
          }
          leaf allow-zero {
            description
              "Allow inclusion of service data with zero usage";
            type empty;
          }
          leaf reporting-level {
            description
              "Default level for service data reporting";
            type enumeration {
              enum rating-group {
                description
                  "Report service data on rating group level";
              }
              enum service-id {
                description
                  "Report service data on service identifier level";
              }
            }
          }
          container rating-group {
            description
              "Setting for enhanced CDRs rating-group level";
            leaf no-zero-usage-container {
              description
                "Do not include zero-usage containers";
              type empty;
              must 'not (../../allow-zero)' {
                error-message "allow-zero can not be used with no-zero-usage-container";
                tailf:dependency "../../allow-zero";
              }
            }
            leaf no-zero-volume-container {
              description
                "Do not include zero-volume containers when timeUsage is not zero and reporting level is RG";
              type empty;
              must 'not (../../allow-zero)' {
                error-message "allow-zero can not be used with no-zero-volume-container";
                tailf:dependency "../../allow-zero";
              }
            }
          }
        }
      }
      leaf no-ims-signaling-context {
        description
          "Don't include IMS signaling context";
        type empty;
      }
      leaf no-rat-type {
        description
          "Don't include radio access technology (RAT) type";
        type empty;
      }
      leaf no-imei-sv {
        description
          "Don't include IMEI and software version";
        type empty;
      }
      leaf include-new-sgsn-address {
        description
          "Enable inclusion of new SGSN address in CDR generated because of SGSN change";
        type empty;
      }
      leaf record-seq-number-single-cdr {
        description
          "Enable inclusion of record sequence numbers in CDRs when only one record is produced";
        type empty;
      }
      leaf no-low-priority-indicator {
        description
          "Don't include low priority indicator";
        type empty;
      }
      leaf no-qos-extended-bitrates {
        description
          "Don't include QoS extended bitrates fields";
        type empty;
      }
      leaf no-qos-apn-ambr {
        description
          "Don't include QoS APN AMBR fields";
        type empty;
      }
      leaf no-list-of-ran-secondary-rat-usage-reports {
        description
          "Don't include Secondary RAT RAN-based usage reports in CDRs";
        type empty;
      }
      leaf no-serving-plmn-rate-control {
        description
          "Don't include Serving PLMN Rate Control data in CDRs";
        type empty;
      }
      leaf no-apn-rate-control {
        description
          "Don't include APN Rate Control data in CDRs";
        type empty;
      }
      leaf no-mo-exception-data {
        description
          "Don't include MO Exception Data in CDRs";
        type empty;
      }
      leaf no-served-mnnai {
        description
          "Don't include Served MNNAI in CDRs";
        type empty;
      }
    }
    container gtp-prime {
      description
        "GTP Prime settings";
      must '(/epg/node/interface/gom-c) or (/epg/pgw/interface/ga)' {
        error-message "At least one of [epg node interface gom-c] or [epg pgw interface ga] must be configured";
        tailf:dependency "/epg/node/interface/gom-c";
        tailf:dependency "/epg/pgw/interface/ga";
      }
      presence "gtp-prime need presence";
      leaf keepalive-interval {
        description
          "Seconds between sending keepalive messages on an idle path";
        type uint8 {
          range "60..200" {
            error-message "Invalid value for attribute 'keepalive-interval'. Valid values are in range:[60,200]";
          }
        }
      }
      leaf t3-response-time {
        description
          "Seconds between control message retries";
        type string {
          pattern '(([1-9])|([1-2][0-9])|(30))' {
            error-message "Value must be a number from 1 to 30.";
          }
        }
      }
      leaf n3-requests {
        description
          "Total number of transmissions allowed for a control message";
        type uint8 {
          range "1..8" {
            error-message "Invalid value for attribute 'n3-requests'. Valid values are in range:[1,8]";
          }
        }
      }
      leaf diffserv {
        description
          "DiffServ DSCP for GTP packets";
        type enumeration {
          enum af11 {
            description
              "Assured forwarding class 1, low drop precedence";
          }
          enum af12 {
            description
              "Assured forwarding class 1, medium drop precedence";
          }
          enum af13 {
            description
              "Assured forwarding class 1, high drop precedence";
          }
          enum af21 {
            description
              "Assured forwarding class 2, low drop precedence";
          }
          enum af22 {
            description
              "Assured forwarding class 2, medium drop precedence";
          }
          enum af23 {
            description
              "Assured forwarding class 2, high drop precedence";
          }
          enum af31 {
            description
              "Assured forwarding class 3, low drop precedence";
          }
          enum af32 {
            description
              "Assured forwarding class 3, medium drop precedence";
          }
          enum af33 {
            description
              "Assured forwarding class 3, high drop precedence";
          }
          enum af41 {
            description
              "Assured forwarding class 4, low drop precedence";
          }
          enum af42 {
            description
              "Assured forwarding class 4, medium drop precedence";
          }
          enum af43 {
            description
              "Assured forwarding class 4, high drop precedence";
          }
          enum ef {
            description
              "Expedited forwarding";
          }
          enum be {
            description
              "Best effort forwarding";
          }
          enum cs1 {
            description
              "Class selector 1";
          }
          enum cs2 {
            description
              "Class selector 2";
          }
          enum cs3 {
            description
              "Class selector 3";
          }
          enum cs4 {
            description
              "Class selector 4";
          }
          enum cs5 {
            description
              "Class selector 5";
          }
          enum cs6 {
            description
              "Class selector 6";
          }
          enum cs7 {
            description
              "Class selector 7";
          }
        }
      }
      leaf transaction-timeout {
        description
          "Seconds a GTP response entry is stored";
        type uint8 {
          range "5..60" {
            error-message "Invalid value for attribute 'transaction-timeout'. Valid values are in range:[5,60]";
          }
        }
      }
      container no-path-management-for-peer {
        description
          "Deactivate path management for peer";
        list address {
          max-elements 40;
          key "name";
          leaf name {
            description
              "Deactive path management for peer address";
            type eip-prefix;
          }
        }
      }
      leaf path-management {
        description
          "Use path management";
        type empty;
      }
      leaf checkalive-interval {
        description
          "Seconds between sending checkalive messages to an unavailable CGF";
        type uint16 {
          range "60..600" {
            error-message "Invalid value for attribute 'checkalive-interval'. Valid values are in range:[60,600]";
          }
        }
      }
      leaf version {
        description
          "GTP Prime version";
        type enumeration {
          enum v0-20 {
            description
              "Use GTP Prime version v0 with 20 bytes header";
          }
          enum v0-6 {
            description
              "Use GTP Prime version v0 with 6 bytes header";
          }
          enum v2 {
            description
              "Use GTP Prime version v2";
          }
        }
      }
      leaf one-data-record-per-transfer {
        description
          "Only send one CDR in a gtp-prime transfer";
        type empty;
      }
      container duplicate-prevention {
        description
          "Use duplicate-prevention";
        must "../version[text()='v2']" {
          error-message "GTP Prime version 2 must be enabled";
          tailf:dependency "../version";
        }
        presence "duplicate-prevention need presence";
        leaf partial {
          description
            "Use partial";
          type empty;
        }
        leaf instant-release {
          description
            "Use instant-release";
          type empty;
          must '../partial' {
            error-message "Duplicate prevention partial must be enabled";
            tailf:dependency "../partial";
          }
        }
      }
    }
    container rf {
      description
        "Rf settings";
      leaf service-context-id {
        description
          "Service Context Identifier";
        type string {
          length "1..80";
        }
      }
      leaf report-ctrl-address-used {
        description
          "Enable GGSN and SGSN address AVPs reported on Rf to be the actual control address used for the session";
        type empty;
      }
      leaf rf-acr-file-format {
        description
          "ACR file format defined by release";
        type enumeration {
          enum 9 {
            description
              "release 9";
          }
          enum 10 {
            description
              "release 10";
          }
          enum 11 {
            description
              "release 11";
          }
          enum 12 {
            description
              "release 12";
          }
          enum 13 {
            description
              "release 13";
          }
          enum 14 {
            description
              "release 14";
          }
          enum 15 {
            description
              "release 15";
          }
        }
      }
      container service-reporting {
        container service-id-level-reporting {
          description
            "Service Identifier Level Reporting options";
          leaf-list service-id {
            description
              "Report on service identifier level";
            type string {
              pattern '[0-9]{1,10}([-][0-9]{1,10})?' {
                error-message "Must be a service identifier or a range of service identifiers";
              }
              length "1..21";
            }
            max-elements 8192;
          }
        }
        leaf reporting-level {
          description
            "Charging Reporting Level options";
          type enumeration {
            enum rating-group {
              description
                "Report service data on rating group level";
            }
            enum service-id {
              description
                "Report service data on service identifier level";
            }
          }
        }
        container sdc-limit {
          description
            "Enable the limit of number of SDC in one ACR message";
          presence "sdc-limit need presence";
          leaf limit {
            description
              "Number of SDC in one ACR message";
            type uint8 {
              range "5..15" {
                error-message "Invalid value for attribute 'limit'. Valid values are in range:[5,15]";
              }
            }
            default "5";
          }
          leaf no-change-condition {
            description
              "No change-condition in split ACR message except for the final one";
            type empty;
          }
        }
        leaf multiple-service-change-condition {
          description
            "Enables Multiple Change Conditions in Rf SDCs.";
          type empty;
        }
        leaf allow-zero {
          description
            "Allow inclusion of service data with zero usage";
          type empty;
        }
      }
    }
    container icr {
      container switchover {
        leaf local-sequence-number-jump {
          description
            "The amount of numbers we will step the local sequence number after an ICR Switchover";
          type uint16 {
            range "0..65000" {
              error-message "Invalid value for attribute 'local-sequence-number-jump'. Valid values are in range:[0,65000]";
            }
          }
        }
        leaf record-sequence-number-jump {
          description
            "The amount of numbers we will step the sequence number after an ICR Switchover";
          type uint16 {
            range "0..65000" {
              error-message "Invalid value for attribute 'record-sequence-number-jump'. Valid values are in range:[0,65000]";
            }
          }
        }
        leaf accounting-record-number-jump {
          description
            "The amount of numbers we will step the accounting record number after an ICR Switchover";
          type uint16 {
            range "0..65000" {
              error-message "Invalid value for attribute 'accounting-record-number-jump'. Valid values are in range:[0,65000]";
            }
          }
        }
      }
    }
    container charging-data-file {
      description
        "Charging records saved on node";
      uses charging-log-type;
    }
    list cdr-encoding-profile {
      description
        "Setting RAT type masking for Ga/Bp";
      max-elements 32;
      key "name";
      leaf name {
        description
          "Limit profile identifier";
        type string {
          pattern '[.0-9A-Za-z_-]*' {
            error-message "Must contain only letters, numbers, underscores or dashes";
          }
          length "1..64";
        }
      }
      container rat-type-map {
        description
          "Defines RAT type mapping";
        list from {
          description
            "Original RAT type identifier to map from";
          key "name";
          uses rat-map-type;
        }
      }
    }
    list rf-encoding-profile {
      description
        "Settings RAT type masking for Rf";
      max-elements 32;
      key "name";
      leaf name {
        description
          "Limit profile identifier";
        type string {
          pattern '[.0-9A-Za-z_-]*' {
            error-message "Must contain only letters, numbers, underscores or dashes";
          }
          length "1..64";
        }
      }
      leaf subscription-id-type {
        description
          "Subscription identifier";
        type enumeration {
          enum network-access-identifier {
            description
              "Use network access identifier as subscription identifier";
          }
        }
      }
      container rat-type-map {
        description
          "Defines RAT type mapping";
        list from {
          description
            "Original RAT type identifier to map from";
          key "name";
          uses rat-map-type;
        }
      }
    }
    leaf no-initial-cdr {
      description
        "Suppress the initial charging record generation";
      type empty;
    }
    leaf use-31bits-charging-id {
      description
        "Use 31 bits charging id instead of default 32 bits";
      type empty;
    }
    choice tariff_choice {
      list tariff-activation {
        key "name";
        uses deprecated-tariff-type;
      }
    }
    container imsi-based-characteristics {
      description
        "Select charging characteristics based on IMSI";
      list complete-cc {
        description
          "Charging characteristics value";
        key "name";
        leaf name {
          description
            "Mapped charging characteristics value in 4 hexadecimal digits";
          type string {
            pattern '[0-9a-fA-F]*' {
              error-message "Invalid value for attribute 'complete-cc'. Valid values are in range:[0000,FFFF]";
            }
            length "4";
          }
        }
        uses imsi-charac-type;
      }
    }
    leaf no-empty-cdr {
      description
        "Do not close CDR at time limit if volume is zero";
      type empty;
    }
    container service-condition-change-trigger {
      status deprecated;
      description
        "Gy service condition change triggers";
      leaf tariff-time-switch {
        status deprecated;
        description
          "The tariff period provided by the OCS changes for the service";
        type empty;
      }
      leaf reauthorization-request {
        status deprecated;
        description
          "The service is reauthorized by the OCS";
        type empty;
      }
      leaf service-idled-out {
        status deprecated;
        description
          "The QHT provided by the OCS expires for the service";
        type empty;
      }
      leaf service-unit-exhausted {
        status deprecated;
        description
          "The event quota provided by the OCS is exhausted for the service";
        type empty;
      }
      leaf service-unit-threshold-reached {
        status deprecated;
        description
          "The event quota threshold provided by the OCS is reached for the service";
        type empty;
      }
      leaf service-stop {
        status deprecated;
        description
          "The service is stopped by the OCS";
        type empty;
      }
      leaf time-exhausted {
        status deprecated;
        description
          "The time quota provided by the OCS is exhausted for the service";
        type empty;
      }
      leaf timeout {
        status deprecated;
        description
          "The VT provided by the OCS expires for the service";
        type empty;
      }
      leaf time-threshold-reached {
        status deprecated;
        description
          "The time quota threshold provided by the OCS is reached for the service";
        type empty;
      }
      leaf volume-exhausted {
        status deprecated;
        description
          "The volume quota provided by the OCS is exhausted for the service";
        type empty;
      }
      leaf volume-threshold-reached {
        status deprecated;
        description
          "The volume quota threshold provided by the OCS is reached for the service";
        type empty;
      }
      leaf continue-ongoing-session {
        status deprecated;
        description
          "Configures the continue-ongoing-session value to be included";
        type empty;
      }
      leaf final {
        status deprecated;
        description
          "The service has stopped";
        type empty;
      }
      leaf rating-condition-change {
        status deprecated;
        description
          "A trigger-type armed by OCS has been hit";
        type empty;
      }
      leaf quota-holding-time {
        status deprecated;
        description
          "The Quota Holding Time has been hit";
        type empty;
      }
    }
    list ga-bp-profile {
      description
        "Configuration for Ga/Bp profile";
      key "name";
      uses charging-profile-common;
      leaf cdr-encoding-profile {
        description
          "Configuration for encoding profile";
        type string {
          pattern '[.0-9A-Za-z_-]*' {
            error-message "Must contain only letters, numbers, underscores or dashes";
          }
          length "1..64";
        }
      }
      must "(((../../charging/characteristics/*/transfer-type[text()='ftp-pull']) or                 (../../charging/characteristics/*/transfer-type[text()='gtp-prime']) or                 (../../charging/characteristics/*/transfer-type[text()='gtpp-ftp']) or                 not (../../charging/characteristics/*/transfer-type)) and              ((../../charging/characteristics/transfer-type[text()='ftp-pull']) or                 (../../charging/characteristics/transfer-type[text()='gtp-prime']) or                 (../../charging/characteristics/transfer-type[text()='gtpp-ftp']) or                 not (../../charging/characteristics/transfer-type)))" {
        error-message "Ga/Bp profiles must be configured with charging profiles having transfer-type (ftp-pull|gtp-prime|gtpp-ftp)";
        tailf:dependency "../../charging/characteristics";
      }
    }
    list rf-profile {
      description
        "Configuration for Rf profile";
      key "name";
      uses charging-profile-common;
      leaf rf-encoding-profile {
        description
          "Configuration for encoding profile";
        type string {
          pattern '[.0-9A-Za-z_-]*' {
            error-message "Must contain only letters, numbers, underscores or dashes";
          }
          length "1..64";
        }
      }
      must "((/epg/pgw/charging/characteristics/*/transfer-type[text()='rf']) and                (/epg/pgw/charging/characteristics/transfer-type[text()='rf']))" {
        error-message "Rf profiles must be configured with charging profiles having transfer-type (rf)";
        tailf:dependency "/epg/pgw/charging/characteristics";
      }
    }
  }

  grouping node-diagnostics-type {
    list trace {
      description
        "Trace";
      key "name";
      leaf name {
        description
          "Trace item";
        type string;
      }
      leaf trace-file-path {
        description
          "Redirect this trace object output to a file in given path";
        type string;
      }
    }
    container override {
      description
        "Override";
      leaf gtp-echo-interval {
        description
          "GTP echo interval";
        type uint8 {
          range "1..200" {
            error-message "Invalid value for attribute 'gtp-echo-interval'. Valid values are in range:[1,200]";
          }
        }
      }
    }
    leaf manual-trace {
      description
        "Manual trace";
      type empty;
    }
  }

  grouping uetrace-type {
    list flag {
      description
        "Select interface or protocol type for UE trace";
      key "name";
      leaf name {
        description
          "Select interface or protocol type for UE trace";
        type enumeration {
          enum gtp {
            description
              "Trace GTP message";
          }
          enum gx {
            description
              "Trace Gx message";
          }
          enum gy {
            description
              "Trace Gy message";
          }
          enum radius {
            description
              "Trace Radius message";
          }
          enum s6b {
            description
              "Trace S6b message";
          }
          enum s6b-auth {
            description
              "Trace S6bAuth message";
          }
          enum sxa {
            description
              "Trace sxa message";
            status current {
              yexte:preliminary;
            }
          }
          enum sxb {
            description
              "Trace sxb message";
            status current {
              yexte:preliminary;
            }
          }
        }
      }
    }
  }

  grouping node-traceoptions-type {
    leaf debug-level {
      description
        "Debug output level";
      type uint8 {
        range "0..31" {
          error-message "Invalid value for attribute 'debug-level'. Valid values are in range:[0,31]";
        }
      }
    }
    list flag {
      description
        "Tracing options";
      key "name";
      leaf name {
        description
          "Tracing options";
        type enumeration {
          enum amf {
            description
              "Trace amf module events";
          }
          enum charging {
            description
              "Trace charging module events";
          }
          enum core {
            description
              "Trace core module events";
          }
          enum data {
            description
              "Trace data module events";
          }
          enum dbp {
            description
              "Trace Diameter base protocol module events";
          }
          enum dhcp {
            description
              "Trace DHCP events";
          }
          enum dns {
            description
              "Trace DNS events";
          }
          enum extdb {
            description
              "Trace external database module events";
          }
          enum http {
            description
              "Trace HTTP module events";
          }
          enum lih {
            description
              "Trace logical interface handler module events";
          }
          enum li {
            description
              "Trace logical interface module events";
          }
          enum limit {
            description
              "Trace limit module events";
          }
          enum nrf {
            description
              "Trace NRF module events";
          }
          enum gccp {
            description
              "Trace GCCP module events";
          }
          enum gnsp {
            description
              "Trace GNSP module events";
          }
          enum gpcp {
            description
              "Trace GPCP module events";
          }
          enum gtp {
            description
              "Trace GTP stack module events";
          }
          enum gtpv2 {
            description
              "Trace GTP v2 stack module events";
          }
          enum pgwcd {
            description
              "Trace PGWCD module events";
          }
          enum gtpb {
            description
              "Trace GTP basic module events";
          }
          enum gucp {
            description
              "Trace GUCP module events";
          }
          enum oam {
            description
              "Trace OAM module events";
          }
          enum pdp {
            description
              "Trace PDP module events";
          }
          enum platform {
            description
              "Trace platform abstraction layer events";
          }
          enum radius {
            description
              "Trace RADIUS events";
          }
          enum rpd {
            description
              "Trace RPD events";
          }
          enum boardh {
            description
              "Trace board handler module events";
          }
          enum app {
            description
              "Trace application log module events";
          }
          enum sac {
            description
              "Trace statistics module events";
          }
          enum gsc {
            description
              "Trace GSC module events";
          }
          enum srvlib {
            description
              "Trace service library module events";
          }
          enum xmltok {
            description
              "Trace XML tokens module events";
          }
          enum xmlparse {
            description
              "Trace XML parser module events";
          }
          enum nct {
            description
              "Trace node call tracing module events";
          }
          enum apnmgt {
            description
              "Trace APN manager module events";
          }
          enum nmbproxy {
            description
              "Trace nmbproxy module events";
          }
          enum sm {
            description
              "Trace state machine module events";
          }
          enum sacc {
            description
              "Trace sacc module events";
          }
          enum qos {
            description
              "Trace QOS module events";
          }
          enum qct {
            description
              "Trace QCT module events";
          }
          enum dapp {
            description
              "Trace DAPP events";
          }
          enum sgwu {
            description
              "Trace SGWU events";
          }
          enum ebm {
            description
              "Trace EBM module events";
          }
          enum etfctrl {
            description
              "Trace ETFCTRL module events";
          }
          enum s6b {
            description
              "Trace S6B module events";
          }
          enum tdm {
            description
              "Trace TDM events";
          }
          enum pgwstats {
            description
              "Trace PGW stats events";
          }
          enum piaf {
            description
              "Trace piaf events";
          }
          enum pmip {
            description
              "Trace PMIP events";
          }
          enum cf {
            description
              "Trace Content Filtering events";
          }
          enum apr {
            description
              "Trace APR module events";
          }
          enum uetrace {
            description
              "Trace Ue Trace module events";
          }
          enum icr {
            description
              "Trace ICR module events";
          }
          enum ppb {
            description
              "Trace Userplane interface module events";
          }
          enum acs {
            description
              "Trace Admission Control service events";
          }
          enum service {
            description
              "Trace Service component events";
          }
          enum se {
            description
              "Trace Session Engine events";
          }
          enum smgr {
            description
              "Trace Session Manager events";
          }
          enum gn {
            description
              "Trace Gn Service events";
          }
          enum mobility {
            description
              "Trace Mobility Service events";
          }
          enum throttle {
            description
              "Trace Trottle service events";
          }
          enum lim {
            description
              "Trace LIM module events";
          }
          enum l2tp {
            description
              "Trace L2TP module events";
          }
          enum connectivity {
            description
              "Trace Connectivity module events";
          }
          enum datamanager {
            description
              "Trace DataManager module events";
          }
          enum s5s2 {
            description
              "Trace S5S2 Service events";
          }
          enum dedbear {
            description
              "Trace DedicatedBearer module events";
          }
          enum msgprio {
            description
              "Trace MessagePriority module events";
          }
          enum pcscf {
            description
              "Trace PCSCF events";
          }
          enum scc {
            description
              "Trace Service Chaining events";
          }
          enum upfselection {
            description
              "Trace Service UpfSelection events";
          }
          enum intdel {
            description
              "Trace Internal Delete module events";
          }
          enum destroy {
            description
              "Trace Destroy module events";
          }
          enum all {
            description
              "Trace everything";
          }
        }
      }
    }
  }

  grouping node-type {
    leaf node-type {
      status current {
        yexte:preliminary;
      }
      description
        "The name of the EPG node type";
      type common-node-type;
      mandatory true;
      must '((current()="sgw-c") and (not (../../pgw)) and (not (../../user-plane))) or
            ((current()="pgw-c") and (not (../../sgw)) and (not (../../user-plane))) or
            ((current()="gw-c") and (not (../../user-plane))) or
            ((current()="gw-u") and (not (../../pgw)) and (not (../../sgw))) or
            ((current()="sgw-c-gw-u") and (not (../../pgw))) or
            ((current()="pgw-c-gw-u") and (not (../../sgw))) or
            ((current()="gw-c-gw-u"))' {
        error-message "Configuration sub Tree does not match specified node-type. Please remove useless subtree and add mandatory subtree for the specified node-type";
      }
    }
    leaf node-name {
      description
        "The name of the EPG node, it must not be equal to 1";
      type string {
        pattern '[A-Za-z2-9]|[.A-Za-z0-9_-]{2,32}' {
          error-message "Node identifier is a string consisting of up to 32 letters, numbers, hyphens, periods, underscores and it must not be equal to 1";
        }
      }
    }
    leaf long-node-id-allowed {
      description
        "Extend the size of node ID up to 32";
      type empty;
    }
    container pm {
      description
        "performance management flags";
      action create-pm-job-to-file {
        description
          "create pm job configurations";
        input {
          leaf ref-job-name {
            description
              "src-job";
            type leafref {
              path "/pme:pm/pme:job/pme:name";
            }
            mandatory true;
          }
          leaf job-name {
            description
              "dst-job";
            type string {
              pattern '[0-9A-Za-z_-]{1,32}' {
                error-message "ERROR: Invalid value for parameter dst-job-name. Valid values are strings in a specified format: [0-9A-Za-z_-]{1,32}";
              }
            }
          }
          leaf target-node-type {
            description
              "Target node type. Default is current running node-type";
            type common-node-type;
          }
        }
        output {
          leaf result {
            type string;
            mandatory true;
          }
        }
      }
      leaf no-admission-control {
        description
          "Disable Pm Job Admission Control";
        type empty;
      }
      leaf no-overload-control {
        description
          "Disable Pm Job Overload Control";
        type empty;
      }
    }
    action kpi {
      description
        "Show key performance indicators (KPIs)";
      input {
        leaf sections {
          description
            "Sections to show [cpu|pgw|sgw|user-plane|all], all is default";
          type enumeration {
            enum cpu {
              description
                "Show CPU KPIs";
            }
            enum pgw {
              description
                "Show PGW KPIs";
            }
            enum sgw {
              description
                "Show SGW KPIs";
            }
            enum all {
              description
                "Show all KPIs";
            }
            enum user-plane {
              description
                "Show user-plane KPIs";
            }
          }
        }
        leaf samples {
          description
            "Amount of the latest PDC measurement samples to show (default is 3, range: 1-39)";
          type uint8 {
            range "1..39" {
              error-message "Invalid value for attribute 'samples'. Valid values are in range:[1,39]";
            }
          }
        }
        leaf date {
          description
            "If configured, display KPI data from specified date yyyy-mm-dd rather than date now";
          type string {
            pattern '((19|2[0-9])[0-9][0-9]-((0[1-9]|1[0-2])-(0[1-9]|1[0-9]|2[0-8]))|((0[4,6,9]|11)-(29|30))|((0[13578]|1[02])-(29|30|31)))|(((((19|2[0-9])(04|08|12|16|20|24|28|32|36|40|44|48|52|56|60|64|68|72|76|80|84|88|92|96))|(2000|2400|2800))-02-29))' {
              error-message "Value must be in a format YYYY-MM-DD";
            }
          }
        }
        leaf time {
          description
            "If configured, display KPI data from specified time hh:mm:ss rather than time now";
          type string {
            pattern '(([0-1][0-9]|2[0-3]):([0-5][0-9]):([0-5][0-9]))' {
              error-message "Value must be in a format hh:mm:ss";
            }
          }
        }
      }
      output {
        leaf result {
          type string;
          mandatory true;
        }
      }
    }
    action counter-value {
      description
        "Show counter value";
      input {
        leaf group {
          description
            "group name";
          type leafref {
            path "/pme:pm/pme:group/pme:name";
          }
          mandatory true;
        }
        leaf counter {
          description
            "counter name";
          type leafref {
            path "/pme:pm/pme:group[pme:name=current()/../group]/pme:measurement-type/pme:id";
          }
        }
        leaf index1 {
          description
            "instance value.";
          type string {
            pattern '[./0-9A-Za-z_-]{1,64}' {
              error-message "ERROR: Invalid value for parameter index1. Valid values are strings in a specified format.";
            }
          }
        }
        leaf index2 {
          description
            "instance value";
          type string {
            pattern '[./0-9A-Za-z_-]{1,64}' {
              error-message "ERROR: Invalid value for parameter index2. Valid values are strings in a specified format.";
            }
          }
        }
        leaf index3 {
          description
            "instance value";
          type string {
            pattern '[./0-9A-Za-z_-]{1,64}' {
              error-message "ERROR: Invalid value for parameter index3. Valid values are strings in a specified format.";
            }
          }
        }
        leaf index4 {
          description
            "instance value";
          type string {
            pattern '[./0-9A-Za-z_-]{1,64}' {
              error-message "ERROR: Invalid value for parameter index4. Valid values are strings in a specified format.";
            }
          }
        }
      }
      output {
        leaf result {
          type string;
          mandatory true;
        }
      }
    }
    action preliminary-config-in-use {
      description
        "Show preliminary configuration in use";
      output {
        leaf result {
          type string;
          mandatory true;
        }
      }
    }
    action deprecated-config-in-use {
      description
        "Show deprecated configuration in use";
      output {
        leaf result {
          type string;
          mandatory true;
        }
      }
    }
    container itc {
      yexte:user-group "ericsson-support,epg-tracing-admin";
      description
        "ITC settings";
      list profile {
        description
          "ITC profile";
        key "name";
        leaf name {
          description
            "Profile name";
          type string {
            pattern '[.0-9A-Za-z_-]*' {
              error-message "ERROR: Invalid value for parameter name. Valid values are strings in a specified format. Type: name? for more information on the format to use.";
            }
            length "1..64";
          }
          mandatory true;
        }
        leaf itc-filter {
          description
            "ITC filter in pcap-filter syntax, enclosed if space is included";
          type string {
            length "0..300";
          }
          mandatory true;
        }
        leaf snaplen-value {
          description
            "Snaplen value in bytes, 0 (default) means entire packets";
          type uint16 {
            range "0..65535" {
              error-message "Invalid value for attribute 'snaplen-value'. Valid values are in range:[0,65535]";
            }
          }
          default "0";
        }
        leaf buffer-value {
          description
            "Buffer value in MB, the default is 100";
          type uint8 {
            range "1..100" {
              error-message "Invalid value for attribute 'buffer-value'. Valid values are in range:[1,100]";
            }
          }
          default "100";
        }
      }
      action start-session {
        yexte:user-group "ericsson-support,epg-tracing-admin";
        description
          "Start ITC session";
        input {
          leaf start-label {
            description
              "Type filter or profile";
            type enumeration {
              enum filter {
                description
                  "Help when filter typed";
              }
              enum profile {
                description
                  "Help when profile typed";
              }
            }
            mandatory true;
          }
          leaf itc-filter {
            when "../start-label = 'filter'";
            description
              "ITC filter in pcap-filter syntax, enclosed if space is included";
            type string {
              length "0..300";
            }
          }
          leaf snaplen {
            when "../start-label = 'filter'";
            description
              "Snaplen value in bytes, 0 (default) means entire packets";
            type uint16 {
              range "0..65535" {
                error-message "Invalid value for attribute 'snaplen'. Valid values are in range:[0,65535]";
              }
            }
          }
          leaf buffer {
            when "../start-label = 'filter'";
            description
              "Buffer value in MB, the default is 100";
            type uint8 {
              range "1..100" {
                error-message "Invalid value for attribute 'buffer'. Valid values are in range:[1,100]";
              }
            }
          }
          leaf itc-profile {
            when "../start-label = 'profile'";
            description
              "ITC profile";
            type string {
              pattern '[.0-9A-Za-z_-]*' {
                error-message "ERROR: Invalid value for parameter itc-profile. Valid values are strings in a specified format. Type: itc-profile? for more information on the format to use.";
              }
              length "1..64";
            }
          }
        }
        output {
          leaf result {
            type string;
            mandatory true;
          }
        }
      }
      action stop-session {
        yexte:user-group "ericsson-support,epg-tracing-admin";
        description
          "Stop ITC session";
        output {
          leaf result {
            type string;
            mandatory true;
          }
        }
      }
      action show-session {
        yexte:user-group "ericsson-support,epg-tracing-admin";
        description
          "Show ITC session";
        output {
          leaf result {
            type string;
            mandatory true;
          }
        }
      }
    }
    container licensed-feature {
      description
        "License feature flags";
      action status {
        description
          "Show Node license status information";
        output {
          leaf result {
            type string;
            mandatory true;
          }
        }
      }
    }
    container feature-activation {
      description
        "Feature activation flags";
      leaf charging-rf {
        description
          "Enable charging over Rf";
        type empty;
      }
      leaf lawful-intercept {
        yexte:user-group "epg-lawful-intercept-admin";
        description
          "Activate lawful interception - Base capacity.";
        type empty;
      }
      leaf lawful-intercept-expansion-1 {
        yexte:user-group "epg-lawful-intercept-admin";
        description
          "Activate lawful interception - Extended capacity.";
        type empty;
      }
      leaf packet-inspection {
        status current {
          yexte:preliminary;
        }
        description
          "Activate packet inspection";
        type empty;
      }
      leaf presence-reporting-area {
        description
          "Activate presence reporting area";
        type empty;
      }
      leaf ue-trace {
        description
          "Activate UE Trace";
        type empty;
        must '/epg/node/node-type != "gw-u"' {
          error-message "Action not allowed for gw-u node";
        }
      }
      leaf ue-trace-user-plane {
        description
          "Activate UE Trace user plane";
        type empty;
        must '((/epg/node/node-type = "gw-u") or
              (/epg/node/node-type = "sgw-c-gw-u") or
              (/epg/node/node-type = "pgw-c-gw-u") or
              (/epg/node/node-type = "gw-c-gw-u"))' {
          error-message "Action only allowed for included gw-u node";
        }
      }
      leaf event-based-monitoring-ctrl-plane {
        description
          "Activate event based monitoring ctrl plane";
        type empty;
        must '/epg/node/node-type != "gw-u"' {
          error-message "Action not allowed for gw-u node";
        }
      }
      leaf event-based-monitoring-user-plane {
        description
          "Activate event based monitoring user plane";
        type empty;
        must '((/epg/node/node-type = "gw-u") or
              (/epg/node/node-type = "sgw-c-gw-u") or
              (/epg/node/node-type = "pgw-c-gw-u") or
              (/epg/node/node-type = "gw-c-gw-u"))' {
          error-message "Action only allowed for included gw-u node";
        }
      }
      leaf location-based-ip-allocation {
        description
          "Activate location based ip allocation.";
        type empty;
      }
      leaf integrated-traffic-capture {
        description
          "Activate Integrated Traffic Capture.";
        type empty;
      }
      leaf non-ip {
        description
          "Activate NonIp";
        type empty;
      }
      leaf sgw-dl-data-buffering {
        description
          "Activate SGW DL data buffering";
        type empty;
      }
      leaf epc-5g {
        description
          "Activate EPC 5G";
        type empty;
      }
    }
    container qos-control {
      description
        "Qos control setting";
      presence "qos-control need presence";
      list dscp-map {
        description
          "Mapping of qci and dscp";
        max-elements 300;
        must '/epg/node/qos-control/dscp-map[name=current()/name]/qci' {
          error-message "qci is mandatory";
        }
        key "name";
        leaf name {
          description
            "Qci to dscp map name";
          type string {
            pattern '[.0-9A-Za-z_-]*' {
              error-message "ERROR: Invalid value for parameter map-name. Valid values are strings in a specified format. Type: map-name? for more information on the format to use.";
            }
            length "1..64";
          }
          mandatory true;
        }
        list qci {
          description
            "Qci setting";
          key "name";
          leaf name {
            description
              "Qci index";
            type uint8 {
              range "1..254" {
                error-message "Invalid value for attribute 'qci-index'. Valid values are in range:[1,254]";
              }
            }
            mandatory true;
          }
          leaf dscp {
            description
              "Dscp name";
            type enumeration {
              enum af11 {
                description
                  "Assured forwarding class 1, low drop precedence";
              }
              enum af12 {
                description
                  "Assured forwarding class 1, medium drop precedence";
              }
              enum af13 {
                description
                  "Assured forwarding class 1, high drop precedence";
              }
              enum af21 {
                description
                  "Assured forwarding class 2, low drop precedence";
              }
              enum af22 {
                description
                  "Assured forwarding class 2, medium drop precedence";
              }
              enum af23 {
                description
                  "Assured forwarding class 2, high drop precedence";
              }
              enum af31 {
                description
                  "Assured forwarding class 3, low drop precedence";
              }
              enum af32 {
                description
                  "Assured forwarding class 3, medium drop precedence";
              }
              enum af33 {
                description
                  "Assured forwarding class 3, high drop precedence";
              }
              enum af41 {
                description
                  "Assured forwarding class 4, low drop precedence";
              }
              enum af42 {
                description
                  "Assured forwarding class 4, medium drop precedence";
              }
              enum af43 {
                description
                  "Assured forwarding class 4, high drop precedence";
              }
              enum ef {
                description
                  "Expedited forwarding";
              }
              enum be {
                description
                  "Best effort forwarding";
              }
              enum cs1 {
                description
                  "Class selector 1";
              }
              enum cs2 {
                description
                  "Class selector 2";
              }
              enum cs3 {
                description
                  "Class selector 3";
              }
              enum cs4 {
                description
                  "Class selector 4";
              }
              enum cs5 {
                description
                  "Class selector 5";
              }
              enum cs6 {
                description
                  "Class selector 6";
              }
              enum cs7 {
                description
                  "Class selector 7";
              }
            }
            mandatory true;
          }
        }
      }
    }
    container diagnostics {
      yexte:user-group "ericsson-support";
      description
        "Diagnostics and support";
      presence "diagnostics need presence";
      uses node-diagnostics-type;
    }
    container load-distribution {
      description
        "Load distribution settings";
      leaf host-aware-ppb-redundancy {
        description
          "Enable load distribution adapted to running 2 PPB VMs on each compute host";
        type empty;
      }
    }
    list board-allocation {
      description
        "Board allocation";
      key "name";
      leaf name {
        description
          "The board to use";
        type string {
          pattern '(gc|gu)-0/(30|(1|2)[0-9]|[1-9])/1' {
            error-message "Invalid board name";
          }
        }
      }
      action statistics {
        description
          "Show board statistics";
        input {
          leaf node {
            description
              "Show board statistics for this node";
            type enumeration {
              enum pgw {
                description
                  "Show PGW board statistics";
              }
              enum sgw {
                description
                  "Show SGW board statistics";
              }
            }
            mandatory true;
          }
        }
        output {
          leaf result {
            type string;
            mandatory true;
          }
        }
      }
      action decommission {
        description
          "Decommission a board";
        status current {
          yexte:preliminary;
        }
        output {
          leaf result {
            type string;
            mandatory true;
          }
        }
      }
      action recommission {
        description
          "Recommission a board";
        status current {
          yexte:preliminary;
        }
        output {
          leaf result {
            type string;
            mandatory true;
          }
        }
      }
      action statistics-charging {
        description
          "Show board charging statistics";
        input {
          leaf node {
            description
              "Show board charging statistics for this node";
            type enumeration {
              enum sgw {
                description
                  "Show SGW board charging statistics";
              }
            }
            mandatory true;
          }
        }
        output {
          leaf result {
            type string;
            mandatory true;
          }
        }
      }
    }
    container uetrace {
      yexte:user-group "ericsson-support,epg-tracing-admin";
      description
        "UE trace settings";
      leaf encryption {
        yexte:user-group "ericsson-support,epg-tracing-admin";
        description
          "The on/off for encryption.";
        type string {
          pattern '(on|off)' {
            error-message "on / off";
          }
        }
      }
      leaf encryption-key {
        yexte:user-group "ericsson-support,epg-tracing-admin";
        description
          "The key for file encryption.";
        type tailf:aes-cfb-128-encrypted-string {
          pattern '($[1-9]$(.|\n)*)|(($0$)?.{1,16})' {
            error-message "The encryption key should be a string with 1 to 16 characters.";
          }
        }
      }
      action start-control-plane-session {
        yexte:user-group "ericsson-support,epg-tracing-admin";
        description
          "Start control plane UE trace session";
        input {
          leaf trace-reference {
            description
              "Trace reference (11 or 12 hexadecimal digits)";
            type string {
              pattern '[0-9a-fA-F]{11,12}' {
                error-message "ERROR: Invalid value for parameter trace-reference. Valid values are strings in a specified format. Type: trace-reference? for more information on the format to use.";
              }
            }
            mandatory true;
            must '/epg/node/node-type != "gw-u"' {
              error-message "Action not allowed for gw-u node";
            }
          }
          leaf identifier-type {
            type enumeration {
              enum imsi {
                description
                  "IMSI identity";
              }
              enum imei {
                description
                  "IMEI identity";
              }
              enum msisdn {
                description
                  "MSISDN identity";
              }
              enum ipaddress {
                description
                  "UE IP address";
              }
              enum nextcall {
                description
                  "NEXT CALL";
              }
            }
            mandatory true;
          }
          leaf identifier-value {
            when '../identifier-type != "nextcall"';
            description
              "Identifier for IMSI , IMEI , MSISDN , UE IP ADDRESS";
            type union {
              type string {
                pattern '[0-9]+' {
                  error-message "Must be numbers with pattern '[0-9]+'";
                }
              }
              type eip-address;
            }
          }
          leaf condition-type {
            when '../identifier-type = "nextcall"';
            description
              "apn, mme-address or sgsn-address";
            type enumeration {
              enum apn {
                description
                  "APN condition";
              }
              enum mme-address {
                description
                  "MME Address condition";
              }
              enum sgsn-address {
                description
                  "SGSN Address condition";
              }
            }
            must '../condition-type != "mme-address" or (../condition-type = "mme-address" and /epg/node/node-type != "pgw-c" and /epg/node/node-type != "pgw-c-gw-u")' {
              error-message "mme-address as condition-type not supported yet on PGW. Please make sure [epg node node-type] does not contain 'pgw-c'";
            }
          }
          leaf condition-value {
            when '../identifier-type = "nextcall"';
            description
              "value of condition-type";
            type union {
              type string;
              type eip-address;
            }
          }
        }
        output {
          leaf result {
            type string;
            mandatory true;
          }
        }
      }
      action stop-control-plane-session {
        yexte:user-group "ericsson-support,epg-tracing-admin";
        description
          "Stop control plane UE trace session";
        input {
          leaf trace-reference {
            description
              "Trace reference (11 or 12 hexadecimal digits)";
            type string {
              pattern '[0-9a-fA-F]{11,12}' {
                error-message "ERROR: Invalid value for parameter trace-reference. Valid values are strings in a specified format. Type: trace-reference? for more information on the format to use.";
              }
            }
            mandatory true;
            must '/epg/node/node-type != "gw-u"' {
              error-message "Action not allowed for gw-u node";
            }
          }
        }
        output {
          leaf result {
            type string;
            mandatory true;
          }
        }
      }
      action show-session {
        yexte:user-group "ericsson-support,epg-tracing-admin";
        description
          "Show UE trace sessions";
        output {
          leaf result {
            type string;
            mandatory true;
          }
        }
      }
      leaf publish-interval {
        description
          "Publish interval";
        type string {
          pattern '1|3|5|15' {
            error-message "ERROR: Invalid value for parameter publish-interval. Valid values are: [1,3,5,15]";
          }
        }
        must '/epg/node/node-type != "gw-u"' {
          error-message "Action not allowed for gw-u node";
        }
      }
    }
    container charging {
      description
        "Charging settings";
      leaf separate-offline-directories {
        description
          "Enables additional offline charging directories";
        type empty;
      }
    }
    container diameter {
      description
        "Diameter settings";
      presence "diameter need presence";
      must '/epg/node/diameter/diameter-application-system' {
        error-message "diameter-application-system is mandatory";
      }
      must '/epg/node/diameter/remote-diameter-peer' {
        error-message "remote-diameter-peer is mandatory";
      }
      leaf local-realm {
        description
          "Local diameter realm";
        type string;
        mandatory true;
      }
      leaf local-host-name {
        description
          "Local host name";
        type string;
        mandatory true;
      }
      list remote-diameter-peer {
        description
          "Remote Diameter peer settings";
        max-elements 32;
        key "name";
        leaf name {
          description
            "Peer ID";
          type string;
        }
        leaf logical-interface {
          description
            "Logical interface";
          type leafref {
            path "/epg/node/logical-interface/name";
          }
          mandatory true;
        }
        leaf address {
          description
            "Peer address";
          type inet:ip-address;
          mandatory true;
          must 'count(/epg/node/diameter/remote-diameter-peer[address=current()])=1' {
            error-message "Peer address must be unique";
          }
        }
        leaf port {
          description
            "Peer port number";
          type uint16;
        }
        leaf watchdog {
          description
            "Watchdog timeout in seconds";
          type uint16 {
            range "3..300" {
              error-message "Invalid value for attribute 'watchdog'. Valid values are in range:[3,300]";
            }
          }
        }
      }
      list diameter-application-system {
        description
          "Diameter application system";
        max-elements 32;
        must '/epg/node/diameter/diameter-application-system[name=current()/name]/peer' {
          error-message "peer is mandatory";
        }
        key "name";
        leaf name {
          description
            "Diameter application system ID";
          type string;
        }
        leaf destination-realm {
          description
            "Destination realm";
          type string;
          mandatory true;
        }
        leaf application-id {
          description
            "vendor-specific application identity";
          type enumeration {
            enum rf {
              description
                "rf";
            }
          }
          mandatory true;
        }
        list peer {
          description
            "Remote Diameter peers and priorities";
          max-elements 32;
          key "name";
          leaf name {
            description
              "Remote Diameter peer ID";
            type leafref {
              path "/epg/node/diameter/remote-diameter-peer/name";
            }
          }
          leaf priority {
            description
              "Priority of the peer\\. A value from 0 to 255, where a lower value takes precedence.";
            type uint8 {
              range "0..255" {
                error-message "Invalid value for attribute 'priority'. Valid values are in range:[0,255]";
              }
            }
            mandatory true;
          }
        }
        leaf request-timeout {
          description
            "Request timeout in seconds";
          type uint8 {
            range "1..60" {
              error-message "Invalid value for attribute 'request-timeout'. Valid values are in range:[1,60]";
            }
          }
        }
        action status {
          description
            "Diameter Application System identifier";
          output {
            leaf result {
              type string;
              mandatory true;
            }
          }
        }
      }
    }
    container secm {
      description
        "Security management";
      uses secm-type;
    }
    container direct-io {
      description
        "Direct I/O";
      leaf internal-routing-instance {
        description
          "Routing Instance used for internal forwarding between PPBs";
        type leafref {
          path "/epg/node/direct-io/routing-instance/name";
        }
        must '/epg/node/direct-io/routing-instance[name=current()]/link-network-address-range' {
          error-message "The routing instance used as internal-routing-instance must have link-network-address-range configured";
        }
      }
      leaf route-advertisement {
        description
          "Advertise routes using specified routing protocol";
        type enumeration {
          enum rip {
            description
              "Routing Information Protocol (RIP) v2 and RIP Next Generation";
          }
        }
      }
      list logical-port {
        description
          "Group of physical ports";
        max-elements 32;
        key "name";
        leaf name {
          description
            "Logical port name";
          type string;
        }
        leaf-list port {
          description
            "List of physical ports that should be grouped in this logical port";
          type uint8 {
            range "0..31" {
              error-message "Invalid value for attribute 'port'. Valid values are in range:[0,31]";
            }
          }
          min-elements 1;
          max-elements 32;
          must 'count(/epg/node/direct-io/logical-port[port=current()])=1' {
            error-message "port index must be unique";
          }
        }
        leaf aggregation {
          description
            "Link aggregation mode";
          type enumeration {
            enum lacp {
              description
                "Link Aggregation Control Protocol";
            }
            enum active-standby {
              description
                "Static active-standby (mode 1)";
            }
          }
        }
        leaf mtu {
          description
            "Maximum Transmission Unit (MTU)";
          type uint16 {
            range "576..3022" {
              error-message "Invalid value for attribute 'mtu'. Valid values are in range:[576,3022]";
            }
          }
        }
      }

      grouping echo-cfg-parms {
        description
          "BFD grouping for base config parameters.";
        leaf bfd-mode {
          type enumeration {
            enum peerless {
              value 1;
              description
                "bfd echo mode without peer.";
            }
          }
          description
            "bfd mode.";
        }
        leaf required-min-echo-tx-interval {
          type uint32 {
            range "3000..60000000";
          }
          units "microseconds";
          default "10000";
          description
            "This is the Required Min Echo TX Interval as defined in BFD
             [RFC5880].";
        }
        leaf interface {
          description
            "Loopback interface for bfd echo";
          type leafref {
            path "/epg/node/direct-io/routing-instance[name=current()/../../../name]/vnf-loopback/name";
          }
        }
      }

      grouping bfd-session-group {
        description
          "BFD augmentation";
        status current {
          yexte:preliminary;
        }
        container bfd {
          description
            "Bidirectional Forwarding Detection (BFD)";
          leaf detection-multiplier {
            type uint8 {
              range "1..255";
            }
            default "3";
            description
              "Multiplier transmitted by local system.";
          }
          container bfd-echo {
            description
              "BFD echo function container";
            uses echo-cfg-parms;
          }
        }
      }
      list routing-instance {
        yexte:user-group "ericsson-support,epg-admin";
        description
          "Routing instance";
        key "name";
        leaf name {
          description
            "Routing instance name";
          type string;
          must '(/epg/node/direct-io/routing-instance[name=current()]/link-network-address-range) or (/epg/node/direct-io/routing-instance[name=current()]/ipv6-link-network-address-range)' {
            error-message "At least one of link-network-address-range and ipv6-link-network-address-range must be configured";
          }
        }
        leaf subnet {
          description
            "Subnet that default-gateway and link-network-address-range belongs to";
          type eipv4-prefix-optional;
        }
        leaf ipv6-subnet {
          description
            "Subnet that ipv6-default-gateway and ipv6-link-network-address-range belongs to";
          type eipv6-prefix-optional;
        }
        leaf link-network-address-range {
          description
            "Range of addresses for link network endpoints";
          type eipv4-prefix-optional;
        }
        leaf ipv6-link-network-address-range {
          description
            "Range of addresses for link network endpoints";
          type eipv6-prefix-optional;
        }
        leaf vlan-id {
          description
            "Virtual Local Area Network Identifier (802.1Q VID)";
          type uint16 {
            range "1..4094" {
              error-message "Invalid value for attribute 'vlan-id'. Valid values are in range:[1,4094]";
            }
          }
          must 'count(/epg/node/direct-io/routing-instance[vlan-id=current()])=1' {
            error-message "vlan-id must be unique";
          }
        }
        leaf default-gateway {
          description
            "Default next-hop gateway";
          type inet:ipv4-address;
        }
        leaf ipv6-default-gateway {
          description
            "Default next-hop gateway";
          type inet:ipv6-address;
        }
        leaf logical-port {
          description
            "Logical port for this routing instance";
          type leafref {
            path "/epg/node/direct-io/logical-port/name";
          }
          mandatory true;
        }
        container vnf-loopback {
          description
            "Routing instance loopback interfaces";
          leaf name {
            description
              "The loopback interface name";
            type string;
          }
          leaf vnf-ipv4-loopback {
            description
              "Loopback address under routing-instance";
            type inet:ipv4-address;
          }
          leaf vnf-ipv6-loopback {
            description
              "Ipv6 loopback address under routing-instance";
            type inet:ipv6-address;
          }
        }
        uses bfd-session-group;
        container companion {
          description
            "Distribute Direct I/O interface routes via another routing instance";
          status current {
            yexte:preliminary;
          }
          leaf routing-context {
            description
              "Companion IPOS routing context";
            status current {
              yexte:preliminary;
            }
            type string;
        must "(/ctxsipos:contexts/ctxipos:context[ctxipos:context-name=current()]) or (/epg/node/direct-io/routing-instance[name=current()])" {
              error-message "Companion instance must not refer to itself or another direct-io instance";
            }
      must "/ctxsipos:contexts/ctxipos:context[ctxipos:context-name=current()]" {
              error-message "Routing instance must be configured under 'managed-element context'";
            }
          }
        }
      }
      action show-arp {
        description
          "Show Address Resolution Protocol statistics";
        input {
          leaf board {
            description
              "Show statistics only from board (e.g\\. gu-0/5/1)";
            type string {
              pattern '(gu-0/(30|(1|2)[0-9]|[1-9])/1)' {
                error-message "Invalid board name";
              }
            }
          }
        }
        output {
          leaf result {
            type string;
            mandatory true;
          }
        }
      }
      action show-bfd {
        description
          "Show Bidirectional Forwarding Detection protocol statistics";
        input {
          leaf board {
            description
              "Show statistics only from board (e.g\\. gu-0/5/1)";
            type string {
              pattern '(gu-0/(30|(1|2)[0-9]|[1-9])/1)' {
                error-message "Invalid board name";
              }
            }
          }
        }
        output {
          leaf result {
            type string;
            mandatory true;
          }
        }
      }
      action show-bfd-sessions {
        description
          "Show Bidirectional Forwarding Detection protocol sessions";
        input {
          leaf board {
            description
              "Show sessions only from board (e.g\\. gu-0/5/1)";
            type string {
              pattern '(gu-0/(30|(1|2)[0-9]|[1-9])/1)' {
                error-message "Invalid board name";
              }
            }
          }
        }
        output {
          leaf result {
            type string;
            mandatory true;
          }
        }
      }
      action show-lacp {
        description
          "Show LACP statistics";
        input {
          leaf board {
            description
              "Show statistics only from board (e.g\\. gu-0/5/1)";
            type string {
              pattern '(gu-0/(30|(1|2)[0-9]|[1-9])/1)' {
                error-message "Invalid board name";
              }
            }
          }
        }
        output {
          leaf result {
            type string;
            mandatory true;
          }
        }
      }
      action show-lacp-aggregates {
        description
          "Show LACP aggregates status";
        input {
          leaf board {
            description
              "Show status only from board (e.g\\. gu-0/5/1)";
            type string {
              pattern '(gu-0/(30|(1|2)[0-9]|[1-9])/1)' {
                error-message "Invalid board name";
              }
            }
          }
        }
        output {
          leaf result {
            type string;
            mandatory true;
          }
        }
      }
      action show-ndp {
        description
          "Show Neighbor Discovery Protocol statistics";
        input {
          leaf board {
            description
              "Show statistics only from board (e.g\\. gu-0/5/1)";
            type string {
              pattern '(gu-0/(30|(1|2)[0-9]|[1-9])/1)' {
                error-message "Invalid board name";
              }
            }
          }
        }
        output {
          leaf result {
            type string;
            mandatory true;
          }
        }
      }
      action show-neighbors {
        description
          "Show neighbor cache that maps L3 to L2 addresses";
        input {
          leaf board {
            description
              "Show statistics only from board (e.g\\. gu-0/5/1)";
            type string {
              pattern '(gu-0/(30|(1|2)[0-9]|[1-9])/1)' {
                error-message "Invalid board name";
              }
            }
          }
        }
        output {
          leaf result {
            type string;
            mandatory true;
          }
        }
      }
      action show-ports {
        description
          "Show Ethernet ports status";
        input {
          leaf board {
            description
              "Show status only from board (e.g\\. gu-0/5/1)";
            type string {
              pattern '(gu-0/(30|(1|2)[0-9]|[1-9])/1)' {
                error-message "Invalid board name";
              }
            }
          }
        }
        output {
          leaf result {
            type string;
            mandatory true;
          }
        }
      }
      action clear-neighbors {
        yexte:user-group "ericsson-support,epg-admin";
        description
          "Clear neighbor cache that maps L3 to L2 addresses";
        input {
          leaf board {
            description
              "Run command only on board (e.g\\. gu-0/5/1)";
            type string {
              pattern '(gu-0/(30|(1|2)[0-9]|[1-9])/1)' {
                error-message "Invalid board name";
              }
            }
          }
        }
        output {
          leaf result {
            type string;
            mandatory true;
          }
        }
      }
    }
    list logical-interface {
      yexte:user-group "ericsson-support,epg-admin";
      description
        "Interface settings";
      key "name";
      leaf name {
        description
          "Logical interface name";
        type string;
        must '(/epg/node/logical-interface[name=current()]/address) or (/epg/node/logical-interface[name=current()]/ipv6-address)' {
          error-message "At least one of address and ipv6-address must be configured";
        }
      }
      leaf routing-instance {
        description
          "Routing instance for logical-interface";
        type string;
        must "(/ctxsipos:contexts/ctxipos:context[ctxipos:context-name=current()]) or (/epg/node/direct-io/routing-instance[name=current()])" {
          error-message "either ipos or direct-io routing instance should be configured";
        }
        default "local";
      }
      leaf address {
        description
          "Interface address or address range";
        type eipv4-prefix-optional;
      }
      leaf ipv6-address {
        description
          "Interface IPv6 address or IPv6 address range";
        type eipv6-prefix-optional;
      }
      container icr {
        description
          "Enable ICR for this interface";
        presence "icr need presence";
        leaf tracked {
          description
            "Toggle to enable that this interface will trigger an ICR switchover in case of problem";
          type empty;
        }
      }
    }
    container interface {
      description
        "Configure interface used by both PGW and SGW";
      container gom-c {
        presence "gom-c need presence";
        leaf logical-interface {
          description
            "Reference to the logical-interface in [epg node logical-interface]";
          type leafref {
            path "/epg/node/logical-interface/name";
          }
          mandatory true;
        }
      }
      container x1 {
        yexte:user-group "epg-lawful-intercept-admin";
        description
          "X1 address";
        presence "x1 need presence";
        must '/epg/node/interface/x2' {
          error-message "X2 needs to be configured too";
          tailf:dependency "/epg/node/interface/x2";
        }
        leaf logical-interface {
          description
            "Reference to the logical-interface in [epg node logical-interface]";
          type leafref {
            path "/epg/node/logical-interface/name";
          }
          mandatory true;
        }
        leaf port {
          description
            "Listening port for X1";
          type uint16 {
            range "1..65535" {
              error-message "Invalid value for attribute 'port'. Valid values are in range:[1,65535]";
            }
          }
          mandatory true;
        }
      }
      container x2 {
        yexte:user-group "epg-lawful-intercept-admin";
        description
          "X2 address";
        presence "x2 need presence";
        must '/epg/node/interface/x1' {
          error-message "X1 needs to be configured too";
          tailf:dependency "/epg/node/interface/x1";
        }
        leaf logical-interface {
          description
            "Reference to the logical-interface in [epg node logical-interface]";
          type leafref {
            path "/epg/node/logical-interface/name";
          }
          mandatory true;
        }
      }
      container li-t3 {
        yexte:user-group "epg-lawful-intercept-admin";
        description
          "li-t3 interface";
        presence "li-t3 need presence";
        must '/epg/node/interface/x1' {
          error-message "X1 needs to be configured too";
          tailf:dependency "/epg/node/interface/x1";
        }
        leaf logical-interface {
          description
            "Reference to the logical-interface in [epg node logical-interface]";
          type leafref {
            path "/epg/node/logical-interface/name";
          }
          mandatory true;
        }
      }
    }
    container lawful-intercept {
      yexte:user-group "epg-lawful-intercept-admin";
      description
        "Configuration for lawful-interception in the node";
      container transport-layer-security {
        description
          "To enable transport layer security";
        leaf node-credential {
          description
            "node-credential reference";
          type leafref {
            path "/epg/node/secm/certm/node-credential/name";
          }
        }
        leaf trust-category {
          description
            "trust-category reference";
          type leafref {
            path "/epg/node/secm/certm/trust-category/name";
          }
        }
      }
      container user-plane-selection {
        description
          "External User Plane Selection settings";
        list li-t3 {
          description
            "li-t3 settings";
          max-elements 32;
          key "name";
          leaf name {
            description
              "Name of li-t3 interface";
            type string {
              pattern '[.0-9A-Za-z_-]*' {
                error-message "Must contain only letters, numbers, underscores or dashes";
              }
              length "1..64";
            }
          }
          leaf shared-secret {
            description
              "The shared secret used for li-t3 interface encryption";
            type tailf:aes-cfb-128-encrypted-string;
            mandatory true;
          }
        }
      }
      leaf uli-in-iri-enable {
        description
          "Determines if UserLocationInfo element will be included in IRI events";
        type empty;
      }
      action clear-peak-active-targets {
        yexte:user-group "epg-lawful-intercept-admin";
        description
          "Clear the counters peak-pgw-active-targets and peak-sgw-active-targets";
        output {
          leaf result {
            type string;
            mandatory true;
          }
        }
      }
      action status {
        description
          "Show information related to Lawful Interception.";
        input {
          leaf level {
            description
              "Detailing level for the information.";
            type enumeration {
              enum brief {
                description
                  "Show brief information (default).";
              }
              enum detail {
                description
                  "Show detailed information (experimental).";
              }
            }
          }
        }
        output {
          leaf result {
            type string;
            mandatory true;
          }
        }
      }
    }
    container isp {
      description
        "Isp logging";
      container heartbeat {
        description
          "Isp heartbeat";
        leaf fast {
          description
            "Fast heartbeat";
          type empty;
        }
      }
    }
    container file-age-monitoring {
      yexte:user-group "ericsson-support,epg-admin";
      description
        "File age monitoring";
      list job-name {
        description
          "File age monitoring job";
        max-elements 8;
        key "name";
        leaf name {
          type string;
          mandatory true;
        }
        leaf filename-pattern {
          description
            "Absolute path/filenamePattern to the file(s) to be matched\\. Same absolute path/filenamePattern cannot exist in multiple jobs.";
          type string;
          mandatory true;
        }
        leaf user {
          description
            "User to be used for deletion if a special one is required";
          type string;
        }
        leaf max-age {
          description
            "Max age of the monitored files in minutes 10-525600";
          type uint32 {
            range "10..525600" {
              error-message "Invalid value for attribute 'max-age'. Valid values are in range:[10,525600]";
            }
          }
          mandatory true;
        }
        leaf log-per-file {
          description
            "Log per file exceeding the configured max age\\. Note that this may be very verobse in case matching many files.";
          type empty;
        }
        leaf action {
          description
            "Action to perform if a file from this group exceeds the configured max-age limit";
          type enumeration {
            enum alarm {
              description
                "Generate an alarm";
            }
            enum delete {
              description
                "Delete the file";
            }
            enum log {
              description
                "Log information (no delete or alarm)";
            }
          }
          mandatory true;
        }
      }
    }
    container ebm {
      yexte:user-group "ericsson-support,epg-tracing-admin";
      description
        "Event Based Monitoring setting";
      leaf logical-interface {
        description
          "Logical interface";
        type leafref {
          path "/epg/node/logical-interface/name";
        }
      }
      list server {
        description
          "Event Based Monitoring server name";
        max-elements 3;
        key "name";
        leaf name {
          description
            "Name of server";
          type string {
            pattern '[.0-9A-Za-z_-]*' {
              error-message "Must contain only letters, numbers, underscores or dashes";
            }
            length "1..64";
          }
        }
        leaf address {
          description
            "EBM server addresses";
          type inet:ip-address;
        }
        leaf port {
          description
            "EBM port number";
          type uint16;
        }
      }
      leaf disable-at-overload {
        description
          "Suspend EBM monitoring when overload is detected.";
        type empty;
      }
      action status {
        description
          "Show node EBM status";
        output {
          leaf result {
            type string;
            mandatory true;
          }
        }
      }
    }
    container fault-management {
      description
        "Fault management settings";
      container alarm-threshold {
        description
          "Alarm threshold";
        container application-memory-threshold-reached {
          description
            "Application memory threshold";
          leaf minor-threshold {
            description
              "Minor percentage";
            type uint8 {
              range "10..99" {
                error-message "Invalid value for attribute 'minor-threshold'. Valid values are in range:[10,99]";
              }
            }
          }
          leaf major-threshold {
            description
              "Major percentage";
            type uint8 {
              range "10..99" {
                error-message "Invalid value for attribute 'major-threshold'. Valid values are in range:[10,99]";
              }
            }
          }
          leaf critical-threshold {
            description
              "critical percentage";
            type uint8 {
              range "10..99" {
                error-message "Invalid value for attribute 'critical-threshold'. Valid values are in range:[10,99]";
              }
            }
          }
        }
        container cpu-usage-threshold-reached {
          description
            "Cpu usage threshold reached";
          leaf minor-threshold {
            description
              "Minor percentage";
            type uint8 {
              range "10..100" {
                error-message "Invalid value for attribute 'minor-threshold'. Valid values are in range:[10,100]";
              }
            }
          }
          leaf major-threshold {
            description
              "Major percentage";
            type uint8 {
              range "10..100" {
                error-message "Invalid value for attribute 'major-threshold'. Valid values are in range:[10,100]";
              }
            }
          }
          leaf critical-threshold {
            description
              "critical percentage";
            type uint8 {
              range "10..100" {
                error-message "Invalid value for attribute 'critical-threshold'. Valid values are in range:[10,100]";
              }
            }
          }
        }
        container ipv4-addr-shared-ip-pool-threshold-reached {
          description
            "ipv4 sharedippool minor/major threshold";
          leaf minor-threshold {
            description
              "Ipv4 sharedippool minor percentage";
            type uint8 {
              range "0..100" {
                error-message "Invalid value for attribute 'minor-threshold'. Valid values are in range:[0,100]";
              }
            }
          }
          leaf major-threshold {
            description
              "Ipv4 sharedippool major percentage";
            type uint8 {
              range "0..100" {
                error-message "Invalid value for attribute 'major-threshold'. Valid values are in range:[0,100]";
              }
            }
          }
        }
        container ipv6-addr-shared-ip-pool-threshold-reached {
          description
            "ipv6 sharedippool minor/major threshold";
          leaf minor-threshold {
            description
              "Ipv6 sharedippool minor percentage, minor-threshold should less than major-threshold.";
            type uint8 {
              range "0..100" {
                error-message "Invalid value for attribute 'minor-threshold'. Valid values are in range:[0,100]";
              }
            }
          }
          leaf major-threshold {
            description
              "Ipv6 sharedippool major percentage, major-threshold should more than minor-threshold.";
            type uint8 {
              range "0..100" {
                error-message "Invalid value for attribute 'major-threshold'. Valid values are in range:[0,100]";
              }
            }
          }
        }
      }
      leaf notification-limit {
        description
          "Number of notifications per second that are allowed to be sent from the node";
        type uint8 {
          range "1..100" {
            error-message "Invalid value for attribute 'notification-limit'. Valid values are in range:[1,100]";
          }
        }
      }
      leaf alarm-toggling-prevention-time {
        description
          "Number of seconds after an alarm toggling that it is prevented from being toggled again";
        type uint16 {
          range "0..600" {
            error-message "Invalid value for attribute 'alarm-toggling-prevention-time'. Valid values are in range:[0,600]";
          }
        }
      }
      action active-notifications {
        description
          "Show currently active notifications";
        output {
          leaf result {
            type string;
            mandatory true;
          }
        }
      }
      action clear-notification {
        yexte:user-group "ericsson-support,epg-admin";
        description
          "Force an active notification to be cleared";
        input {
          leaf fault-id {
            description
              "Fault ID of the notification to be cleared";
            type uint32;
            mandatory true;
          }
        }
        output {
          leaf result {
            type string;
            mandatory true;
          }
        }
      }
    }
    container internal-debug {
      yexte:user-group "ericsson-support";
      description
        "Actions used internally";
      leaf no-pm-suspect-flag {
        description
          "not allow suspect flag in pm job ROP file";
        type empty;
      }
      container traceoptions {
        description
          "PGWCD trace options";
        presence "traceoptions need presence";
        uses node-traceoptions-type;
      }
      container uetrace {
        description
          "UE trace options";
        uses uetrace-type;
      }
      action execute {
        description
          "Execute a remote debugging command.";
        input {
          leaf cmd-string {
            description
              "Command to execute";
            type string;
            mandatory true;
          }
        }
        output {
          leaf result {
            type string;
            mandatory true;
          }
        }
      }
      action export-pm-xml-file {
        description
          "Write a PM XML file with current node counters.";
        output {
          leaf result {
            type string;
            mandatory true;
          }
        }
      }
      action reset-alerts {
        description
          "Resets info about any existing alerts";
        output {
          leaf result {
            type string;
            mandatory true;
          }
        }
      }
      action status {
        description
          "Show detailed board CPU and Memory Statistics";
        output {
          leaf result {
            type string;
            mandatory true;
          }
        }
      }
      action memtracker-start {
        description
          "Start memtracker";
        input {
          leaf board-name {
            description
              "Boardname (e.g\\. gc-0/5/1)";
            type string {
              pattern '((gc|gu)-0/(30|(1|2)[0-9]|[1-9])/1)|rp' {
                error-message "Invalid board name";
              }
            }
            mandatory true;
          }
          leaf application-id {
            description
              "Id of application (e.g\\. pgw, gsc, sgw, ppb, gpsd)";
            type enumeration {
              enum pgw {
                description
                  "Trace pgw allocations";
              }
              enum sgw {
                description
                  "Trace sgw allocations";
              }
              enum gsc {
                description
                  "Trace gsc allocations";
              }
              enum ppb {
                description
                  "Trace ppb allocations";
              }
              enum gpsd {
                description
                  "Trace gpsd allocations";
              }
            }
            mandatory true;
          }
          leaf sampling-interval {
            description
              "Interval doing book keeping of memory allocations";
            type string {
              pattern '(1)|(2)|(4)|(8)|(16)|(32)|(64)|(128)' {
                error-message "Value must be a power of 2. Between 1 and 128.";
              }
              length "0..3";
            }
          }
        }
        output {
          leaf result {
            type string;
            mandatory true;
          }
        }
      }
      action memtracker-stop {
        description
          "Stop memtracker";
        input {
          leaf board-name {
            description
              "Boardname (e.g\\. gc-0/5/1)";
            type string;
            mandatory true;
          }
          leaf application-id {
            description
              "Id of application (e.g\\. pgw, gsc, sgw, ppb, gpsd)";
            type enumeration {
              enum pgw {
                description
                  "Trace pgw allocations";
              }
              enum sgw {
                description
                  "Trace sgw allocations";
              }
              enum gsc {
                description
                  "Trace gsc allocations";
              }
              enum ppb {
                description
                  "Trace ppb allocations";
              }
              enum gpsd {
                description
                  "Trace gpsd allocations";
              }
            }
            mandatory true;
          }
        }
        output {
          leaf result {
            type string;
            mandatory true;
          }
        }
      }
      action memtracker-report {
        description
          "Generate memtracker report";
        input {
          leaf board-name {
            description
              "Boardname (e.g\\. gc-0/5/1)";
            type string;
            mandatory true;
          }
          leaf application-id {
            description
              "Id of application (e.g\\. pgw, gsc, sgw, ppb, gpsd)";
            type enumeration {
              enum pgw {
                description
                  "Trace pgw allocations";
              }
              enum sgw {
                description
                  "Trace sgw allocations";
              }
              enum gsc {
                description
                  "Trace gsc allocations";
              }
              enum ppb {
                description
                  "Trace ppb allocations";
              }
              enum gpsd {
                description
                  "Trace gpsd allocations";
              }
            }
            mandatory true;
          }
        }
        output {
          leaf result {
            type string;
            mandatory true;
          }
        }
      }
      action memtracker-show {
        description
          "Show memtracker status";
        input {
          leaf board-name {
            description
              "Boardname (e.g\\. gc-0/5/1)";
            type string;
            mandatory true;
          }
          leaf application-id {
            description
              "Id of application (e.g\\. pgw, gsc, sgw, ppb, gpsd)";
            type enumeration {
              enum pgw {
                description
                  "Trace pgw allocations";
              }
              enum sgw {
                description
                  "Trace sgw allocations";
              }
              enum gsc {
                description
                  "Trace gsc allocations";
              }
              enum ppb {
                description
                  "Trace ppb allocations";
              }
              enum gpsd {
                description
                  "Trace gpsd allocations";
              }
            }
            mandatory true;
          }
        }
        output {
          leaf result {
            type string;
            mandatory true;
          }
        }
      }
      container session-resilience {
        description
          "SGW session resilience commands";
        action generate-imsi-or-imei-sgw-pe {
          description
            "Generate IMSIs or IMEIs based on certain criteria for SGW pe:s";
          input {
            leaf output-type {
              description
                "The output type should be either imsi or imei";
              type enumeration {
                enum imsi {
                  description
                    "imsi";
                }
                enum imei {
                  description
                    "imei";
                }
              }
              mandatory true;
            }
            leaf start-imsi-or-imei {
              description
                "The IMSI or IMEI that will be used as the start of the search for matching IMSIs or IMEIs";
              type string {
                pattern '[0-9]{5,16}' {
                  error-message "IMSI or IMEI must be 5 to 16 digits.";
                }
              }
              mandatory true;
            }
            leaf count {
              description
                "The number of IMSIs or IMEIs to generate";
              type uint32;
              mandatory true;
            }
            leaf increment {
              description
                "How much to increment IMSI or IMEI when searching (examples: 1, 10000 etc)";
              type uint32;
              mandatory true;
            }
            leaf primary-sc-pe {
              description
                "The primary sgw-c process entity for the IMSIs or IMEIs\\. Should be in the format: SC:3:2 (boardgroup 3 and board 2) or 'any'";
              type string;
              mandatory true;
            }
            leaf secondary-sc-pe {
              description
                "The secondary sgw-c process entity for the IMSIs or IMEIs\\. Should be in the format: SC:3:2 (boardgroup 3 and board 2) or 'any'";
              type string;
              mandatory true;
            }
            leaf primary-u-pe {
              description
                "The primary U(ser plane) process entity for the IMSIs or IMEIs\\. Should be in the format: U:3:2 (boardgroup 3 and board 2) or 'any'";
              type string;
              mandatory true;
            }
            leaf secondary-u-pe {
              description
                "The secondary U(ser plane) process entity for the IMSIs or IMEIs\\. Should be in the format: U:3:2 (boardgroup 3 and board 2) or 'any'";
              type string;
              mandatory true;
            }
          }
          output {
            leaf result {
              type string;
              mandatory true;
            }
          }
        }
        action generate-imsi-or-imei-pgw-pe {
          description
            "Generate IMSIs or IMEIs based on certain criteria for PGW pe:s";
          input {
            leaf output-type {
              description
                "The output type should be either imsi or imei";
              type enumeration {
                enum imsi {
                  description
                    "imsi";
                }
                enum imei {
                  description
                    "imei";
                }
              }
              mandatory true;
            }
            leaf start-imsi-or-imei {
              description
                "The IMSI or IMEI that will be used as the start of the search for matching IMSIs or IMEIs";
              type string {
                pattern '[0-9]{5,16}' {
                  error-message "IMSI or IMEI must be 5 to 16 digits.";
                }
              }
              mandatory true;
            }
            leaf count {
              description
                "The number of IMSIs or IMEIs to generate";
              type uint32;
              mandatory true;
            }
            leaf increment {
              description
                "How much to increment IMSI or IMEI when searching (examples: 1, 10000 etc)";
              type uint32;
              mandatory true;
            }
            leaf primary-pc-pe {
              description
                "The primary pgw-c process entity for the IMSIs or IMEIs\\. Should be in the format: PC:3:2 (boardgroup 3 and board 2) or 'any'";
              type string;
              mandatory true;
            }
            leaf secondary-pc-pe {
              description
                "The secondary pgw-c process entity for the IMSIs or IMEIs\\. Should be in the format: PC:3:2 (boardgroup 3 and board 2) or 'any'";
              type string;
              mandatory true;
            }
            leaf primary-u-pe {
              description
                "The primary U(ser plane) process entity for the IMSIs or IMEIs\\. Should be in the format: U:3:2 (boardgroup 3 and board 2) or 'any'";
              type string;
              mandatory true;
            }
            leaf secondary-u-pe {
              description
                "The secondary U(ser plane) process entity for the IMSIs or IMEIs\\. Should be in the format: U:3:2 (boardgroup 3 and board 2) or 'any'";
              type string;
              mandatory true;
            }
          }
          output {
            leaf result {
              type string;
              mandatory true;
            }
          }
        }
        action generate-imsi-or-imei-li {
          description
            "Generate IMSIs or IMEIs based on certain criteria";
          input {
            leaf output-type {
              description
                "The output type should be either imsi or imei";
              type enumeration {
                enum imsi {
                  description
                    "imsi";
                }
                enum imei {
                  description
                    "imei";
                }
              }
              mandatory true;
            }
            leaf start-imsi-or-imei {
              description
                "The IMSI or IMEI that will be used as the start of the search for matching IMSIs or IMEIs";
              type string {
                pattern '[0-9]{5,16}' {
                  error-message "IMSI or IMEI must be 5 to 16 digits.";
                }
              }
              mandatory true;
            }
            leaf count {
              description
                "The number of IMSIs or IMEIs to generate";
              type uint32;
              mandatory true;
            }
            leaf increment {
              description
                "How much to increment IMSI or IMEI when searching (examples: 1, 10000 etc)";
              type uint32;
              mandatory true;
            }
            leaf load-index {
              description
                "The load index to generate the IMSIs or IMEIs for";
              type uint16 {
                range "0..8191" {
                  error-message "Invalid value for attribute 'load-index'. Valid values are in range:[0,8191]";
                }
              }
              mandatory true;
            }
          }
          output {
            leaf result {
              type string;
              mandatory true;
            }
          }
        }
        action get-loadindex-scaleout {
          description
            "Get a load-index based on certain criteria";
          input {
            leaf scaleout-pe {
              description
                "The process entity that is added in scale out.";
              type string {
                pattern '((SC|PC|U)(:[0-9][0-9]?){2})' {
                  error-message "Invalid process entity, must be SC|PC|U:[0-9]:[0-9]";
                }
              }
              mandatory true;
            }
            leaf primary-src-pe {
              description
                "The primary process entity holding a load index before the scale out.";
              type string {
                pattern '(((SC|PC|U)(:[0-9][0-9]?){2}:?[0-9]?[0-9]?)|any)' {
                  error-message "Invalid process entity, must be SC|PC|U:[0-9]:[0-9]+ or any";
                }
              }
              mandatory true;
            }
            leaf secondary-src-pe {
              description
                "The secondary process entity holding a load index before the scale out.";
              type string {
                pattern '(((SC|PC|U)(:[0-9][0-9]?){2}:?[0-9]?[0-9]?)|any)' {
                  error-message "Invalid process entity, must be SC|PC|U:[0-9]:[0-9]+ or any";
                }
              }
              mandatory true;
            }
            leaf primary-dst-pe {
              description
                "The primary process entity holding a load index after the scale out.";
              type string {
                pattern '(((SC|PC|U)(:[0-9][0-9]?){2}:?[0-9]?[0-9]?)|any)' {
                  error-message "Invalid process entity, must be SC|PC|U:[0-9]:[0-9]+ or any";
                }
              }
              mandatory true;
            }
            leaf secondary-dst-pe {
              description
                "The secondary process entity holding a load index after the scale out.";
              type string {
                pattern '(((SC|PC|U)(:[0-9][0-9]?){2}:?[0-9]?[0-9]?)|any)' {
                  error-message "Invalid process entity, must be SC|PC|U:[0-9]:[0-9]+ or any";
                }
              }
              mandatory true;
            }
            leaf count {
              description
                "The number of load-indexes to find";
              type uint32;
              mandatory true;
            }
          }
          output {
            leaf result {
              type string;
              mandatory true;
            }
          }
        }
        action get-loadindex-scalein {
          description
            "Get a load-index based on certain criteria";
          input {
            leaf scalein-pe {
              description
                "The process entity that is decomissioned in scale in.";
              type string {
                pattern '((SC|PC)(:[0-9][0-9]?){2})' {
                  error-message "Invalid process entity, must be SC|PC:[0-9]:[0-9]";
                }
              }
              mandatory true;
            }
            leaf primary-src-pe {
              description
                "The primary process entity holding a load index before the scale in.";
              type string {
                pattern '(((SC|PC)(:[0-9][0-9]?){2}:?[0-9]?[0-9]?)|any)' {
                  error-message "Invalid process entity, must be SC|PC:[0-9]:[0-9]+ or any";
                }
              }
              mandatory true;
            }
            leaf secondary-src-pe {
              description
                "The secondary process entity holding a load index before the scale in.";
              type string {
                pattern '(((SC|PC)(:[0-9][0-9]?){2}:?[0-9]?[0-9]?)|any)' {
                  error-message "Invalid process entity, must be SC|PC:[0-9]:[0-9]+ or any";
                }
              }
              mandatory true;
            }
            leaf primary-dst-pe {
              description
                "The primary process entity holding a load index after the scale in.";
              type string {
                pattern '(((SC|PC)(:[0-9][0-9]?){2}:?[0-9]?[0-9]?)|any)' {
                  error-message "Invalid process entity, must be SC|PC:[0-9]:[0-9]+ or any";
                }
              }
              mandatory true;
            }
            leaf secondary-dst-pe {
              description
                "The secondary process entity holding a load index after the scale in.";
              type string {
                pattern '(((SC|PC)(:[0-9][0-9]?){2}:?[0-9]?[0-9]?)|any)' {
                  error-message "Invalid process entity, must be SC|PC:[0-9]:[0-9]+ or any";
                }
              }
              mandatory true;
            }
            leaf count {
              description
                "The number of load-indexes to find";
              type uint32;
              mandatory true;
            }
          }
          output {
            leaf result {
              type string;
              mandatory true;
            }
          }
        }
        container lim {
          description
            "LIM manager session resilience commands";
          action clients {
            description
              "Show the clients connected to the master LIM manager";
            output {
              leaf result {
                type string;
                mandatory true;
              }
            }
          }
          action history-li {
            description
              "Show the orders issued and the confirmations received by the LIM manager for a specific load index";
            input {
              leaf pe-type {
                description
                  "Specifies the process entity type [sgwc|pgwc|u|diameterendpoint] ";
                type string {
                  pattern '(sgwc|pgwc|u|diameterendpoint)' {
                    error-message "Invalid process entity type";
                  }
                }
                mandatory true;
              }
              leaf load-index {
                description
                  "Specify the load index or 'all' for all load indexes";
                type string {
                  pattern '(all|[0-9]{1,5})' {
                    error-message "Invalid load index (should be 'all' or 0-2047)";
                  }
                }
                mandatory true;
              }
            }
            output {
              leaf result {
                type string;
                mandatory true;
              }
            }
          }
          action master-table {
            description
              "Show the master load index map table";
            input {
              leaf pe-type {
                description
                  "Specifies the process entity type [all|sgwc|pgwc|u|diameterendpoint]";
                type string {
                  pattern '(all|sgwc|pgwc|u|diameterendpoint)' {
                    error-message "Invalid process entity type";
                  }
                }
                mandatory true;
              }
            }
            output {
              leaf result {
                type string;
                mandatory true;
              }
            }
          }
          action master-table-li {
            description
              "Show the master load index map table";
            input {
              leaf pe-type {
                description
                  "Specifies the process entity type [all|sgwc|pgwc|u|diameterendpoint]";
                type string {
                  pattern '(all|sgwc|pgwc|u|diameterendpoint)' {
                    error-message "Invalid process entity type";
                  }
                }
                mandatory true;
              }
              leaf load-indices {
                description
                  "Load indices to print, might be either a comma-separated list, a range or both, for example 1,3,5-7,9";
                type string;
                mandatory true;
              }
            }
            output {
              leaf result {
                type string;
                mandatory true;
              }
            }
          }
          action manager-status {
            description
              "Show the status of the LIM manager";
            output {
              leaf result {
                type string;
                mandatory true;
              }
            }
          }
        }
        action imsi-mapping {
          description
            "Show the load index and process entities for an IMSI";
          input {
            leaf imsi {
              description
                "Imsi identity";
              type uint64 {
                range "1..999999999999999" {
                  error-message "Invalid value for attribute 'imsi'. Valid values are in range:[1,999999999999999]";
                }
              }
              mandatory true;
            }
          }
          output {
            leaf result {
              type string;
              mandatory true;
            }
          }
        }
        action imei-mapping {
          description
            "Show the load index and process entities for an IMEI";
          input {
            leaf imei {
              description
                "Imei identity";
              type uint64 {
                range "1..9999999999999999" {
                  error-message "Invalid value for attribute 'imei'. Valid values are in range:[1,9999999999999999]";
                }
              }
              mandatory true;
            }
          }
          output {
            leaf result {
              type string;
              mandatory true;
            }
          }
        }
        action ip-mapping {
          description
            "Show the load index and process entities for an IP";
          input {
            leaf ip {
              description
                "IP address";
              type inet:ip-address;
              mandatory true;
            }
          }
          output {
            leaf result {
              type string;
              mandatory true;
            }
          }
        }
      }
    }
    action status {
      description
        "Show Node operational status information";
      output {
        leaf result {
          type string;
          mandatory true;
        }
      }
    }
    container olp {
      leaf reserve-priority-service {
        description
          "Priority service call reservation margin percentage";
        type string {
          pattern '((0.[0-9])|([0-9])|([1-9].[0-9])|([1-9][0-9])|([1-9][0-9].[0-9])|(100)|(100.0))' {
            error-message "Value must be a number from 0.0 to 100.0";
          }
        }
      }
      action status {
        description
          "Show Overload status information";
        input {
          leaf value {
            description
              "detail or board name";
            type string {
              pattern 'brief|detail|(gc|gu)-0/(30|(1|2)[0-9]|[1-9])/1' {
                error-message "ERROR: Invalid value for parameter value. Valid values are strings in a specified format. Type: value? for more information on the format to use.";
              }
            }
          }
        }
        output {
          leaf result {
            type string;
            mandatory true;
          }
        }
      }
    }
    container icr {
      description
        "Configure ICR Capabilities";
      presence "icr need presence";
      container switchover-threshold {
        description
          "Service availablity threshold";
        leaf control-plane {
          type uint8 {
            range "0..100" {
              error-message "Invalid value for attribute 'control-plane'. Valid values are in range:[0,100]";
            }
          }
          default "1";
        }
        leaf user-plane {
          type uint8 {
            range "0..100" {
              error-message "Invalid value for attribute 'user-plane'. Valid values are in range:[0,100]";
            }
          }
          default "1";
        }
      }
      action status {
        description
          "Show icr status information";
        input {
          leaf value {
            description
              "active or standby node";
            type string {
              pattern 'active|standby' {
                error-message "ERROR: invalid parameter for node. Valid node are active or standby";
              }
            }
          }
        }
        output {
          leaf result {
            type string;
            mandatory true;
          }
        }
      }
      leaf paired-mode {
        description
          "Set if this node is paired with another in one EPG setup";
        type empty;
      }
    }
    container multi-config {
      description
        "Multiple configuration management.";
      status current {
        yexte:preliminary;
      }
      leaf max-instance-number {
        description
          "The maximum size of configuration list.";
        type uint8 {
          range "1..50" {
            error-message "Invalid value for attribute 'max-instance-number'. Valid values are in range:[1,50]";
          }
        }
        default "50";
      }
      leaf enable-session-upgrade {
        description
          "Let sessions upgrade to a later configuration version when possible";
        status current {
          yexte:preliminary;
        }
        type empty;
      }
      leaf session-upgrade-rate {
        description
          "The rate at which sessions are evaluated for configuration upgrade. Unit is evaluations per minute.";
        status current {
          yexte:preliminary;
        }
        type uint32 {
          range "1..600000" {
            error-message "Invalid value for attribute 'session-upgrade-rate'. Valid values are in range:[1,600000]";
          }
        }
        default "6000";
      }
      action list-config-instances {
        description
          "Show all configuration version.";
        output {
          leaf result {
            type string;
            mandatory true;
          }
        }
      }
      action delete {
        description
          "Delete specific configuration.";
        input {
          leaf version {
            description
              "delete configuration with specific version";
            type string;
            mandatory true;
          }
        }
        output {
          leaf result {
            type string;
            mandatory true;
          }
        }
      }
    }
  }

  grouping load-control-information-type {
    leaf bearer-limit {
      description
        "Maximum number of bearers expected on the node\\. This value is only used to calculate the load metric based on the number of bearers.";
      type uint32 {
        range "1..4294967295" {
          error-message "Invalid value for attribute 'bearer-limit'. Valid values are in range:[1,4294967295]";
        }
      }
      mandatory true;
    }
    leaf sending-period {
      description
        "Sending period in seconds\\. A new Load Control Information is sent if this period of time has passed since the last time it was sent.";
      type uint32 {
        range "30..2678400" {
          error-message "Invalid value for attribute 'sending-period'. Valid values are in range:[30,2678400]";
        }
      }
      default "120";
    }
    leaf metric-threshold {
      description
        "Metric change threshold in percentage\\. A new Load Control Information is sent if there is an increase or decrease that is more than or equal to this many percentage points in the load metric on the node.";
      type uint8 {
        range "1..100" {
          error-message "Invalid value for attribute 'metric-threshold'. Valid values are in range:[1,100]";
        }
      }
      default "5";
    }
    leaf calculation-period {
      description
        "Calculation period in seconds\\. The load metric is recalculated every <calculation-period> seconds.";
      type uint16 {
        range "30..7200" {
          error-message "Invalid value for attribute 'calculation-period'. Valid values are in range:[30,7200]";
        }
      }
      default "60";
    }
    leaf maximum-metric {
      description
        "The maximum load metric percentage value to be sent\\. <maximum-metric> is sent instead of any larger calculated load metric value.";
      type uint8 {
        range "0..100" {
          error-message "Invalid value for attribute 'maximum-metric'. Valid values are in range:[0,100]";
        }
      }
      default "99";
    }
  }

  grouping pgw-pause-charging-type {
    leaf packets-loss-threshold {
      description
        "Packets loss threshold per PDN";
      type uint32 {
        range "1..67108863" {
          error-message "Invalid value for attribute 'packets-loss-threshold'. Valid values are in range:[1,67108863]";
        }
      }
      default "1000";
    }
    leaf bytes-loss-threshold {
      description
        "Bytes loss threshold per PDN";
      type uint32 {
        range "64..4294967295" {
          error-message "Invalid value for attribute 'bytes-loss-threshold'. Valid values are in range:[64,4294967295]";
        }
      }
      default "1000000";
    }
  }

  grouping sgw-control-plane-type {
    container load-control {
      description
        "Manipulate the signaling performance settings of the SGW";
      leaf sgw-deletes-per-second {
        description
          "Maximum SGW PDN Connection deactivation rate";
        type uint32 {
          range "50..30000" {
            error-message "Invalid value for attribute 'sgw-deletes-per-second'. Valid values are in range:[50,30000]";
          }
        }
        default "700";
      }
      leaf mme-restoration-ddn-per-second {
        description
          "Maximum rate of DDN internally generated by the command of MME Restoration";
        type uint32 {
          range "50..80000" {
            error-message "Invalid value for attribute 'mme-restoration-ddn-per-second'. Valid values are in range:[50,80000]";
          }
        }
        default "700";
      }
      leaf ddn-per-second {
        description
          "Maximum rate of DDN";
        type uint32 {
          range "1000..80000" {
            error-message "Invalid value for attribute 'ddn-per-second'. Valid values are in range:[1000,80000]";
          }
        }
      }
    }
    container session {
      description
        "Session settings";
      container block {
        yexte:user-group "ericsson-support,epg-admin";
        description
          "New EPS sessions blocked";
        presence "block need presence";
        leaf node {
          description
            "Block on node level";
          type empty;
        }
      }
      action terminate {
        yexte:user-group "ericsson-support,epg-admin";
        description
          "Terminate existing EPS sessions";
        output {
          leaf result {
            type string;
            mandatory true;
          }
        }
      }
      action terminate-stop {
        yexte:user-group "ericsson-support,epg-admin";
        description
          "Stop terminating existing EPS sessions";
        output {
          leaf result {
            type string;
            mandatory true;
          }
        }
      }
      action terminate-idle-session-start {
        yexte:user-group "ericsson-support,epg-admin";
        description
          "Start terminating idle UEs";
        output {
          leaf result {
            type string;
            mandatory true;
          }
        }
      }
      action terminate-idle-session-stop {
        yexte:user-group "ericsson-support,epg-admin";
        description
          "Stop terminating idle UEs";
        output {
          leaf result {
            type string;
            mandatory true;
          }
        }
      }
      action terminate-idle-session-show {
        description
          "Terminate idle UE status";
        output {
          leaf result {
            type string;
            mandatory true;
          }
        }
      }
      leaf-list no-idle-termination-qci {
        description
          "Session with bearers having configured qciValue should not be terminated during idle session deletion process\\. If nothing configured, 1, 65, 66, 67, 69, 82, 83 are the default values.";
        type uint8 {
          range "1..254" {
            error-message "Invalid value for attribute 'no-idle-termination-qci'. Valid values are in range:[1,254]";
          }
        }
      }
    }
    container signaling {
      description
        "SGW signaling setting";
      container preservation-information {
        description
          "Enable sending GTP message private extension upon UE status change";
        presence "preservation-information need presence";
        leaf disable-suppress {
          description
            "Disable suppression of an MBR message notifying UE status";
          type empty;
        }
        leaf suppress-timeout {
          description
            "Setting suppression timeout";
          type uint16 {
            range "1..300" {
              error-message "Invalid value for attribute 'suppress-timeout'. Valid values are in range:[1,300]";
            }
          }
        }
        leaf max-suppress {
          description
            "Setting max suppression count";
          type uint8 {
            range "1..10" {
              error-message "Invalid value for attribute 'max-suppress'. Valid values are in range:[1,10]";
            }
          }
        }
        leaf-list exclude-qci {
          description
            "Setting Qci excluded from preservation information";
          type string {
            pattern '([1-9]|(12[8-9])|(1[3-9][0-9])|(2[0-4][0-9])|(25[0-4]))' {
              error-message "Value must be a number from 1 to 9 or 128 to 254";
            }
            length "1..3";
          }
          max-elements 10;
        }
        leaf-list exclude-pgw {
          description
            "Setting PGW IP address-list excluded from preservation information : address-list should be wrapped with double-quotation mark";
          type string;
        }
      }
      leaf no-extra-s5s8-signaling {
        description
          "Enables the feature";
        type empty;
      }
      action info {
        description
          "The number of suppressed Modify Bearer Request messages when sending of extra information to the PGW is disabled";
        output {
          leaf result {
            type string;
            mandatory true;
          }
        }
      }
      action gtp-restart-counter {
        description
          "Show GTP restart counter.";
        output {
          leaf result {
            type string;
            mandatory true;
          }
        }
      }
      action set-gtp-restart-counter {
        yexte:user-group "ericsson-support,epg-admin";
        description
          "Set GTP restart counter\\. SGW has to be stopped and started before changes take effect\\. The restart will add one (1) to the count.";
        input {
          leaf count {
            description
              "Set GTP restart counter\\. SGW has to be stopped and started before changes take effect\\. The restart will add one (1) to the count.";
            type uint8 {
              range "0..255" {
                error-message "Invalid value for attribute 'count'. Valid values are in range:[0,255]";
              }
            }
            mandatory true;
          }
        }
        output {
          leaf result {
            type string;
            mandatory true;
          }
        }
      }
      action origin-state-id {
        description
          "Show SGW origin-state id.";
        output {
          leaf result {
            type string;
            mandatory true;
          }
        }
      }
      action set-origin-state-id {
        description
          "Set SGW origin-state id\\. SGW has to be stopped and started before changes take effect\\. The restart will add one (1) to the count.";
        input {
          leaf count {
            description
              "Set origin-state-id\\. SGW has to be stopped and started before changes take effect\\. The restart will add one (1) to the count.";
            type uint32 {
              range "0..4294967295" {
                error-message "Invalid value for attribute 'count'. Valid values are in range:[0,4294967295]";
              }
            }
            mandatory true;
          }
        }
        output {
          leaf result {
            type string;
            mandatory true;
          }
        }
      }
    }
  }

  grouping session-priority-arp-priority-type-sgw {
    leaf name {
      description
        "Configure ARP priority level for mapping between ARP and message priority";
      type uint8 {
        range "1..15" {
          error-message "Invalid value for attribute 'arp-index'. Valid values are in range:[1,15]";
        }
      }
    }
    leaf message-priority-level {
      description
        "Configure message priority level which is used as the default value";
      type uint8 {
        range "0..15" {
          error-message "Invalid value for attribute 'message-priority-level'. Valid values are in range:[0,15]";
        }
      }
    }
    list qci {
      max-elements 254;
      key "name";
      uses session-priority-qci-type-sgw;
    }
  }

  grouping session-priority-qci-type-sgw {
    leaf name {
      description
        "Configure QCI for mapping between ARP, QCI and message priority";
      type uint8 {
        range "1..254" {
          error-message "Invalid value for attribute 'qci-index'. Valid values are in range:[1,254]";
        }
      }
    }
    leaf message-priority-level {
      description
        "Configure message priority level for mapping between ARP, QCI and message priority";
      type uint8 {
        range "0..15" {
          error-message "Invalid value for attribute 'message-priority-level'. Valid values are in range:[0,15]";
        }
      }
    }
  }

  grouping sgw-charging-profiles {
    leaf name {
      description
        "Profile 0..15";
      type uint8 {
        range "0..15" {
          error-message "Invalid value for attribute 'profile-id'. Valid values are in range:[0,15]";
        }
      }
    }
    leaf volume-limit {
      description
        "Volume of charging data to buffer";
      type uint32 {
        range "100..2097152" {
          error-message "Invalid value for attribute 'volume-limit'. Valid values are in range:[100,2097152]";
        }
      }
    }
    leaf time-limit {
      description
        "Time to buffer charging data";
      type uint16 {
        range "15..1440" {
          error-message "Invalid value for attribute 'time-limit'. Valid values are in range:[15,1440]";
        }
      }
    }
    leaf change-limit {
      description
        "Maximum number of charging condition changes that forces ACR Interim generation";
      type uint8 {
        range "1..10" {
          error-message "Invalid value for attribute 'change-limit'. Valid values are in range:[1,10]";
        }
      }
    }
    leaf no-cdr-generation {
      description
        "Do not generate charging records";
      type empty;
    }
    leaf acr-interim-interval {
      description
        "Interval in minutes for generating ACR interim";
      type uint16 {
        range "1..1440" {
          error-message "Invalid value for attribute 'acr-interim-interval'. Valid values are in range:[1,1440]";
        }
      }
    }
    leaf internal-acr-interim-interval {
      description
        "Internal interval in minutes for generating ACR interim";
      type uint8 {
        range "1..10" {
          error-message "Invalid value for attribute 'internal-acr-interim-interval'. Valid values are in range:[1,10]";
        }
      }
    }
  }

  grouping sgw-charging-log-type {
    leaf maximum-size {
      description
        "Maximum size of charging log file";
      type uint32 {
        range "1024..102400" {
          error-message "Invalid value for attribute 'maximum-size'. Valid values are in range:[1024,102400]";
        }
      }
    }
    leaf maximum-age {
      description
        "Maximum age of charging log file";
      type uint16 {
        range "5..1440" {
          error-message "Invalid value for attribute 'maximum-age'. Valid values are in range:[5,1440]";
        }
      }
    }
    leaf compression {
      description
        "Compress all CDR log files";
      type empty;
    }
    container local-data-file {
      description
        "CDRs meant for normal offline transfer";
      leaf force-empty-files {
        description
          "Generate empty CDR log files if no CDRs are received";
        type empty;
      }
    }
  }

  grouping ebm-event-type {
    leaf session-creation {
      description
        "session-creation event is collected";
      type empty;
    }
    leaf session-deletion {
      description
        "session-deletion event is collected";
      type empty;
    }
    leaf session-suspension {
      description
        "session-suspension event is collected";
      type empty;
    }
    leaf session-resume {
      description
        "session-resume event is collected";
      type empty;
    }
    leaf bearer-creation {
      description
        "bearer-creation event is collected";
      type empty;
    }
    leaf bearer-deletion {
      description
        "bearer-deletion event is collected";
      type empty;
    }
    leaf bearer-update {
      description
        "bearer-update event is collected";
      type empty;
    }
    leaf bearer-modification {
      description
        "bearer-modification event is collected";
      type empty;
    }
    leaf downlink-data-notification {
      description
        "downlink-data-notification event is collected";
      type empty;
    }
    leaf indirect-data-forwarding-creation {
      description
        "indirect-data-forwarding-creation event is collected";
      type empty;
    }
    leaf indirect-data-forwarding-deletion {
      description
        "indirect-data-forwarding-deletion event is collected";
      type empty;
    }
    leaf change-notification {
      description
        "change-notification event is collected";
      type empty;
    }
  }

  grouping ebm-type {
    list ebm-profile {
      must '/epg/sgw/ebm/ebm-profile[name=current()/name]/event' {
        error-message "event is mandatory";
      }
      max-elements 16;
      key "name";
      uses sgw-ebm-profile-type;
    }
    action statistics {
      description
        "SGW EBM statistics";
      output {
        leaf result {
          type string;
          mandatory true;
        }
      }
    }
  }

  grouping sgw-ebm-profile-type {
    leaf name {
      description
        "Event based monitoring profile name";
      type string;
    }
    container selector {
      description
        "User selection settings";
      uses sgw-ebm-profile-selector-type;
    }
    container event {
      description
        "Monitoring events settings";
      presence "event need presence";
      uses ebm-event-type;
    }
  }

  grouping sgw-ebm-profile-selector-type {
    leaf apn {
      description
        "Select users based on APN";
      type string;
    }
    leaf imsi {
      description
        "Select users based on IMSI regular expression";
      type string;
    }
    leaf cause-code {
      description
        "Filter event based on cause code";
      type uint16 {
        range "0..65535" {
          error-message "Invalid value for attribute 'cause-code'. Valid values are in range:[0,65535]";
        }
      }
    }
  }

  grouping interface-ipv6-type {
    leaf mtu {
      description
        "IPv6 Maximum transmission unit";
      type uint16 {
        range "1280..3022" {
          error-message "Invalid value for attribute 'mtu'. Valid values are in range:[1280,3022]";
        }
      }
    }
    leaf no-generate-udp-checksum {
      description
        "If enabled, turns off udp checksum generation for IPv6";
      type empty;
    }
    leaf no-validate-udp-checksum {
      description
        "If enabled, turns off udp checksum validation for IPv6";
      type empty;
    }
  }

  grouping sxa-user-plane-node-type {
    leaf name {
      description
        "User plane node name";
      type string {
        pattern '[.0-9A-Za-z_-]*' {
          error-message "Must contain only letters, numbers, underscores or dashes";
        }
        length "1..64";
      }
    }
    leaf li-t3 {
      description
        "Reference to the li-t3 in [epg node lawful-intercept user-plane-selection]";
      type leafref {
        path "/epg/node/lawful-intercept/user-plane-selection/li-t3/name";
      }
    }
    leaf pfcp-address {
      description
        "Pfcp Sxa Address";
      type inet:ip-address;
      mandatory true;
    }
    leaf dcnr {
      description
        "Dual connectivity NR";
      type empty;
    }
    leaf idle-pkts-session {
      description
        "Number of buffered idle packets per session";
      type uint16 {
        range "0..1024" {
          error-message "Invalid value for attribute 'idle-pkts-session'. Valid values are in range:[0,1024]";
        }
      }
    }
    container s1s4s11s12-u {
      description
        "s1s4s11s12-u interface";
      presence "s1s4s11s12-u need presence";
      must '(not (../s11-u)) and (not (../s1s4s12-u))' {
        error-message "Can't configure S11U or S1S4S12U at the same time as S1S4S11S12U configured";
      }
      leaf network-instance {
        type string;
      }
      leaf dscp-map {
        description
          "dscp-map name";
        type leafref {
          path "/epg/node/qos-control/dscp-map/name";
        }
      }
      leaf path-failure {
        description
          "If configured, delete the PDN connections on the failed s1s4s11s12-u path";
        type empty;
      }
    }
    container s1s4s12-u {
      description
        "s1s4s12-u interface";
      presence "s1s4s12-u need presence";
      must 'not (../s1s4s11s12-u)' {
        error-message "Can't configure S1S4S11S12U at the same time as separate S1S4S12U configured";
      }
      must '(../s11-u)' {
        error-message "Can't configure S1S4S12U without separate S11U configured";
      }
      leaf network-instance {
        type string;
      }
      leaf dscp-map {
        description
          "dscp-map name";
        type leafref {
          path "/epg/node/qos-control/dscp-map/name";
        }
      }
      leaf path-failure {
        description
          "If configured, delete the PDN connections on the failed s1s4s12-u path";
        type empty;
      }
    }
    container s11-u {
      description
        "s11-u interface";
      presence "s11-u need presence";
      must 'not (../s1s4s11s12-u)' {
        error-message "Can't configure S1S4S11S12U at the same time as separate S11U configured";
      }
      must '(../s1s4s12-u)' {
        error-message "Can't configure separate S11U without S1S4S12U configured";
      }
      leaf network-instance {
        type string;
      }
      leaf dscp-map {
        description
          "dscp-map name";
        type leafref {
          path "/epg/node/qos-control/dscp-map/name";
        }
      }
      leaf path-failure {
        description
          "If configured, delete the PDN connections on the failed s11-u path";
        type empty;
      }
    }
    container s5s8-u {
      description
        "s5s8-u interface";
      presence "s5s8-u need presence";
      must '(not (../s5-u)) and (not (../s8-u))' {
        error-message "Can't configure S5S8U at the same time as separate S5U or S8U";
      }
      leaf network-instance {
        type string;
      }
      leaf dscp-map {
        description
          "dscp-map name";
        type leafref {
          path "/epg/node/qos-control/dscp-map/name";
        }
      }
      leaf path-failure {
        description
          "If configured, delete the PDN connections on the failed s5s8-u path";
        type empty;
      }
    }
    container s5-u {
      description
        "s5-u interface";
      presence "s5-u need presence";
      must 'not (../s5s8-u)' {
        error-message "Can't configure separate S5U at the same time as S5S8U";
      }
      leaf network-instance {
        type string;
      }
      leaf dscp-map {
        description
          "dscp-map name";
        type leafref {
          path "/epg/node/qos-control/dscp-map/name";
        }
      }
      leaf path-failure {
        description
          "If configured, delete the PDN connections on the failed s5-u path";
        type empty;
      }
    }
    container s8-u {
      description
        "s8-u interface";
      presence "s8-u need presence";
      must 'not (../s5s8-u)' {
        error-message "Can't configure separate S8U at the same time as S5S8U";
      }
      leaf network-instance {
        type string;
      }
      leaf dscp-map {
        description
          "dscp-map name";
        type leafref {
          path "/epg/node/qos-control/dscp-map/name";
        }
      }
      leaf path-failure {
        description
          "If configured, delete the PDN connections on the failed s8-u path";
        type empty;
      }
    }
  }

  grouping sgw-type {
    container olp {
      list emergency-apn {
        description
          "List of Emergency APNs";
        max-elements 10;
        key "name";
        leaf name {
          description
            "Emergency APN";
          type string;
        }
      }
    }
    leaf node {
      description
        "Identifier for SGW node, it must not be equal to 1";
      type string {
        pattern '[A-Za-z2-9]|[.A-Za-z0-9_-]{2,32}' {
          error-message "Node identifier is a string consisting of up to 32 letters, numbers, hyphens, periods, underscores and it must not be equal to 1";
        }
      }
      mandatory true;
    }
    container feature-activation {
      description
        "Feature activation flags";
      leaf network-triggered-restoration {
        description
          "Enable the sgsn-mme geo-redundant Pool Support feature\\. Used in network-triggered service restoration procedures";
        type empty;
      }
    }
    container pgw-pause-charging {
      description
        "Pgw pause charging feature settings";
      presence "pgw-pause-charging need presence";
      uses pgw-pause-charging-type;
    }
    container session-priority {
      description
        "Configure Enhanced Multimedia Priority Services";
      list arp-priority-level {
        max-elements 15;
        key "name";
        uses session-priority-arp-priority-type-sgw;
      }
    }
    container late-request-handling {
      description
        "late-request-handling is used to detect of the Late Overlapping Create Session Request which is an old         attempt but arrives late, and the Timed Out Create Session Request which already expires in the downstream node,         to maintain the session uniqueness and avoid stale session or error session.";
      presence "late-request-handling need presence";
      leaf no-detect-timed-out-request {
        description
          "noDetectTimedOutRequest is used to disable the detection of the Timed Out Create Session Request";
        type empty;
      }
      leaf no-detect-late-overlapping-request {
        description
          "noDetectLateOverlappingRequest is used to disable the detection of the Late Overlapping Create Session Request";
        type empty;
      }
    }
    container charging {
      description
        "SGW charging settings";
      container rf {
        description
          "The Id of an existing Rf DAS";
        presence "rf need presence";
        leaf diameter-application-system {
          description
            "Diameter application system to use for Rf Charging";
          type leafref {
            path "/epg/node/diameter/diameter-application-system/name";
          }
          mandatory true;
        }
        leaf acr-retries {
          description
            "Number of retries to perform per ACR at diameter failures";
          type uint8 {
            range "0..4" {
              error-message "Invalid value for attribute 'acr-retries'. Valid values are in range:[0,4]";
            }
          }
        }
        leaf service-context-id {
          description
            "Service Context Identifier";
          type string {
            length "1..80";
          }
        }
        leaf rf-acr-file-format {
          description
            "ACR file format defined by release";
          type enumeration {
            enum 9 {
              description
                "release 9";
            }
            enum 10 {
              description
                "release 10";
            }
            enum 11 {
              description
                "release 11";
            }
            enum 12 {
              description
                "release 12";
            }
            enum 13 {
              description
                "release 13";
            }
            enum 14 {
              description
                "release 14";
            }
            enum 15 {
              description
                "release 15";
            }
          }
        }
        container acr-attribute {
          description
            "Configure AVPs to be included or excluded from Rf ACRs";
          presence "acr-attribute need presence";
          leaf no-sgw-address {
            description
              "Configure sgw-address to be excluded from ACRs";
            type empty;
          }
          leaf no-user-csg-information {
            description
              "Configure user-csg-information to be excluded from ACRs";
            type empty;
          }
          leaf no-secondary-rat-usage-report {
            description
              "Configure secondary-rat-usage-report to be excluded from ACRs";
            type empty;
          }
          leaf no-qos-extended-bitrates {
            description
              "Configure qos-extended-bitrates AVPs to be excluded from ACRs";
            type empty;
          }
          leaf sgw-address-value {
            description
              "Configure the address to use in the sgw-address AVP";
            type enumeration {
              enum s5s8c {
                description
                  "Use S5/S8-c address";
              }
              enum s4s11c {
                description
                  "Use S4/S11-c address";
              }
            }
          }
          leaf charging-gateway-function-host {
            description
              "Configure charging-gateway-function-host to be included with ACRs";
            type empty;
          }
          leaf charging-group-id {
            description
              "Configure charging-group-id to be included with ACRs";
            type empty;
          }
          leaf cp-ciot-eps-optimisation-indicator {
            description
              "Configure Cp CIoT EPS Optimisation Indicator to be included with ACR:s";
            type empty;
          }
          leaf uni-pdu-cp-only-flag {
            description
              "Configure UNI PDU CP Only Flag  to be included with ACR:s";
            type empty;
          }
          leaf connected-info {
            description
              "Configure idle-to-connected-transition-count and connected-duration to be included with ACRs";
            type empty;
          }
          leaf no-imsi-unauthenticated-flag {
            description
              "Configure imsi-unauthenticated-flag to be excluded from ACRs";
            type empty;
          }
          leaf tdv-charging-id {
            description
              "Configure 3gppChargingId TDV to be included with ACRs";
            type empty;
          }
          leaf serving-plmn-rate-control {
            description
              "Configure serving plmn rate control to be included with ACRs";
            type empty;
          }
          leaf mo-exception-data {
            description
              "Configure mo exception data to be included with ACRs";
            type empty;
          }
        }
      }
      container user-location-change-trigger {
        description
          "ULI parameters to be treated as charging triggers";
        leaf cgi {
          type empty;
        }
        leaf ecgi {
          type empty;
        }
        leaf lai {
          type empty;
        }
        leaf rai {
          type empty;
        }
        leaf sai {
          type empty;
        }
        leaf tai {
          type empty;
        }
      }
      container triggers {
        description
          "The type of charging triggers";
        leaf user-csg-information-change {
          description
            "Enable change-condition UserCSGInformationChange";
          type empty;
        }
      }
      container equivalent-plmn-id-list {
        description
          "Equivalent plmn-id list";
        leaf-list plmn-id {
          description
            "Serving Home Public Land Mobile Network identifier";
          type string {
            pattern '[0-9]{5,6}' {
              error-message "PLMN identifier is a string of 5 or 6 digits";
            }
            length "5..6";
          }
        }
      }
      leaf closing-reason-for-sgw-change {
        description
          "Closing reason when charging is triggered by SGW change";
        type enumeration {
          enum sgw-change {
            description
              "Indicate SGW change in closing reason.";
          }
          enum normal-release {
            description
              "Indicate normal release in closing reason.";
          }
        }
        default "normal-release";
      }
      leaf charging-record-combined-session {
        description
          "Enable charging records for user sessions within the combined SGW/PGW";
        type empty;
      }
      leaf change-in-up-to-ue-trigger {
        description
          "Enable change-condition Up to Ue";
        type empty;
      }
      container cdr-attribute {
        description
          "Attributes in charging data records";
        leaf apn-encoding {
          description
            "Method of ASN.1 encoding of the APN field in sgw-cdr";
          type enumeration {
            enum dot-notation {
              description
                "Encode dot as '.'";
            }
            enum digit-notation {
              description
                "Encode dot as digit";
            }
          }
        }
        leaf sgw-address-value {
          description
            "Configure the address to use in the sgw-address Cdr Field";
          type enumeration {
            enum s5s8c {
              description
                "Use S5/S8-c address";
            }
            enum s4s11c {
              description
                "Use S4/S11-c address";
            }
          }
        }
        leaf no-imsi-unauthenticated-flag {
          description
            "Don't include IMSI Unauthenticated Flag";
          type empty;
        }
        leaf no-msisdn-number-plan-indicator {
          description
            "Don't include the number plan indicator in MSISDN.";
          type empty;
        }
        leaf no-sgw-ipv6-address {
          description
            "Don't include SGW IPv6 address";
          type empty;
        }
        leaf no-cp-ciot-eps-optimisation-indicator {
          description
            "Don't include Cp CIoT EPS Optimisation Indicator";
          type empty;
        }
        leaf no-uni-pdu-cp-only-flag {
          description
            "Don't include UNI PDU CP Only Flag";
          type empty;
        }
        leaf no-serving-node-ipv6-address {
          description
            "Don't include serving node IPv6 address";
          type empty;
        }
        leaf no-pdn-type-extension {
          description
            "Don't include cdr attribute pdpPDNType extension";
          type empty;
        }
        leaf no-pgw-ipv6-address-used {
          description
            "Don't include PGW IPv6 address used";
          type empty;
        }
        leaf no-low-priority-indicator {
          description
            "Don't include low priority indicator";
          type empty;
        }
        leaf record-seq-number-single-cdr {
          description
            "Enable inclusion of record sequence numbers in CDRs when only one record is produced";
          type empty;
        }
        leaf no-serving-plmn-rate-control {
          description
            "Disable inclusion of Serving PLMN rate control information";
          type empty;
        }
        leaf no-mo-exception-data {
          description
            "Disable inclusion of MO Exception Data";
          type empty;
        }
        leaf no-secondary-rat-usage-report {
          description
            "Disable inclusion of secondary RAT usage report";
          type empty;
        }
        leaf no-qos-extended-bitrates {
          description
            "Disable inclusion of qos extended bitrates";
          type empty;
        }
        leaf no-qos-apn-ambr {
          description
            "Disable inclusion of qos APN AMBR";
          type empty;
        }
        leaf no-user-csg-information {
          description
            "Disable inclusion of User CSG Information";
          type empty;
        }
      }
      leaf qos-bitrates-with-bps {
        description
          "Transfer qos kpbs to bps";
        type empty;
      }
      leaf charging-format {
        description
          "Format of charging records";
        type enumeration {
          enum 9 {
            description
              "Version 9";
          }
          enum 13 {
            description
              "Version 13";
          }
          enum 15 {
            description
              "Version 15";
          }
        }
      }
      container charging-data-file {
        description
          "Charging records logged to node";
        uses sgw-charging-log-type;
      }
      container characteristics {
        description
          "account-type charging characteristics";
        leaf default-profile {
          description
            "Default profile to use";
          type enumeration {
            enum 0 {
              description
                "Profile 0";
            }
            enum 1 {
              description
                "Profile 1";
            }
            enum 2 {
              description
                "Profile 2";
            }
            enum 3 {
              description
                "Profile 3";
            }
            enum 4 {
              description
                "Profile 4";
            }
            enum 5 {
              description
                "Profile 5";
            }
            enum 6 {
              description
                "Profile 6";
            }
            enum 7 {
              description
                "Profile 7";
            }
            enum 8 {
              description
                "Profile 8";
            }
            enum 9 {
              description
                "Profile 9";
            }
            enum 10 {
              description
                "Profile 10";
            }
            enum 11 {
              description
                "Profile 11";
            }
            enum 12 {
              description
                "Profile 12";
            }
            enum 13 {
              description
                "Profile 13";
            }
            enum 14 {
              description
                "Profile 14";
            }
            enum 15 {
              description
                "Profile 15";
            }
          }
        }
        leaf roaming-based-profile {
          description
            "Profile used for roaming users";
          type enumeration {
            enum 0 {
              description
                "Profile 0";
            }
            enum 1 {
              description
                "Profile 1";
            }
            enum 2 {
              description
                "Profile 2";
            }
            enum 3 {
              description
                "Profile 3";
            }
            enum 4 {
              description
                "Profile 4";
            }
            enum 5 {
              description
                "Profile 5";
            }
            enum 6 {
              description
                "Profile 6";
            }
            enum 7 {
              description
                "Profile 7";
            }
            enum 8 {
              description
                "Profile 8";
            }
            enum 9 {
              description
                "Profile 9";
            }
            enum 10 {
              description
                "Profile 10";
            }
            enum 11 {
              description
                "Profile 11";
            }
            enum 12 {
              description
                "Profile 12";
            }
            enum 13 {
              description
                "Profile 13";
            }
            enum 14 {
              description
                "Profile 14";
            }
            enum 15 {
              description
                "Profile 15";
            }
          }
        }
        leaf ignore-profile-from-serving-node {
          description
            "Ignore profile from serving node";
          type empty;
        }
        leaf acr-interim-interval {
          description
            "Interval in minutes for generating ACR interim";
          type uint16 {
            range "1..1440" {
              error-message "Invalid value for attribute 'acr-interim-interval'. Valid values are in range:[1,1440]";
            }
          }
        }
        leaf internal-acr-interim-interval {
          description
            "Internal interval in minutes for generating ACR interim";
          type uint8 {
            range "1..10" {
              error-message "Invalid value for attribute 'internal-acr-interim-interval'. Valid values are in range:[1,10]";
            }
          }
        }
        list profile {
          max-elements 16;
          key "name";
          uses sgw-charging-profiles;
        }
      }
    }
    container interface {
      description
        "GTP interfaces settings";
      container s4s11-c {
        description
          "S4/S11-c interface settings";
        presence "s4s11-c need presence";
        leaf pgw-restart-notification {
          description
            "SGW supports PRN feature";
          type empty;
        }
        container load-control-information {
          presence "load-control-information need presence";
          description
            "Enables the SGW gtp-c Load Control Information to MME feature";
          uses load-control-information-type;
        }
        list network-restoration-pool {
          description
            "Pool of MMEs or SGSNs\\. Used in network-triggered service restoration procedures\\. Configuration should be aligned with configuration of geographically redundant pools in the MMEs or SGSNs";
          max-elements 256;
          must '/epg/sgw/interface/s4s11-c/network-restoration-pool[name=current()/name]/network-element' {
            error-message "network-element is mandatory";
          }
          key "name";
          leaf name {
            description
              "Name of the pool";
            type string;
          }
          container user-location-information {
            description
              "Add Private Extension for User Location Information to DDN Message";
            presence "user-location-information need presence";
            leaf vendor-id {
              description
                "Select vendor-id for Private Extension";
              type enumeration {
                enum 5806 {
                  description
                    "Use 5806 as Enterprise Id of Private Extension";
                }
                enum 11665 {
                  description
                    "Use 11665 as Enterprise Id of Private Extension";
                }
              }
              mandatory true;
            }
          }
          list network-element {
            description
              "Properties for an network element within the pool";
            max-elements 256;
            key "name";
            leaf name {
              description
                "Name of the network element";
              type string;
            }
            leaf priority {
              description
                "Specifies in what order multiple configured peers are accessed in a round robin schedule\\. A value from 0 to 255, where the lowest is accessed first.";
              type uint8 {
                range "0..255" {
                  error-message "Invalid value for attribute 'priority'. Valid values are in range:[0,255]";
                }
              }
            }
            leaf address {
              description
                "Unique ip-address of the network element, expressed either as IPv4 or IPv6";
              type inet:ip-address;
              mandatory true;
            }
          }
        }
        leaf transaction-timeout {
          description
            "Specifies for how long time after receiving a request that retransmissions of the request will be detectable";
          type uint8 {
            range "10..60" {
              error-message "Invalid value for attribute 'transaction-timeout'. Valid values are in range:[10,60]";
            }
          }
        }
        leaf logical-interface {
          description
            "Logical interface";
          type leafref {
            path "/epg/node/logical-interface/name";
          }
          mandatory true;
          must '(/epg/node/logical-interface[name=current()])' {
            error-message "Logical interface must be configured under [epg node logical-interface]";
          }
        }
        leaf nw-restoration-timer {
          description
            "Specifies how long, in minutes, an inactive PDN connection is maintained after an MME or SGSN restart is detected or an MME or SGSN is detected as unavailable";
          type uint16 {
            range "1..18601" {
              error-message "Invalid value for attribute 'nw-restoration-timer'. Valid values are in range:[1,18601]";
            }
          }
        }
        leaf nw-restoration-cleanout-timer {
          description
            "Specifies how long, in hours, an inactive PDN connection is maintained after a previously unavailable MME or SGSN becomes available";
          type uint8 {
            range "1..100" {
              error-message "Invalid value for attribute 'nw-restoration-cleanout-timer'. Valid values are in range:[1,100]";
            }
          }
        }
        leaf no-path-management {
          description
            "If enabled, turns off path management completely, no echo requests are sent";
          type empty;
          must 'not (/epg/sgw/feature-activation/network-triggered-restoration)' {
            error-message "Path management must be enabled when [epg sgw feature-activation network-triggered-restoration] is enabled";
            tailf:dependency "/epg/sgw/feature-activation/network-triggered-restoration";
          }
        }
        leaf no-peer-restart {
          description
            "If enabled, when a changed restart counter is received, no path failures are propagated";
          type empty;
        }
        leaf no-path-failure {
          description
            "If enabled, when an echo request is not responded to, no path failures are propagated";
          type empty;
        }
        leaf-list gtp-path-failure-alarm-peer {
          description
            "GtpPathFailureAlarmPeer defines the SGSN/MME IP address list which are monitored to send GTP Path Error alarm instead of GTP Path Failure alert";
          type inet:ip-address;
          max-elements 80;
        }
        leaf indirect-data-forwarding {
          description
            "Enable indirect data forwarding in S1-based handover";
          type empty;
        }
        leaf diffserv {
          description
            "DiffServ DSCP for GTP packets";
          type enumeration {
            enum af11 {
              description
                "Assured forwarding class 1, low drop precedence";
            }
            enum af12 {
              description
                "Assured forwarding class 1, medium drop precedence";
            }
            enum af13 {
              description
                "Assured forwarding class 1, high drop precedence";
            }
            enum af21 {
              description
                "Assured forwarding class 2, low drop precedence";
            }
            enum af22 {
              description
                "Assured forwarding class 2, medium drop precedence";
            }
            enum af23 {
              description
                "Assured forwarding class 2, high drop precedence";
            }
            enum af31 {
              description
                "Assured forwarding class 3, low drop precedence";
            }
            enum af32 {
              description
                "Assured forwarding class 3, medium drop precedence";
            }
            enum af33 {
              description
                "Assured forwarding class 3, high drop precedence";
            }
            enum af41 {
              description
                "Assured forwarding class 4, low drop precedence";
            }
            enum af42 {
              description
                "Assured forwarding class 4, medium drop precedence";
            }
            enum af43 {
              description
                "Assured forwarding class 4, high drop precedence";
            }
            enum ef {
              description
                "Expedited forwarding";
            }
            enum be {
              description
                "Best effort forwarding";
            }
            enum cs1 {
              description
                "Class selector 1";
            }
            enum cs2 {
              description
                "Class selector 2";
            }
            enum cs3 {
              description
                "Class selector 3";
            }
            enum cs4 {
              description
                "Class selector 4";
            }
            enum cs5 {
              description
                "Class selector 5";
            }
            enum cs6 {
              description
                "Class selector 6";
            }
            enum cs7 {
              description
                "Class selector 7";
            }
          }
        }
        leaf echo-interval {
          description
            "Specifies the interval between Echo Request messages (seconds) Should never be less than 60 seconds according to 3GPP specification";
          type uint8 {
            range "5..200" {
              error-message "Invalid value for attribute 'echo-interval'. Valid values are in range:[5,200]";
            }
          }
          default "60";
        }
        leaf t3-response-time {
          description
            "Specifies the time in seconds between control message retries";
          type string {
            pattern '((0.[3-9])|([1-9])|([1-9].[0-9])|([1-2][0-9])|([1-2][0-9].[0-9])|(30)|(30.0))' {
              error-message "Value must be a number from 0.3 to 30.0";
            }
          }
        }
        leaf n3-requests {
          description
            "Specifies the number of total attempts allowed for a control message";
          type uint8 {
            range "1..8" {
              error-message "Invalid value for attribute 'n3-requests'. Valid values are in range:[1,8]";
            }
          }
        }
        container echo-request {
          description
            "Echo Request specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container create-bearer-request {
          description
            "Create Bearer Request specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container update-bearer-request {
          description
            "Update Bearer Request specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container delete-bearer-request {
          description
            "Delete Bearer Request specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container downlink-data-notification {
          description
            "Downlink Data Notification specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        action gtp-path-status {
          description
            "Show status of GTP paths";
          input {
            leaf scope {
              type enumeration {
                enum inactive {
                  description
                    "Show inactive paths";
                }
                enum supervised {
                  description
                    "Show supervised paths";
                }
                enum all {
                  description
                    "Show all paths";
                }
              }
              mandatory true;
            }
          }
          output {
            leaf result {
              type string;
              mandatory true;
            }
          }
        }
        action mme-restore-start {
          yexte:user-group "ericsson-support,epg-admin";
          description
            "Start SGW initiated MME Restoration";
          input {
            leaf mme-pool {
              description
                "Type MME Pool Name";
              type string;
              mandatory true;
            }
            leaf mme {
              description
                "Type MME Name";
              type string;
              mandatory true;
            }
          }
          output {
            leaf result {
              type string;
              mandatory true;
            }
          }
        }
        action mme-restore-stop {
          yexte:user-group "ericsson-support,epg-admin";
          description
            "Stop SGW initiated MME Restoration";
          input {
            leaf mme-pool {
              description
                "Type MME Pool Name";
              type string;
              mandatory true;
            }
            leaf mme {
              description
                "Type MME Name";
              type string;
              mandatory true;
            }
          }
          output {
            leaf result {
              type string;
              mandatory true;
            }
          }
        }
        action mme-restore-show {
          description
            "Show SGW initiated MME Restoration";
          input {
            leaf mme-pool {
              description
                "Type MME Pool Name";
              type string;
            }
            leaf mme {
              description
                "Type MME Name";
              type string;
            }
          }
          output {
            leaf result {
              type string;
              mandatory true;
            }
          }
        }
        leaf identify-sender-by-source-address {
          description
            "Enable identification of sender by source address";
          type empty;
        }
        leaf message-priority {
          description
            "Enable message priority for this interface";
          type empty;
        }
      }
      container s5s8-c {
        description
          "S5/S8-c interface settings";
        presence "s5s8-c need presence";
        must '(not (/epg/pgw)) or (/epg/pgw/interface/s5s8-c)' {
          error-message "In combined mode, configured with [epg sgw interface s5s8-c], [epg pgw interface s5s8-c] is required.";
          tailf:dependency "/epg/pgw";
          tailf:dependency "/epg/pgw/interface/s5s8-c";
        }
        leaf no-orig-time-stamp-max-wait-time {
          description
            "noOrigTimeStampMaxWaitTime is used to disable the sending on S5/S8 interface of the standard IE Origination Time Stamp and Maximum Wait Time.";
          type empty;
        }
        leaf no-orig-time-stamp-max-wait-time-on-s8 {
          description
            "noOrigTimeStampMaxWaitTimeOnS8 is used to disable the sending for roaming users on S8 interface of the standard IE Origination Time Stamp and Maximum Wait Time.";
          type empty;
        }
        leaf addl-orig-time-stamp-max-wait-time {
          description
            "addOrigTimeStampMaxWaitTime is used to enable the sending on S5 interface of the Private Extension IE Origination Time Stamp and Maximum Wait Time.";
          type empty;
        }
        leaf transaction-timeout {
          description
            "Specifies for how long time after receiving a request that retransmissions of the request will be detectable";
          type uint8 {
            range "10..60" {
              error-message "Invalid value for attribute 'transaction-timeout'. Valid values are in range:[10,60]";
            }
          }
        }
        leaf logical-interface {
          description
            "Logical interface";
          type leafref {
            path "/epg/node/logical-interface/name";
          }
          mandatory true;
          must '(/epg/node/logical-interface[name=current()])' {
            error-message "Logical interface must be configured under [epg node logical-interface]";
          }
        }
        leaf diffserv {
          description
            "DiffServ DSCP for GTP packets";
          type enumeration {
            enum af11 {
              description
                "Assured forwarding class 1, low drop precedence";
            }
            enum af12 {
              description
                "Assured forwarding class 1, medium drop precedence";
            }
            enum af13 {
              description
                "Assured forwarding class 1, high drop precedence";
            }
            enum af21 {
              description
                "Assured forwarding class 2, low drop precedence";
            }
            enum af22 {
              description
                "Assured forwarding class 2, medium drop precedence";
            }
            enum af23 {
              description
                "Assured forwarding class 2, high drop precedence";
            }
            enum af31 {
              description
                "Assured forwarding class 3, low drop precedence";
            }
            enum af32 {
              description
                "Assured forwarding class 3, medium drop precedence";
            }
            enum af33 {
              description
                "Assured forwarding class 3, high drop precedence";
            }
            enum af41 {
              description
                "Assured forwarding class 4, low drop precedence";
            }
            enum af42 {
              description
                "Assured forwarding class 4, medium drop precedence";
            }
            enum af43 {
              description
                "Assured forwarding class 4, high drop precedence";
            }
            enum ef {
              description
                "Expedited forwarding";
            }
            enum be {
              description
                "Best effort forwarding";
            }
            enum cs1 {
              description
                "Class selector 1";
            }
            enum cs2 {
              description
                "Class selector 2";
            }
            enum cs3 {
              description
                "Class selector 3";
            }
            enum cs4 {
              description
                "Class selector 4";
            }
            enum cs5 {
              description
                "Class selector 5";
            }
            enum cs6 {
              description
                "Class selector 6";
            }
            enum cs7 {
              description
                "Class selector 7";
            }
          }
        }
        leaf echo-interval {
          description
            "Specifies the interval between Echo Request messages (seconds) Should never be less than 60 seconds according to 3GPP specification";
          type uint8 {
            range "5..200" {
              error-message "Invalid value for attribute 'echo-interval'. Valid values are in range:[5,200]";
            }
          }
          default "60";
        }
        leaf no-peer-restart {
          description
            "If enabled, when a changed restart counter is received, no path failures are propagated";
          type empty;
        }
        leaf no-path-failure {
          description
            "If enabled, when an echo request is not responded to, no path failures are propagated";
          type empty;
        }
        leaf no-path-management {
          description
            "If enabled, turns off path management completely, no echo requests are sent";
          type empty;
        }
        leaf t3-response-time {
          description
            "Specifies the time in seconds between control message retries";
          type string {
            pattern '((0.[3-9])|([1-9])|([1-9].[0-9])|([1-2][0-9])|([1-2][0-9].[0-9])|(30)|(30.0))' {
              error-message "Value must be a number from 0.3 to 30.0";
            }
          }
        }
        leaf n3-requests {
          description
            "Specifies the number of total attempts allowed for a control message";
          type uint8 {
            range "1..8" {
              error-message "Invalid value for attribute 'n3-requests'. Valid values are in range:[1,8]";
            }
          }
        }
        leaf pgw-pause-charging {
          description
            "Enable PGW pause charging feature for this interface";
          type empty;
          must '/epg/sgw/pgw-pause-charging' {
            error-message "Pgw pause charging feature must be configured under [epg sgw pgw-pause-charging]";
            tailf:dependency "/epg/sgw/pgw-pause-charging";
          }
        }
        leaf p-cscf-restoration {
          description
            "Enable p-cscf restoration procedure for external PGW";
          type empty;
        }
        container echo-request {
          description
            "Echo Request specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container change-notification-request {
          description
            "Change Notification Request specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container create-session-request {
          description
            "Create Session Request specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container delete-session-request {
          description
            "Delete Session Request specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container modify-bearer-request {
          description
            "Modify Bearer Request specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container modify-bearer-command {
          description
            "Modify Bearer Command specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container delete-bearer-command {
          description
            "Delete Bearer Command specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container bearer-resource-command {
          description
            "Bearer Resource Command specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container resume-notification {
          description
            "Resume Notification specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container suspend-notification {
          description
            "Suspend Notification specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        action gtp-path-status {
          description
            "Show status of GTP paths";
          input {
            leaf scope {
              type enumeration {
                enum inactive {
                  description
                    "Show inactive paths";
                }
                enum supervised {
                  description
                    "Show supervised paths";
                }
                enum all {
                  description
                    "Show all paths";
                }
              }
              mandatory true;
            }
          }
          output {
            leaf result {
              type string;
              mandatory true;
            }
          }
        }
        leaf identify-sender-by-source-address {
          description
            "Enable identification of sender by source address";
          type empty;
        }
        leaf reject-cause-when-sender-invalid {
          description
            "Configure the reject cause when Delete Bearer Request/Create Bearer Request/Update Bearer Request is rejected because the sender of these messages is not as expected.";
          type enumeration {
            enum 64 {
              description
                "ContextNotFound";
            }
            enum 109 {
              description
                "InvalidPeer";
            }
          }
        }
        leaf message-priority {
          description
            "Enable message priority for this interface";
          type empty;
        }
      }
      container s5-c {
        description
          "S5-c interface settings";
        presence "s5-c need presence";
        leaf no-orig-time-stamp-max-wait-time {
          description
            "noOrigTimeStampMaxWaitTime is used to disable the sending on S5/S8 interface of the standard IE Origination Time Stamp and Maximum Wati Time.";
          type empty;
        }
        leaf addl-orig-time-stamp-max-wait-time {
          description
            "addlOrigTimeStampMaxWaitTime is used to enable the sending on S5 interface of the Private Extension IE Origination Time Stamp and Maximum Wati Time.";
          type empty;
        }
        leaf transaction-timeout {
          description
            "Specifies for how long time after receiving a request that retransmissions of the request will be detectable";
          type uint8 {
            range "10..60" {
              error-message "Invalid value for attribute 'transaction-timeout'. Valid values are in range:[10,60]";
            }
          }
        }
        leaf logical-interface {
          description
            "Logical interface";
          type leafref {
            path "/epg/node/logical-interface/name";
          }
          mandatory true;
          must '(/epg/node/logical-interface[name=current()]) and (/epg/sgw/interface/s5-c)' {
            error-message "Logical interface must be configured under [epg node logical-interface] and s5-c under [epg sgw interface]";
          }
        }
        leaf diffserv {
          description
            "DiffServ DSCP for GTP packets";
          type enumeration {
            enum af11 {
              description
                "Assured forwarding class 1, low drop precedence";
            }
            enum af12 {
              description
                "Assured forwarding class 1, medium drop precedence";
            }
            enum af13 {
              description
                "Assured forwarding class 1, high drop precedence";
            }
            enum af21 {
              description
                "Assured forwarding class 2, low drop precedence";
            }
            enum af22 {
              description
                "Assured forwarding class 2, medium drop precedence";
            }
            enum af23 {
              description
                "Assured forwarding class 2, high drop precedence";
            }
            enum af31 {
              description
                "Assured forwarding class 3, low drop precedence";
            }
            enum af32 {
              description
                "Assured forwarding class 3, medium drop precedence";
            }
            enum af33 {
              description
                "Assured forwarding class 3, high drop precedence";
            }
            enum af41 {
              description
                "Assured forwarding class 4, low drop precedence";
            }
            enum af42 {
              description
                "Assured forwarding class 4, medium drop precedence";
            }
            enum af43 {
              description
                "Assured forwarding class 4, high drop precedence";
            }
            enum ef {
              description
                "Expedited forwarding";
            }
            enum be {
              description
                "Best effort forwarding";
            }
            enum cs1 {
              description
                "Class selector 1";
            }
            enum cs2 {
              description
                "Class selector 2";
            }
            enum cs3 {
              description
                "Class selector 3";
            }
            enum cs4 {
              description
                "Class selector 4";
            }
            enum cs5 {
              description
                "Class selector 5";
            }
            enum cs6 {
              description
                "Class selector 6";
            }
            enum cs7 {
              description
                "Class selector 7";
            }
          }
        }
        leaf echo-interval {
          description
            "Specifies the interval between Echo Request messages (seconds) Should never be less than 60 seconds according to 3GPP specification";
          type uint8 {
            range "5..200" {
              error-message "Invalid value for attribute 'echo-interval'. Valid values are in range:[5,200]";
            }
          }
          default "60";
        }
        leaf no-peer-restart {
          description
            "If enabled, when a changed restart counter is received, no path failures are propagated";
          type empty;
        }
        leaf no-path-failure {
          description
            "If enabled, when an echo request is not responded to, no path failures are propagated";
          type empty;
        }
        leaf no-path-management {
          description
            "If enabled, turns off path management completely, no echo requests are sent";
          type empty;
        }
        leaf t3-response-time {
          description
            "Specifies the time in seconds between control message retries";
          type string {
            pattern '((0.[3-9])|([1-9])|([1-9].[0-9])|([1-2][0-9])|([1-2][0-9].[0-9])|(30)|(30.0))' {
              error-message "Value must be a number from 0.3 to 30.0";
            }
          }
        }
        leaf n3-requests {
          description
            "Specifies the number of total attempts allowed for a control message";
          type uint8 {
            range "1..8" {
              error-message "Invalid value for attribute 'n3-requests'. Valid values are in range:[1,8]";
            }
          }
        }
        leaf pgw-pause-charging {
          description
            "Enable PGW pause charging feature for this interface";
          type empty;
          must '/epg/sgw/pgw-pause-charging' {
            error-message "Pgw pause charging feature must be configured under [epg sgw pgw-pause-charging]";
            tailf:dependency "/epg/sgw/pgw-pause-charging";
          }
        }
        leaf p-cscf-restoration {
          description
            "Enable p-cscf restoration procedure for external PGW";
          type empty;
        }
        container echo-request {
          description
            "Echo Request specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container change-notification-request {
          description
            "Change Notification Request specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container create-session-request {
          description
            "Create Session Request specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container delete-session-request {
          description
            "Delete Session Request specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container modify-bearer-request {
          description
            "Modify Bearer Request specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container modify-bearer-command {
          description
            "Modify Bearer Command specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container delete-bearer-command {
          description
            "Delete Bearer Command specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container bearer-resource-command {
          description
            "Bearer Resource Command specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container resume-notification {
          description
            "Resume Notification specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container suspend-notification {
          description
            "Suspend Notification specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        action gtp-path-status {
          description
            "Show status of GTP paths";
          input {
            leaf scope {
              type enumeration {
                enum inactive {
                  description
                    "Show inactive paths";
                }
                enum supervised {
                  description
                    "Show supervised paths";
                }
                enum all {
                  description
                    "Show all paths";
                }
              }
              mandatory true;
            }
          }
          output {
            leaf result {
              type string;
              mandatory true;
            }
          }
        }
        leaf identify-sender-by-source-address {
          description
            "Enable identification of sender by source address";
          type empty;
        }
        leaf reject-cause-when-sender-invalid {
          description
            "Configure the reject cause when Delete Bearer Request/Create Bearer Request/Update Bearer Request is rejected because the sender of these messages is not as expected.";
          type enumeration {
            enum 64 {
              description
                "ContextNotFound";
            }
            enum 109 {
              description
                "InvalidPeer";
            }
          }
        }
        leaf message-priority {
          description
            "Enable message priority for this interface";
          type empty;
        }
      }
      container s8-c {
        description
          "S8-c interface settings";
        presence "s8-c need presence";
        leaf no-orig-time-stamp-max-wait-time {
          description
            "noOrigTimeStampMaxWaitTime is used to disable the sending on S5/S8 interface of the standard IE Origination Time Stamp and Maximum Wati Time.";
          type empty;
        }
        leaf transaction-timeout {
          description
            "Specifies for how long time after receiving a request that retransmissions of the request will be detectable";
          type uint8 {
            range "10..60" {
              error-message "Invalid value for attribute 'transaction-timeout'. Valid values are in range:[10,60]";
            }
          }
        }
        leaf logical-interface {
          description
            "Logical interface";
          type leafref {
            path "/epg/node/logical-interface/name";
          }
          mandatory true;
          must '(/epg/node/logical-interface[name=current()]) and (/epg/sgw/interface/s8-c)' {
            error-message "Logical interface must be configured under [epg node logical-interface] and s8-c under [epg sgw interface]";
          }
        }
        leaf diffserv {
          description
            "DiffServ DSCP for GTP packets";
          type enumeration {
            enum af11 {
              description
                "Assured forwarding class 1, low drop precedence";
            }
            enum af12 {
              description
                "Assured forwarding class 1, medium drop precedence";
            }
            enum af13 {
              description
                "Assured forwarding class 1, high drop precedence";
            }
            enum af21 {
              description
                "Assured forwarding class 2, low drop precedence";
            }
            enum af22 {
              description
                "Assured forwarding class 2, medium drop precedence";
            }
            enum af23 {
              description
                "Assured forwarding class 2, high drop precedence";
            }
            enum af31 {
              description
                "Assured forwarding class 3, low drop precedence";
            }
            enum af32 {
              description
                "Assured forwarding class 3, medium drop precedence";
            }
            enum af33 {
              description
                "Assured forwarding class 3, high drop precedence";
            }
            enum af41 {
              description
                "Assured forwarding class 4, low drop precedence";
            }
            enum af42 {
              description
                "Assured forwarding class 4, medium drop precedence";
            }
            enum af43 {
              description
                "Assured forwarding class 4, high drop precedence";
            }
            enum ef {
              description
                "Expedited forwarding";
            }
            enum be {
              description
                "Best effort forwarding";
            }
            enum cs1 {
              description
                "Class selector 1";
            }
            enum cs2 {
              description
                "Class selector 2";
            }
            enum cs3 {
              description
                "Class selector 3";
            }
            enum cs4 {
              description
                "Class selector 4";
            }
            enum cs5 {
              description
                "Class selector 5";
            }
            enum cs6 {
              description
                "Class selector 6";
            }
            enum cs7 {
              description
                "Class selector 7";
            }
          }
        }
        leaf echo-interval {
          description
            "Specifies the interval between Echo Request messages (seconds) Should never be less than 60 seconds according to 3GPP specification";
          type uint8 {
            range "5..200" {
              error-message "Invalid value for attribute 'echo-interval'. Valid values are in range:[5,200]";
            }
          }
          default "60";
        }
        leaf no-peer-restart {
          description
            "If enabled, when a changed restart counter is received, no path failures are propagated";
          type empty;
        }
        leaf no-path-failure {
          description
            "If enabled, when an echo request is not responded to, no path failures are propagated";
          type empty;
        }
        leaf no-path-management {
          description
            "If enabled, turns off path management completely, no echo requests are sent";
          type empty;
        }
        leaf t3-response-time {
          description
            "Specifies the time in seconds between control message retries";
          type string {
            pattern '((0.[3-9])|([1-9])|([1-9].[0-9])|([1-2][0-9])|([1-2][0-9].[0-9])|(30)|(30.0))' {
              error-message "Value must be a number from 0.3 to 30.0";
            }
          }
        }
        leaf n3-requests {
          description
            "Specifies the number of total attempts allowed for a control message";
          type uint8 {
            range "1..8" {
              error-message "Invalid value for attribute 'n3-requests'. Valid values are in range:[1,8]";
            }
          }
        }
        leaf pgw-pause-charging {
          description
            "Enable PGW pause charging feature for this interface";
          type empty;
          must '/epg/sgw/pgw-pause-charging' {
            error-message "Pgw pause charging feature must be configured under [epg sgw pgw-pause-charging]";
            tailf:dependency "/epg/sgw/pgw-pause-charging";
          }
        }
        container echo-request {
          description
            "Echo Request specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container change-notification-request {
          description
            "Change Notification Request specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container create-session-request {
          description
            "Create Session Request specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container delete-session-request {
          description
            "Delete Session Request specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container modify-bearer-request {
          description
            "Modify Bearer Request specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container modify-bearer-command {
          description
            "Modify Bearer Command specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container delete-bearer-command {
          description
            "Delete Bearer Command specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container bearer-resource-command {
          description
            "Bearer Resource Command specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container resume-notification {
          description
            "Resume Notification specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        container suspend-notification {
          description
            "Suspend Notification specific settings";
          leaf t3-response-time {
            description
              "Specifies the time in seconds between control message retries";
            type string {
              pattern '((0.[3-9])|([1-9])|([1-9].[0-9])|([1-2][0-9])|([1-2][0-9].[0-9])|(30)|(30.0))' {
                error-message "Value must be a number from 0.3 to 30.0";
              }
            }
          }
          leaf n3-requests {
            description
              "Specifies the number of total attempts allowed for a control message";
            type uint8 {
              range "1..8" {
                error-message "Invalid value for attribute 'n3-requests'. Valid values are in range:[1,8]";
              }
            }
          }
        }
        action gtp-path-status {
          description
            "Show status of GTP paths";
          input {
            leaf scope {
              type enumeration {
                enum inactive {
                  description
                    "Show inactive paths";
                }
                enum supervised {
                  description
                    "Show supervised paths";
                }
                enum all {
                  description
                    "Show all paths";
                }
              }
              mandatory true;
            }
          }
          output {
            leaf result {
              type string;
              mandatory true;
            }
          }
        }
        leaf message-priority {
          description
            "Enable message priority for this interface";
          type empty;
        }
      }
      container sx {
        description
          "Sx interface settings";
        presence "sx need presence";
        leaf logical-interface {
          description
            "Logical interface";
          type leafref {
            path "/epg/node/logical-interface/name";
          }
          mandatory true;
        }
        leaf no-pfcp-path-management {
          description
            "If enabled, disable PFCP path management.";
          type empty;
        }
        leaf no-pfcp-path-failure {
          description
            "If enabled, do not delete the UPF related PDN connection when PFCP path failure to the UPF is detected";
          type empty;
        }
        leaf no-peer-restart {
          description
            "If enabled, do not delete the PDN connection related with the restarted UPF when UPF Restart is detected";
          type empty;
        }
        action path-status {
          description
            "Show status of pfcp path";
          input {
            choice node-id {
              leaf all {
                description
                  "Show status of all pfcp path";
                type empty;
              }
              leaf upf-node-fqdn-id {
                description
                  "Show status of one Fully Qualified Domain Name (FQDN) upf path";
                type string {
                  pattern '[.0-9A-Za-z_-]*' {
                    error-message "Must contain only letters, numbers, underscores or dashes";
                  }
                  length "1..255";
                }
                mandatory true;
              }
              leaf upf-node-ip-id {
                description
                  "Show status of one ip-address upf path";
                type inet:ip-address;
              }
            }
          }
          output {
            leaf result {
              type string;
              mandatory true;
            }
          }
        }
        leaf association-interval {
          description
            "Interval in 100ms unit for re-sending association setup request";
          type uint16 {
            range "1..6000" {
              error-message "Invalid value for attribute 'association-interval'. Valid values are in range:[1,6000]";
            }
          }
          default "600";
        }
        leaf n1 {
          description
            "Total number of transmissions allowed for a pfcp message";
          type uint8 {
            range "1..10" {
              error-message "Invalid value for attribute 'n1'. Valid values are in range:[1,10]";
            }
          }
          default "3";
        }
        leaf t1 {
          description
            "Interval between pfcp message retries in 100ms unit";
          type uint16 {
            range "1..500" {
              error-message "Invalid value for attribute 't1'. Valid values are in range:[1,500]";
            }
          }
          default "50";
        }
        leaf heartbeat-interval {
          description
            "Interval between Sx Heartbeat Request messages in 100ms unit";
          type uint16 {
            range "1..6000" {
              error-message "Invalid value for attribute 'heartbeat-interval'. Valid values are in range:[1,6000]";
            }
          }
          default "600";
        }
        leaf co-located-user-plane {
          description
            "Enable co-located user plane";
          type empty;
        }
        leaf mtu-size {
          description
            "Maximum transmission unit. Default values IPv4: 1500, IPv6: 1280.";
          type uint16 {
            range "1280..3000" {
              error-message "Invalid value for attribute 'mtu-size'. Valid values are in range:[1280,3000]";
            }
          }
        }
        leaf diffserv {
          description
            "DSCP (DiffServ Code Point) for Sx packets";
          type enumeration {
            enum af11 {
              description
                "Assured forwarding class 1, low drop precedence";
            }
            enum af12 {
              description
                "Assured forwarding class 1, medium drop precedence";
            }
            enum af13 {
              description
                "Assured forwarding class 1, high drop precedence";
            }
            enum af21 {
              description
                "Assured forwarding class 2, low drop precedence";
            }
            enum af22 {
              description
                "Assured forwarding class 2, medium drop precedence";
            }
            enum af23 {
              description
                "Assured forwarding class 2, high drop precedence";
            }
            enum af31 {
              description
                "Assured forwarding class 3, low drop precedence";
            }
            enum af32 {
              description
                "Assured forwarding class 3, medium drop precedence";
            }
            enum af33 {
              description
                "Assured forwarding class 3, high drop precedence";
            }
            enum af41 {
              description
                "Assured forwarding class 4, low drop precedence";
            }
            enum af42 {
              description
                "Assured forwarding class 4, medium drop precedence";
            }
            enum af43 {
              description
                "Assured forwarding class 4, high drop precedence";
            }
            enum ef {
              description
                "Expedited forwarding";
            }
            enum be {
              description
                "Best effort forwarding";
            }
            enum cs1 {
              description
                "Class selector 1";
            }
            enum cs2 {
              description
                "Class selector 2";
            }
            enum cs3 {
              description
                "Class selector 3";
            }
            enum cs4 {
              description
                "Class selector 4";
            }
            enum cs5 {
              description
                "Class selector 5";
            }
            enum cs6 {
              description
                "Class selector 6";
            }
            enum cs7 {
              description
                "Class selector 7";
            }
          }
          default "af31";
        }
        leaf heartbeat-times {
          description
            "Number of times to retry unsuccessful transfer of Heartbeat Request to detect Sx path failure";
          type uint8 {
            range "1..10" {
              error-message "Invalid value for attribute 'heartbeat-times'. Valid values are in range:[1,10]";
            }
          }
          default "3";
        }
      }
      action gtp-path-status {
        description
          "Show status of GTP paths";
        input {
          leaf scope {
            type enumeration {
              enum inactive {
                description
                  "Show inactive paths";
              }
              enum supervised {
                description
                  "Show supervised paths";
              }
              enum all {
                description
                  "Show all paths";
              }
            }
            mandatory true;
          }
        }
        output {
          leaf result {
            type string;
            mandatory true;
          }
        }
      }
    }
    container location {
      description
        "Location area";
      list area-id {
        key "name";
        uses locationarea-type;
      }
    }
    container control-plane {
      description
        "Control plane settings";
      uses sgw-control-plane-type;
    }
    container user-plane {
      description
        "User plane settings";
      list node-name {
        key "name";
        uses sxa-user-plane-node-type;
      }
    }
    container user-plane-pool {
      presence "user plane pool";
      description
        "User Plane Pool configuration";
      list pool {
        description
          "User Plane Node Pool list";
        key "name";
        leaf name {
          description
            "User plane pool name";
          type string;
        }
        list node-name {
          key "name";
          min-elements 1;
          max-elements 2000;
          leaf name {
            type string;
            must '/epg/sgw/user-plane/node-name[name=current()]' {
              error-message "node-name must be configured under [epg sgw user-plane node-name]";
            }
          }
          leaf weight {
            description
              "Enable configure weight-factors for External User Plane";
            type uint8 {
              range "0..10" {
                error-message "Invalid value for attribute 'weight'. Valid values are in range:[0,10]";
              }
            }
            default "1";
          }
          leaf priority {
            description
              "Enable configure priority-factors for External User Plane";
            type uint8 {
              range "1..255" {
                error-message "Invalid value for attribute 'priority'. Valid values are in range:[1,255]";
              }
            }
            default "1";
          }
        }
      }
    }
    container user-plane-selection {
      description
        "External User Plane Selection settings";
      leaf default-pool {
        description
          "Default User Plane Node Pool";
        type string;
        must '/epg/sgw/user-plane-pool/pool[name=current()]' {
          error-message "default-pool must be configured under [epg sgw user-plane-pool pool]";
        }
      }
      list selection-condition {
        key "name";
        leaf name {
          description
            "Selection condition name";
          type string {
            pattern '[.0-9A-Za-z_-]*' {
              error-message "Must contain only letters, numbers, underscores or dashes";
            }
            length "1..64";
          }
        }
        list data-network {
          key "name";
          leaf name {
            description
              "Data network apn name";
            type string {
              pattern '[.0-9A-Za-z_-]*' {
                error-message "Must contain only letters, numbers, underscores or dashes";
              }
              length "1..64";
            }
          }
        }
        list area-id {
          key "name";
          leaf name {
            description
              "Area Id";
            type string;
            must '/epg/sgw/location/area-id[name=current()]' {
              error-message "area-id must be configured under [epg sgw location area-id]";
            }
          }
        }
        leaf selected-pool {
          description
            "Selected pool name";
          type string;
          must '/epg/sgw/user-plane-pool/pool[name=current()]' {
            error-message "selected-pool must be configured under [epg sgw user-plane-pool pool]";
          }
        }
      }
    }
    container stop {
      yexte:user-group "ericsson-support,epg-admin";
      description
        "Stop the SGW service";
      presence "stop need presence";
      leaf node {
        description
          "Stop on node level";
        type empty;
      }
    }
    container ebm {
      yexte:user-group "ericsson-support,epg-tracing-admin";
      description
        "SGW control plane event based monitoring settings";
      uses ebm-type;
    }
    container bearer {
      description
        "SGW bearer settings";
      leaf limit {
        description
          "Maximum active sgw-only bearers";
        type uint32 {
          range "1..4294967295" {
            error-message "Invalid value for attribute 'limit'. Valid values are in range:[1,4294967295]";
          }
        }
        default "32000000";
      }
      leaf cause-code-in-manual-deletion {
        description
          "Reactivation request should be included in delete bearer";
        type empty;
      }
      action terminate-imsi {
        yexte:user-group "ericsson-support,epg-admin";
        description
          "Terminate specified IMSI";
        input {
          leaf imsi-identifier {
            description
              "IMSI identifier";
            type string {
              pattern '([0-9]{5,15})|([0-9]{1,14}\*)' {
                error-message "ERROR: Invalid value for parameter imsi-identifier. Valid values are strings in a specified format. Type: imsi-identifier? for more information on the format to use.";
              }
              length "2..15";
            }
          }
        }
        output {
          leaf result {
            type string;
            mandatory true;
          }
        }
      }
      action terminate-all-sessions-on-pgw {
        yexte:user-group "ericsson-support,epg-admin";
        description
          "Terminate all sessions on PGW";
        input {
          leaf ip-address {
            description
              "PGW IP address-list : address-list should be wrapped with double-quotation mark";
            type string;
            mandatory true;
          }
          leaf ue-reconnect-option {
            description
              "append private extension for specific UeReconnectOption";
            type enumeration {
              enum reactivation {
                description
                  "append reactivation private extension";
              }
              enum reattach {
                description
                  "append reattach private extension";
              }
            }
          }
          leaf idle-session {
            description
              "terminate idle session of specific pgw ip address";
            type empty;
          }
        }
        output {
          leaf result {
            type string;
            mandatory true;
          }
        }
      }
      action terminate-all-pfcp-sessions-on-upf {
        yexte:user-group "ericsson-support,epg-admin";
        description
          "Terminate all sessions on UPF";
        input {
          leaf ip-address {
            description
              "UPF IP address-list : address-list should be wrapped with double-quotation mark";
            type string;
            mandatory true;
          }
          leaf idle-session {
            description
              "terminate idle session of specific upf ip address";
            type empty;
          }
        }
        output {
          leaf result {
            type string;
            mandatory true;
          }
        }
      }
    }
    container ddn {
      description
        "Configure Downlink Data Notification";
      container ddn-throttling {
        description
          "Enable SGW DDN Throttling";
        presence "ddn-throttling need presence";
        container high-prio-services {
          description
            "Set high priority services";
          presence "high-prio-services need presence";
          leaf-list arp-priority-level {
            description
              "ARP Priority Level value for high priority services";
            type uint8 {
              range "1..15" {
                error-message "Invalid value for attribute 'arp-priority-level'. Valid values are in range:[1,15]";
              }
            }
          }
          leaf-list qci {
            description
              "QCI value for high priority services";
            type uint8 {
              range "1..254" {
                error-message "Invalid value for attribute 'qci'. Valid values are in range:[1,254]";
              }
            }
          }
        }
      }
      leaf dl-user-plane-setup-timer {
        description
          "This downlink user plane setup timer is used for the SGW waiting for Modify Bearer Request or Modify Access Bearer Request for the UE in ECM-Idle status";
        type uint8 {
          range "1..60 " {
            error-message "Invalid value for attribute 'dl-user-plane-setup-timer'. Valid values are in range:[1,60]";
          }
        }
      }
      leaf ddn-interval {
        description
          "Specifies how many seconds after sending a Downlink Data Notification for a UE a new notification may be sent\\. Default is 13\\. If set to 0 and a paging failure occurs, there is no limit between notifications\\. Notifications for bearers with higher priority (lower ARP priority level) overrides this.";
        type uint8 {
          range "0..60" {
            error-message "Invalid value for attribute 'ddn-interval'. Valid values are in range:[0,60]";
          }
        }
      }
      container service-aware-smart-paging {
        description
          "service-aware Smart Paging is used to prioritize the Downlink Data Notification(DDN) messages sending and indicate a higher priority in the DDN messages based on DSCP value or service inspection";
        container dscp-aware {
          description
            "Service Dscp Aware Smart Paging is used to lower the ARP priority level in Downlink Data Notification messages sent to bearers that match configured paging profiles to indicate a higher priority";
          list profile {
            description
              "Profile with matching pattern under From and corresponding action under Then";
            max-elements 32;
            must '/epg/sgw/ddn/service-aware-smart-paging/dscp-aware/profile[name=current()/name]/from' {
              error-message "from is mandatory";
            }
            must '/epg/sgw/ddn/service-aware-smart-paging/dscp-aware/profile[name=current()/name]/then' {
              error-message "then is mandatory";
            }
            key "name";
            leaf name {
              description
                "Name of the profile";
              type string;
            }
            container from {
              description
                "ARP priority level and QCI value for bearer together with DSCP value specifies which packets to apply service-aware smart paging profiles to";
              presence "from need presence";
              leaf arp-priority-level {
                description
                  "ARP priority level value for bearer";
                type uint8 {
                  range "1..15" {
                    error-message "Invalid value for attribute 'arp-priority-level'. Valid values are in range:[1,15]";
                  }
                }
                mandatory true;
              }
              leaf dscp {
                description
                  "Downlink payload inner DSCP value to be used for service-aware smart paging inspection on bearers matching the QCI and ARP value of this profile";
                type enumeration {
                  enum af11 {
                    description
                      "Assured forwarding class 1, low drop precedence";
                  }
                  enum af12 {
                    description
                      "Assured forwarding class 1, medium drop precedence";
                  }
                  enum af13 {
                    description
                      "Assured forwarding class 1, high drop precedence";
                  }
                  enum af21 {
                    description
                      "Assured forwarding class 2, low drop precedence";
                  }
                  enum af22 {
                    description
                      "Assured forwarding class 2, medium drop precedence";
                  }
                  enum af23 {
                    description
                      "Assured forwarding class 2, high drop precedence";
                  }
                  enum af31 {
                    description
                      "Assured forwarding class 3, low drop precedence";
                  }
                  enum af32 {
                    description
                      "Assured forwarding class 3, medium drop precedence";
                  }
                  enum af33 {
                    description
                      "Assured forwarding class 3, high drop precedence";
                  }
                  enum af41 {
                    description
                      "Assured forwarding class 4, low drop precedence";
                  }
                  enum af42 {
                    description
                      "Assured forwarding class 4, medium drop precedence";
                  }
                  enum af43 {
                    description
                      "Assured forwarding class 4, high drop precedence";
                  }
                  enum ef {
                    description
                      "Expedited forwarding";
                  }
                  enum be {
                    description
                      "Best effort forwarding";
                  }
                  enum cs1 {
                    description
                      "Class selector 1";
                  }
                  enum cs2 {
                    description
                      "Class selector 2";
                  }
                  enum cs3 {
                    description
                      "Class selector 3";
                  }
                  enum cs4 {
                    description
                      "Class selector 4";
                  }
                  enum cs5 {
                    description
                      "Class selector 5";
                  }
                  enum cs6 {
                    description
                      "Class selector 6";
                  }
                  enum cs7 {
                    description
                      "Class selector 7";
                  }
                }
                mandatory true;
              }
              leaf qci {
                description
                  "QCI value for bearer";
                type uint8 {
                  range "1..254" {
                    error-message "Invalid value for attribute 'qci'. Valid values are in range:[1,254]";
                  }
                }
                mandatory true;
              }
            }
            container then {
              description
                "ARP priority level is included in the Downlink Data Notification message sent, when the service-aware smart paging profile is applied\\. The possibility is also given to exclude EBI from this message";
              presence "then need presence";
              leaf ddn-arp-priority-level {
                description
                  "ARP priority level is included in the Downlink Data Notification message sent, when the service-aware-smart paging profile is applied";
                type uint8 {
                  range "1..15" {
                    error-message "Invalid value for attribute 'ddn-arp-priority-level'. Valid values are in range:[1,15]";
                  }
                }
                mandatory true;
              }
              leaf exclude-ebi {
                description
                  "Exclude EBI from the downlink data notification sent, when the service-aware smart paging profile is applied";
                type empty;
              }
              leaf message-priority-level {
                description
                  "Message priority level is included in the Downlink Data Notification message sent, when the service-aware-smart paging profile is applied";
                type uint8 {
                  range "0..15" {
                    error-message "Invalid value for attribute 'message-priority-level'. Valid values are in range:[0,15]";
                  }
                }
              }
            }
          }
        }
        container service-id-aware {
          status current {
            yexte:preliminary;
          }
          description
            "Preliminary, serviceid-aware Smart Paging is used to send the Downlink Data Notification messages in high priority for services that match configured paging profiles";
          leaf data-type-indication {
            status current {
              yexte:preliminary;
            }
            description
              "Add Private Extension to indicate data type in Downlink Data Notification messages";
            type empty;
          }
          list profile {
            status current {
              yexte:preliminary;
            }
            description
              "Profile with matching pattern under From and corresponding action under Then";
            max-elements 32;
            must '/epg/sgw/ddn/service-aware-smart-paging/service-id-aware/profile[name=current()/name]/from' {
              error-message "from is mandatory";
            }
            must '/epg/sgw/ddn/service-aware-smart-paging/service-id-aware/profile[name=current()/name]/then' {
              error-message "then is mandatory";
            }
            key "name";
            leaf name {
              description
                "Paging profile name";
              type string;
            }
            container from {
              description
                "Define match criteria";
              presence "from need presence";
              leaf-list service-id {
                description
                  "A list of Service Identifier\\. E.g\\. [1, 3-100, 255]";
                type string {
                  pattern '((([0-9])|([1-9][0-9])|(1[0-9][0-9])|(2[0-4][0-9])|(25[0-5]))(-((([0-9])|([1-9][0-9])|(1[0-9][0-9])|(2[0-4][0-9])|(25[0-5]))))?)' {
                    error-message "Value must be a number from 0 to 255 or a range";
                  }
                }
                min-elements 1;
                max-elements 256;
              }
            }
            container then {
              description
                "Action to take if the 'from' condition is matched";
              presence "then need presence";
              leaf datatype {
                description
                  "Indicate data type in Downlink Data Notification messages for services that match configured paging profiles";
                type enumeration {
                  enum m-voip {
                    description
                      "Mobile voice over Internet Protocol";
                  }
                  enum normal-data {
                    description
                      "Normal data(default value)";
                  }
                }
                default "normal-data";
              }
              leaf service-priority {
                description
                  "priority of the service";
                type enumeration {
                  enum high {
                    description
                      "High priority";
                  }
                  enum normal {
                    description
                      "Normal priority(default value)";
                  }
                  enum buffering {
                    description
                      "Buffering priority";
                  }
                  enum drop {
                    description
                      "Drop priority";
                  }
                }
                default "normal";
              }
              leaf precedence {
                description
                  "Precedence of the service. The lower precedence values indicate higher precedence, and the higher precedence values indicate lower precedence ";
                type uint32 {
                  range "0..255" {
                    error-message "Invalid value for attribute 'precedence'. Valid values are in range:[0,255]";
                  }
                }
                default "1";
              }
            }
          }
        }
      }
      container inter-mme-paging {
        description
          "Configure inter-mme Paging";
        leaf disable {
          description
            "Disable inter-mme Paging";
          type empty;
        }
        leaf delay {
          description
            "Delay(msec) for resending DDN";
          type uint16 {
            range "0..3000" {
              error-message "Invalid value for attribute 'delay'. Valid values are in range:[0,3000]";
            }
          }
        }
      }
    }
    container internal-debug {
      yexte:user-group "ericsson-support";
      description
        "Actions used internally";
      action export-pm-xml-file {
        description
          "Write a PM XML file with current SGW counters.";
        output {
          leaf result {
            type string;
            mandatory true;
          }
        }
      }
      action gtp-path-status {
        description
          "Show status of a specific path";
        input {
          leaf ip-address {
            description
              "The peer ip address of the specific path";
            type string;
            mandatory true;
          }
        }
        output {
          leaf result {
            type string;
            mandatory true;
          }
        }
      }
      action gtp-path-status-all {
        description
          "Prints the status of all paths to file";
        output {
          leaf result {
            type string;
            mandatory true;
          }
        }
      }
      action pfcp-path-status {
        description
          "Show status of a specific Pfcp path";
        input {
          leaf ip-address {
            description
              "Node id (ip address format) of the specific Pfcp path";
            type string;
            mandatory true;
          }
        }
        output {
          leaf result {
            type string;
            mandatory true;
          }
        }
      }
      action set-peer-restart-counter {
        description
          "Set restart counter of a specific peer";
        input {
          leaf restart-counter {
            description
              "The new restart counter value of the specific peer";
            type uint8 {
              range "0..255" {
                error-message "Invalid value for attribute 'restart-counter'. Valid values are in range:[0,255]";
              }
            }
            mandatory true;
          }
          leaf ip-address {
            description
              "The ip address of the specific peer";
            type string;
            mandatory true;
          }
        }
        output {
          leaf result {
            type string;
            mandatory true;
          }
        }
      }
      action storage-manager-history {
        description
          "Prints checkin/checkout history of the storage manager";
        output {
          leaf result {
            type string;
            mandatory true;
          }
        }
      }
      action statistics {
        description
          "Counter identity";
        input {
          leaf identity {
            description
              "Counter identity";
            type string;
            mandatory true;
          }
        }
        output {
          leaf result {
            type string;
            mandatory true;
          }
        }
      }
      action reset-dvalue {
        description
          "Reset delay-value with '0' for DDN";
        output {
          leaf result {
            type string;
            mandatory true;
          }
        }
      }
      leaf nw-restoration-timer-sec {
        description
          "Specifies how long, in seconds, an inactive PDN connection is maintained after an MME or SGSN restart is detected or an MME or SGSN is detected as unavailable";
        type uint8 {
          range "1..60" {
            error-message "Invalid value for attribute 'nw-restoration-timer-sec'. Valid values are in range:[1,60]";
          }
        }
      }
      leaf nw-restoration-cleanout-timer-sec {
        description
          "Specifies how long, in seconds, an inactive PDN connection is maintained after a previously unavailable MME or SGSN becomes available";
        type uint16 {
          range "1..3600" {
            error-message "Invalid value for attribute 'nw-restoration-cleanout-timer-sec'. Valid values are in range:[1,3600]";
          }
        }
      }
      container session-resilience {
        description
          "SGW session resilience commands";
        action replica {
          description
            "Show information about replicas";
          input {
            leaf process-entity {
              description
                "Identifies the sgw-c process entity that should answer the command, for example 'all' or 'SC:2:2:0'";
              type string {
                pattern '(all|((SC|U)(:[0-9]?){3}))' {
                  error-message "Invalid process entity";
                }
              }
              mandatory true;
            }
          }
          output {
            leaf result {
              type string;
              mandatory true;
            }
          }
        }
        action replica-li {
          description
            "Show information about replicas for a load index";
          input {
            leaf load-index {
              description
                "Load index to display information about (optional, shows overview otherwise)";
              type uint16 {
                range "0..2047" {
                  error-message "Invalid value for attribute 'load-index'. Valid values are in range:[0,2047]";
                }
              }
              mandatory true;
            }
            leaf process-entity {
              description
                "Identifies the sgw-c process entity that should answer the command, for example 'all' or 'SC:2:2:0'";
              type string {
                pattern '(all|((SC|U)(:[0-9]?){3}))' {
                  error-message "Invalid process entity";
                }
              }
              mandatory true;
            }
          }
          output {
            leaf result {
              type string;
              mandatory true;
            }
          }
        }
        action replica-li-debug {
          description
            "Show debug information about replicas for a load index";
          input {
            leaf load-index {
              description
                "Load index to display information about (optional, shows overview otherwise)";
              type uint16 {
                range "0..2047" {
                  error-message "Invalid value for attribute 'load-index'. Valid values are in range:[0,2047]";
                }
              }
              mandatory true;
            }
            leaf process-entity {
              description
                "Identifies the sgw-c process entity that should answer the command, for example 'all' or 'SC:2:2:0'";
              type string {
                pattern '(all|((SC|U)(:[0-9]?){3}))' {
                  error-message "Invalid process entity";
                }
              }
              mandatory true;
            }
          }
          output {
            leaf result {
              type string;
              mandatory true;
            }
          }
        }
        action replicator {
          description
            "Show information about replicators";
          input {
            leaf communication-id {
              description
                "Communication ID to display info for (currently only: 'internal' or 'ICR')";
              type string {
                pattern '(internal|ICR)' {
                  error-message "Invalid communication id. Must be 'internal' or 'ICR'";
                }
              }
              mandatory true;
            }
            leaf process-entity {
              description
                "Identifies the sgw-c process entity that should answer the command, for example 'all' or 'SC:2:2:0'";
              type string {
                pattern '(all|((SC|U)(:[0-9]?){3}))' {
                  error-message "Invalid process entity";
                }
              }
              mandatory true;
            }
          }
          output {
            leaf result {
              type string;
              mandatory true;
            }
          }
        }
        action replicator-li {
          description
            "Show information about replicators for a load index";
          input {
            leaf communication-id {
              description
                "Communication ID to display info for (currently only: 'internal' or 'ICR')";
              type string {
                pattern '(internal|ICR)' {
                  error-message "Invalid communication id. Must be 'internal' or 'ICR'";
                }
              }
              mandatory true;
            }
            leaf load-index {
              description
                "Load index to display information about (optional, shows overview otherwise)";
              type uint16 {
                range "0..2047" {
                  error-message "Invalid value for attribute 'load-index'. Valid values are in range:[0,2047]";
                }
              }
              mandatory true;
            }
            leaf process-entity {
              description
                "Identifies the sgw-c process entity that should answer the command, for example 'all' or 'SC:2:2:0'";
              type string {
                pattern '(all|((SC|U)(:[0-9]?){3}))' {
                  error-message "Invalid process entity";
                }
              }
              mandatory true;
            }
          }
          output {
            leaf result {
              type string;
              mandatory true;
            }
          }
        }
        action replicator-li-debug {
          description
            "Show debug information about replicators for a load index";
          input {
            leaf communication-id {
              description
                "Communication ID to display info for (currently only: 'internal' or 'ICR')";
              type string {
                pattern '(internal|ICR)' {
                  error-message "Invalid communication id. Must be 'internal' or 'ICR'";
                }
              }
              mandatory true;
            }
            leaf load-index {
              description
                "Load index to display information about (optional, shows overview otherwise)";
              type uint16 {
                range "0..2047" {
                  error-message "Invalid value for attribute 'load-index'. Valid values are in range:[0,2047]";
                }
              }
              mandatory true;
            }
            leaf process-entity {
              description
                "Identifies the sgw-c process entity that should answer the command, for example 'all' or 'SC:2:2:0'";
              type string {
                pattern '(all|((SC|U)(:[0-9]?){3}))' {
                  error-message "Invalid process entity";
                }
              }
              mandatory true;
            }
          }
          output {
            leaf result {
              type string;
              mandatory true;
            }
          }
        }
        container lim {
          description
            "SGW LIM session resilience commands";
          action history-pe {
            description
              "Show the LIM history in sgw-c";
            input {
              leaf load-indices {
                description
                  "Load indices to print, might be either a comma-separated list, a range or both, for example 1,3,5-7,9";
                type string;
                mandatory true;
              }
              leaf process-entity {
                description
                  "Identifies the sgw-c process entity that should answer the command, for example 'all' or 'SC:2:2:0'";
                type string {
                  pattern '(all|((SC|U)(:[0-9]?){3}))' {
                    error-message "Invalid process entity";
                  }
                }
                mandatory true;
              }
            }
            output {
              leaf result {
                type string;
                mandatory true;
              }
            }
          }
          action pending {
            description
              "Show the pending orders of the LIM in sgw-c, and status";
            input {
              leaf process-entity {
                description
                  "Identifies the sgw-c process entity that should answer the command, for example 'all' or 'SC:2:2:0'";
                type string {
                  pattern '(all|((SC|U)(:[0-9]?){3}))' {
                    error-message "Invalid process entity";
                  }
                }
                mandatory true;
              }
            }
            output {
              leaf result {
                type string;
                mandatory true;
              }
            }
          }
          action synchronizers {
            description
              "Show the status of the LIM synchronizers in sgw-c";
            input {
              leaf process-entity {
                description
                  "Identifies the sgw-c process entity that should answer the command, for example 'all' or 'SC:2:2:0'";
                type string {
                  pattern '(all|((SC|U)(:[0-9]?){3}))' {
                    error-message "Invalid process entity";
                  }
                }
                mandatory true;
              }
            }
            output {
              leaf result {
                type string;
                mandatory true;
              }
            }
          }
          action synchronizers-li {
            description
              "Show the status of the LIM synchronizers in sgw-c";
            input {
              leaf load-indices {
                description
                  "Load indices to print, might be either a comma-separated list, a range or both, for example 1,3,5-7,9";
                type string;
                mandatory true;
              }
              leaf process-entity {
                description
                  "Identifies the sgw-c process entity that should answer the command, for example 'all' or 'SC:2:2:0'";
                type string {
                  pattern '(all|((SC|U)(:[0-9]?){3}))' {
                    error-message "Invalid process entity";
                  }
                }
                mandatory true;
              }
            }
            output {
              leaf result {
                type string;
                mandatory true;
              }
            }
          }
          action table {
            description
              "Show the LIM table as stored in sgw-c";
            input {
              leaf process-entity {
                description
                  "Identifies the process entity that should answer the command, for example 'SC:2:2:0'";
                type string {
                  pattern '(all|((SC|U)(:[0-9][0-9]?){0,3}))' {
                    error-message "Invalid process entity";
                  }
                }
                mandatory true;
              }
            }
            output {
              leaf result {
                type string;
                mandatory true;
              }
            }
          }
          action table-pe-type {
            description
              "Show the LIM table as stored in sgw-c";
            input {
              leaf pe-type {
                description
                  "Print LIM indices for user plane or control plane";
                type string {
                  pattern '(all|sgwc|u)' {
                    error-message "Invalid pe type";
                  }
                }
                mandatory true;
              }
              leaf process-entity {
                description
                  "Identifies the process entity that should answer the command, for example 'SC:2:2:0'";
                type string {
                  pattern '(all|((SC|U)(:[0-9][0-9]?){0,3}))' {
                    error-message "Invalid process entity";
                  }
                }
                mandatory true;
              }
            }
            output {
              leaf result {
                type string;
                mandatory true;
              }
            }
          }
          action table-pe-type-li {
            description
              "Show the LIM table as stored in sgw-c";
            input {
              leaf pe-type {
                description
                  "Print LIM indices for user plane or control plane [all|sgwc|u]";
                type string {
                  pattern '(all|sgwc|u)' {
                    error-message "Invalid pe type";
                  }
                }
                mandatory true;
              }
              leaf load-indices {
                description
                  "Load indices to print, might be either a comma-separated list, a range or both, for example 1,3,5-7,9";
                type string;
                mandatory true;
              }
              leaf process-entity {
                description
                  "Process entity that should print the LIM table, for example 'all' or 'SC:2:2:0'";
                type string {
                  pattern '(all|((SC|U)(:[0-9][0-9]?){0,3}))' {
                    error-message "Invalid process entity";
                  }
                }
                mandatory true;
              }
            }
            output {
              leaf result {
                type string;
                mandatory true;
              }
            }
          }
          action ue-distribution {
            description
              "Show the UE distribution among the load indices";
            input {
              leaf level {
                type enumeration {
                  enum detail {
                    description
                      "Show detailed information";
                  }
                  enum brief {
                    description
                      "Show brief information";
                  }
                }
                mandatory true;
              }
              leaf process-entity {
                description
                  "Identifies the sgw-c process entity that should answer the command, for example 'all' or 'SC:2:2:0'";
                type string {
                  pattern '(all|((SC|U)(:[0-9]?){3}))' {
                    error-message "Invalid process entity";
                  }
                }
                mandatory true;
              }
            }
            output {
              leaf result {
                type string;
                mandatory true;
              }
            }
          }
          action ue-distribution-li {
            description
              "Show the UE distribution for a load index";
            input {
              leaf level {
                type enumeration {
                  enum detail {
                    description
                      "Show detailed information";
                  }
                  enum brief {
                    description
                      "Show brief information";
                  }
                }
                mandatory true;
              }
              leaf load-index {
                description
                  "Load index to display information about (optional, shows overview otherwise)";
                type uint16 {
                  range "0..2047" {
                    error-message "Invalid value for attribute 'load-index'. Valid values are in range:[0,2047]";
                  }
                }
                mandatory true;
              }
              leaf process-entity {
                description
                  "Identifies the sgw-c process entity that should answer the command, for example 'all' or 'SC:2:2:0'";
                type string {
                  pattern '(all|((SC|U)(:[0-9]?){3}))' {
                    error-message "Invalid process entity";
                  }
                }
                mandatory true;
              }
            }
            output {
              leaf result {
                type string;
                mandatory true;
              }
            }
          }
          action history-database {
            description
              "Show history of LIM orders received in sgw-c data storage";
            input {
              leaf load-indices {
                description
                  "Load indices to print, might be either a comma-separated list, a range or both, for example 1,3,5-7,9";
                type string;
                mandatory true;
              }
              leaf process-entity {
                description
                  "Identifies the sgw-c process entity that should answer the command, for example 'all' or 'SC:2:2:0'";
                type string {
                  pattern '(all|((SC|U)(:[0-9]?){3}))' {
                    error-message "Invalid process entity";
                  }
                }
                mandatory true;
              }
            }
            output {
              leaf result {
                type string;
                mandatory true;
              }
            }
          }
        }
      }
      leaf ddn-checkout-retry-times {
        description
          "ddn checkout retry times";
        type uint8 {
          range "4..100" {
            error-message "Invalid value for attribute 'ddn-checkout-retry-times'. Valid values are in range:[4,100]";
          }
        }
        default "4";
      }
    }
    action statistics {
      description
        "Show SGW statistics";
      output {
        leaf result {
          type string;
          mandatory true;
        }
      }
    }
    action statistics-charging {
      description
        "Show SGW statistics charging";
      output {
        leaf result {
          type string;
          mandatory true;
        }
      }
    }
    action statistics-mme {
      description
        "Show SGW statistics MME";
      input {
        leaf ip-address {
          description
            "MME IP address, expressed either as IPv4 or IPv6";
          type inet:ip-address;
        }
      }
      output {
        leaf result {
          type string;
          mandatory true;
        }
      }
    }
    action statistics-pgw {
      description
        "Show SGW statistics PGW";
      input {
        leaf ip-address {
          description
            "PGW IP address, expressed either as IPv4 or IPv6";
          type inet:ip-address;
        }
      }
      output {
        leaf result {
          type string;
          mandatory true;
        }
      }
    }
    action statistics-plmn {
      description
        "Show SGW statistics PLMN ID";
      input {
        leaf plmn-id {
          description
            "Public Land Mobile Network identifier";
          type string {
            pattern '([0-9]{5,15})|([0-9]{1,18})' {
              error-message "PLMN identifier is a string of 5 or 6 digits";
            }
            length "5..6";
          }
        }
      }
      output {
        leaf result {
          type string;
          mandatory true;
        }
      }
    }
    action statistics-upf {
      description
        "Show SGW statistics UPF";
      input {
        leaf node-id {
          description
            "UPF IP address, expressed either as IPv4 or IPv6";
          type inet:ip-address;
        }
      }
      output {
        leaf result {
          type string;
          mandatory true;
        }
      }
    }
    action statistics-qci {
      description
        "Show SGW statistics qci";
      input {
        leaf qci {
          description
            "print statistics indexed on qci value : 1~254 or all";
          type string {
            pattern '(other|all|(([1-9])|([1-9][0-9])|(1[0-9][0-9])|(2[0-4][0-9])|(25[0-4])))' {
              error-message "Invalid qci value : 1~254 or all";
            }
          }
        }
        leaf interface {
          description
            "print statistics indexed on interface value";
          type enumeration {
            enum all {
              description
                "all interfaces";
            }
            enum s4s11 {
              description
                "s4s11 interface";
            }
            enum s5s8 {
              description
                "s5s8 interface";
            }
            enum s5 {
              description
                "s5 interface";
            }
            enum s8 {
              description
                "s8 interface";
            }
          }
        }
        leaf detail-level {
          description
            "print counters or gauges only";
          type enumeration {
            enum brief {
              description
                "gauges only";
            }
            enum detail {
              description
                "gauges and counters";
            }
          }
        }
      }
      output {
        leaf result {
          type string;
          mandatory true;
        }
      }
    }
    action statistics-arp {
      description
        "Show SGW statistics arp";
      output {
        leaf result {
          type string;
          mandatory true;
        }
      }
    }
    leaf-list imsi-prefix-statistics {
      description
        "Prefix of IMSI (1~15 digits) for command epg sgw statistics-imsi-prefix";
      type string {
        pattern '([0-9]{1,15})' {
          error-message "ERROR: Invalid value for parameter imsi-prefix-statistics. Valid values are strings in a specified format. Type: imsi-prefix-statistics? for more information on the format to use.";
        }
        length "1..15";
      }
      max-elements 200;
    }
    action statistics-imsi-prefix {
      description
        "Show SGW statistics per IMSI prefix";
      input {
        leaf imsi-prefix {
          description
            "Prefix of IMSI (1-15 digits)";
          type string {
            pattern '([0-9]{1,15})' {
              error-message "ERROR: Invalid value for parameter imsi-prefix. Valid values are strings in a specified format. Type: imsi-prefix? for more information on the format to use.";
            }
            length "1..15";
          }
        }
      }
      output {
        leaf result {
          type string;
          mandatory true;
        }
      }
    }
    action user-info {
      yexte:user-group "ericsson-support,epg-tracing-admin,epg-admin";
      description
        "Show imsi or imei information";
      input {
        leaf identifier-type {
          type enumeration {
            enum imsi {
              description
                "Use IMSI as subscription identifier";
            }
            enum imei {
              description
                "Use IMEI as subscription identifier";
            }
          }
          mandatory true;
        }
        leaf value {
          description
            "Imsi or imei identity";
          type string {
            pattern '([0-9]{5,15})|([0-9]{1,18})' {
              error-message "ERROR: Invalid value for parameter value. Valid values are strings in a specified format. Type: value? for more information on the format to use.";
            }
          }
          mandatory true;
        }
      }
      output {
        leaf result {
          type string;
          mandatory true;
        }
      }
    }
    action user-info-unknown-imsi {
      yexte:user-group "ericsson-support,epg-tracing-admin,epg-admin";
      description
        "Show unauthenticated user information";
      output {
        leaf result {
          type string;
          mandatory true;
        }
      }
    }
    action user-info-imsi-list {
      yexte:user-group "ericsson-support,epg-tracing-admin,epg-admin";
      description
        "Show list of IMSIs";
      output {
        leaf result {
          type string;
          mandatory true;
        }
      }
    }
    action statistics-service-id {
      status current {
        yexte:preliminary;
      }
      description
        "Preliminary, Show SGW statistics Service Id Smart Paging";
      input {
        leaf service-id {
          description
            "print statistics indexed on service id value : 0~255";
          type string {
            pattern '(([0-9])|([1-9][0-9])|(1[0-9][0-9])|(2[0-4][0-9])|(25[0-5]))' {
              error-message "Invalid service id value : 0~255";
            }
          }
        }
      }
      output {
        leaf result {
          type string;
          mandatory true;
        }
      }
    }
  }

  grouping ipv6-router-advertisement-type {
    leaf maximum-interval {
      description
        "Maximum interval between router advertisements";
      type uint16 {
        range "5400..21600" {
          error-message "Invalid value for attribute 'maximum-interval'. Valid values are in range:[5400,21600]";
        }
      }
    }
    leaf minimum-interval {
      description
        "Minimum interval between router advertisements";
      type uint16 {
        range "3600..16200" {
          error-message "Invalid value for attribute 'minimum-interval'. Valid values are in range:[3600,16200]";
        }
      }
    }
    leaf maximum-initial-interval {
      description
        "Maximum interval between initial router advertisements";
      type uint8 {
        range "10..16" {
          error-message "Invalid value for attribute 'maximum-initial-interval'. Valid values are in range:[10,16]";
        }
      }
    }
    leaf maximum-initial-advertisements {
      description
        "Maximum number of initial router advertisements";
      type uint8 {
        range "2..5" {
          error-message "Invalid value for attribute 'maximum-initial-advertisements'. Valid values are in range:[2,5]";
        }
      }
    }
    leaf link-local-interface-identifier {
      description
        "Interface identifier for PPB link-local addresses";
      type inet:ipv6-address;
    }
    leaf reachable-time {
      description
        "Value to be placed in reachable time field";
      type uint32 {
        range "0..3600000" {
          error-message "Invalid value for attribute 'reachable-time'. Valid values are in range:[0,3600000]";
        }
      }
    }
    leaf retransmission-timer {
      description
        "Value to be placed in retrans timer field";
      type uint32;
    }
    leaf router-lifetime {
      description
        "Value to be placed in router lifetime field";
      type uint16 {
        range "5400..21840" {
          error-message "Invalid value for attribute 'router-lifetime'. Valid values are in range:[5400,21840]";
        }
      }
    }
    leaf current-hop-limit {
      description
        "Value to be placed in current hop limit field";
      type uint8 {
        range "0..255" {
          error-message "Invalid value for attribute 'current-hop-limit'. Valid values are in range:[0,255]";
        }
      }
    }
  }

  grouping plmn-type {
    leaf name {
      description
        "Name of PLMN";
      type string {
        pattern '[A-Za-z.0-9-]*' {
          error-message "PLMN name may consist of up to 20 letters, numbers, periods and dashes";
        }
        length "1..20";
      }
    }
    list plmn-id {
      key "name";
      uses plmn-id-type;
    }
  }

  grouping plmn-id-type {
    leaf name {
      description
        "Public land mobile network identifier";
      type string {
        pattern '[0-9]*' {
          error-message "PLMN identifier is a string of 5 or 6 digits";
        }
        length "5..6";
      }
    }
    leaf home-plmn {
      description
        "This is home PLMN";
      type empty;
    }
    list sgsn-address {
      key "name";
      uses sgsn-address-type;
    }
  }

  grouping sgsn-address-type {
    leaf name {
      description
        "SGSN IPv4 or IPv6 address with optional prefix";
      type eip-prefix-optional;
    }
    leaf rat-type {
      description
        "SGSN radio access technology (RAT)";
      type common-rat-type;
    }
  }

  grouping pgw-user-plane-type {
    leaf mtu {
      description
        "Maximum transmission unit (MTU) for end user IP packets downlink\\. This value is overridden if MTU is configured on APN level.";
      type uint16 {
        range "1280..2900" {
          error-message "Invalid value for attribute 'mtu'. Valid values are in range:[1280,2900]";
        }
      }
      default "1280";
    }
    list node-name {
      key "name";
      uses user-plane-node-type;
      max-elements 256;
    }
    container predefined-rule {
      description
        "Predefined URR identifiers for offline and online charging";
      list profile {
        description
          "Predefined rule profile";
        key "name";
        max-elements 1;
        leaf name {
          description
            "Predefined rule profile name";
          type common-string-id;
        }
        list rating-group {
          description
            "Predefined URR identifiers per rating-group";
          key "name";
          leaf name {
            description
              "Rating-group-id";
            type uint32;
          }
          leaf online-urr-id {
            description
              "Predefined URR identifier for online charging";
            type uint32 {
              range "1..2147483647" {
                error-message "Invalid value for attribute 'online'. Valid values are in range:[1,2147483647]";
              }
            }
          }
          leaf offline-urr-id {
            description
              "Predefined URR identifier for offline charging";
            type uint32 {
              range "1..2147483647" {
                error-message "Invalid value for attribute 'offline'. Valid values are in range:[1,2147483647]";
              }
            }
          }
          list service-id {
            description
              "Predefined URR identifiers per service-id";
            key "name";
            leaf name {
              description
                "Service-id";
              type uint32;
            }
            leaf online-urr-id {
              description
                "Predefined URR identifier for online charging";
              type uint32 {
                range "1..2147483647" {
                  error-message "Invalid value for attribute 'online'. Valid values are in range:[1,2147483647]";
                }
              }
            }
            leaf offline-urr-id {
              description
                "Predefined URR identifier for offline charging";
              type uint32 {
                range "1..2147483647" {
                  error-message "Invalid value for attribute 'offline'. Valid values are in range:[1,2147483647]";
                }
              }
            }
          }
        }
        list monitoring-key {
          description
            "Predefined URR identifiers per monitoring key";
          key "name";
          leaf name {
            description
              "Monitoring key";
            type common-string-id;
          }
          leaf urr-id {
            description
              "Predefined URR identifier for usage monitoring key";
            type uint32 {
              range "1..2147483647" {
                error-message "Invalid value for attribute 'urr-id'. Valid values are in range:[1,2147483647]";
              }
            }
          }
        }
      }
    }
  }

  grouping user-plane-node-type {
    leaf name {
      description
        "User plane node name";
      type string {
        pattern '[.0-9A-Za-z_-]*' {
          error-message "Must contain only letters, numbers, underscores or dashes";
        }
        length "1..64";
      }
    }

    grouping apn-address-range-type {
      leaf name {
        description
          "Address range for APN network for cups";
        type eipv4-prefix-optional;
      }
      leaf-list data-network {
        max-elements 3000;
        type leafref {
          path "/epg/pgw/apn/name";
        }
      }
    }

    grouping apn-ipv6-address-range-type {
      leaf name {
        description
          "Address range for APN network for cups";
        type eipv6-prefix-optional;
      }
      leaf-list data-network {
        max-elements 3000;
        type leafref {
          path "/epg/pgw/apn/name";
        }
      }
    }
    container sxb-ie-options {
      description
        "Settings for optional attributes over Sxb";
      leaf debug-info {
        description
          "Include debug information IE in Sxb";
        type empty;
      }
      container subscriber-info {
        description
          "Optional inclusion of subscriber information in Sxb";
        leaf apn {
          description
            "User equipment APN";
          type enumeration {
            enum logical {
              description
                "Logical APN name";
            }
            enum requested {
              description
                "Requested APN name";
            }
            enum used {
              description
                "Used APN name";
            }
          }
        }
        leaf nas {
          description
            "Network access server identifier";
          type empty;
        }
        leaf pgw-c-ip-address {
          description
            "PGW control plane IP address";
          type empty;
        }
        leaf rat {
          description
            "RAT type";
          type empty;
        }
        leaf uli {
          description
            "ULI";
          type empty;
        }
      }
    }
    leaf li-t3 {
      description
        "Reference to the li-t3 in [epg node lawful-intercept user-plane-selection]";
      type leafref {
        path "/epg/node/lawful-intercept/user-plane-selection/li-t3/name";
      }
    }
    leaf pfcp-address {
      description
        "PFCP address";
      type inet:ip-address;
      mandatory true;
    }
    list ip-selection-condition {
      key "name";
      max-elements 1000;
      ordered-by user;
      uses ip-selection-condition-type;
      must '(/epg/pgw/user-plane/node-name[name=current()/../name]/ip-selection-condition[name=current()/name]/data-network) or (/epg/pgw/user-plane/node-name[name=current()/../name]/ip-selection-condition[name=current()/name]/area-id)' {
        error-message "Data network or area id must be configured in a ip selection condition";
      }
      must '(/epg/pgw/user-plane/node-name[name=current()/../name]/ip-selection-condition[name=current()/name]/selected-shared-ipv4-pool) or (/epg/pgw/user-plane/node-name[name=current()/../name]/ip-selection-condition[name=current()/name]/selected-shared-ipv6-pool)' {
        error-message "At least one selected shared ip pool must be configured in a ip selection condition";
      }
    }
    list address {
      status current {
        yexte:preliminary;
      }
      key "name";
      uses apn-address-range-type;
    }
    list ipv6-address {
      status current {
        yexte:preliminary;
      }
      key "name";
      uses apn-ipv6-address-range-type;
    }
    container s5s8-u {
      description
        "s5s8-u network-instance";
      leaf network-instance {
        type string;
      }
    }
    container sx-u {
      description
        "sx-u network-instance";
      leaf network-instance {
        type string;
      }
    }
    leaf dcnr {
      status current {
        yexte:preliminary;
      }
      description
        "Dual connectivity NR";
      type empty;
    }
    leaf co-located {
      status current {
        yexte:preliminary;
      }
      description
        "Co-located user plane";
      type empty;
    }
    leaf creation {
      description
        "PDP context creation state";
      type enumeration {
        enum unblocked {
          description
            "No restrictions on PDP context creation";
        }
        enum blocked {
          description
            "New PDP context creation fully blocked";
        }
      }
    }
  }

  grouping ip-selection-condition-type {
    leaf name {
      description
        "Ip selection condition name";
      type string {
        pattern '[.0-9A-Za-z_-]*' {
          error-message "Must contain only letters, numbers, underscores or dashes";
        }
        length "1..64";
      }
    }
    leaf-list data-network {
      max-elements 3000;
      type leafref {
        path "/epg/pgw/apn/name";
      }
    }
    leaf-list area-id {
      max-elements 3000;
      type leafref {
        path "/epg/pgw/location/area/name";
      }
    }
    leaf selected-shared-ipv4-pool {
      description
        "Selected shared ipv4 pool name";
      type leafref {
        path "/epg/pgw/shared-ip-pool/name";
      }
      must '(/epg/pgw/shared-ip-pool[name=current()]/address)' {
        error-message "Selected shared ipv4 pool must have ipv4 range";
      }
    }
    leaf selected-shared-ipv6-pool {
      description
        "Selected shared ipv6 pool name";
      type leafref {
        path "/epg/pgw/shared-ip-pool/name";
      }
      must '(/epg/pgw/shared-ip-pool[name=current()]/ipv6-address)' {
        error-message "Selected shared ipv6 pool must have ipv6 range";
      }
    }
  }

  grouping sx-n4-interface-type {
    leaf logical-interface {
      status current {
        yexte:preliminary;
      }
      description
        "Logical interface";
      type leafref {
        path "/epg/node/logical-interface/name";
      }
    }
    leaf heartbeat-interval {
      status current {
        yexte:preliminary;
      }
      description
        "Interval between Sx Heartbeat Request messages in 100ms unit";
      type uint16 {
        range "1..6000" {
          error-message "Invalid value for attribute 'heartbeat-interval'. Valid values are in range:[1,6000]";
        }
      }
      default "600";
    }
    leaf association-interval {
      status current {
        yexte:preliminary;
      }
      description
        "Interval between Association Setup Request messages in 100ms unit";
      type uint16 {
        range "1..6000" {
          error-message "Invalid value for attribute 'association -interval'. Valid values are in range:[1,6000]";
        }
      }
      default "600";
    }
    leaf n1 {
      status current {
        yexte:preliminary;
      }
      description
        "Total number of transmissions for a pfcp message";
      type uint16 {
        range "1..10" {
          error-message "Invalid value for attribute 'n1'. Valid values are in range:[1, 10]";
        }
      }
      default "3";
    }
    leaf t1 {
      status current {
        yexte:preliminary;
      }
      description
        "Interval between pfcp message retries in 100ms unit";
      type uint16 {
        range "1..500" {
          error-message "Invalid value for attribute 't1'. Valid values are in range:[1,500]";
        }
      }
      default "50";
    }
    leaf no-pfcp-path-management {
      description
        "If enabled, disable PFCP path management.";
      status current {
        yexte:preliminary;
      }
      type empty;
    }
    leaf no-pfcp-path-failure {
      description
        "If enabled, do not delete the UPF related PDN connection when PFCP path failure to the UPF is detected";
      status current {
        yexte:preliminary;
      }
      type empty;
    }
    leaf no-peer-restart {
      description
        "If enabled, do not delete the PDN connection related with the restarted UPF when UPF Restart is detected";
      status current {
        yexte:preliminary;
      }
      type empty;
    }
    leaf mtu-size {
      status current {
        yexte:preliminary;
      }
      description
        "Maximum transmission unit. Default values IPv4: 1500, IPv6: 1280.";
      type uint16 {
        range "1280..3000" {
          error-message "Invalid value for attribute 'mtu-size'. Valid values are in range:[1280,3000]";
        }
      }
    }
    leaf diffserv {
      status current {
        yexte:preliminary;
      }
      description
        "DSCP (DiffServ Code Point) for Sx packets";
      type enumeration {
        enum af11 {
          description
            "Assured forwarding class 1, low drop precedence";
        }
        enum af12 {
          description
            "Assured forwarding class 1, medium drop precedence";
        }
        enum af13 {
          description
            "Assured forwarding class 1, high drop precedence";
        }
        enum af21 {
          description
            "Assured forwarding class 2, low drop precedence";
        }
        enum af22 {
          description
            "Assured forwarding class 2, medium drop precedence";
        }
        enum af23 {
          description
            "Assured forwarding class 2, high drop precedence";
        }
        enum af31 {
          description
            "Assured forwarding class 3, low drop precedence";
        }
        enum af32 {
          description
            "Assured forwarding class 3, medium drop precedence";
        }
        enum af33 {
          description
            "Assured forwarding class 3, high drop precedence";
        }
        enum af41 {
          description
            "Assured forwarding class 4, low drop precedence";
        }
        enum af42 {
          description
            "Assured forwarding class 4, medium drop precedence";
        }
        enum af43 {
          description
            "Assured forwarding class 4, high drop precedence";
        }
        enum ef {
          description
            "Expedited forwarding";
        }
        enum be {
          description
            "Best effort forwarding";
        }
        enum cs1 {
          description
            "Class selector 1";
        }
        enum cs2 {
          description
            "Class selector 2";
        }
        enum cs3 {
          description
            "Class selector 3";
        }
        enum cs4 {
          description
            "Class selector 4";
        }
        enum cs5 {
          description
            "Class selector 5";
        }
        enum cs6 {
          description
            "Class selector 6";
        }
        enum cs7 {
          description
            "Class selector 7";
        }
      }
    }
    leaf heartbeat-times {
      status current {
        yexte:preliminary;
      }
      description
        "Number of times to retry unsuccessful transfer of Heartbeat Request to detect Sx path failure";
      type uint8 {
        range "1..10" {
          error-message "Invalid value for attribute 'heartbeat-times'. Valid values are in range:[1,10]";
        }
      }
      default "3";
    }
    leaf load-control-capability {
      description
        "Enable load control capability";
      type empty;
    }
    leaf over-load-control-capability {
      description
        "Enable overload control capability";
      type empty;
    }
    action path-status {
      description
        "Show status of pfcp path";
      input {
        choice node-id {
          leaf all {
            description
              "Show status of all pfcp path";
            type empty;
          }
          leaf upf-node-fqdn-id {
            description
              "Show status of one Fully Qualified Domain Name (FQDN) upf path";
            type string {
              pattern '[.0-9A-Za-z_-]*' {
                error-message "Must contain only letters, numbers, underscores or dashes";
              }
              length "1..255";
            }
            mandatory true;
          }
          leaf upf-node-ip-id {
            description
              "Show status of one ip-address upf path";
            type inet:ip-address;
          }
        }
      }
      output {
        leaf result {
          type string;
          mandatory true;
        }
      }
    }
  }

  grouping pgw-interface-type {
    container s5s8-c {
      description
        "S5 and S8 control plane interface";
      presence "s5s8-c need presence";
      leaf logical-interface {
        description
          "Reference to the logical-interface in [epg node logical-interface]";
        type leafref {
          path "/epg/node/logical-interface/name";
        }
        mandatory true;
      }
      leaf message-priority {
        description
          "The messagePriority configured under [epg pgw interface s5s8-c] S5s8c";
        type empty;
      }
      leaf diffserv {
        description
          "DSCP (DiffServ Code Point) for GTP packets";
        type enumeration {
          enum af11 {
            description
              "Assured forwarding class 1, low drop precedence";
          }
          enum af12 {
            description
              "Assured forwarding class 1, medium drop precedence";
          }
          enum af13 {
            description
              "Assured forwarding class 1, high drop precedence";
          }
          enum af21 {
            description
              "Assured forwarding class 2, low drop precedence";
          }
          enum af22 {
            description
              "Assured forwarding class 2, medium drop precedence";
          }
          enum af23 {
            description
              "Assured forwarding class 2, high drop precedence";
          }
          enum af31 {
            description
              "Assured forwarding class 3, low drop precedence";
          }
          enum af32 {
            description
              "Assured forwarding class 3, medium drop precedence";
          }
          enum af33 {
            description
              "Assured forwarding class 3, high drop precedence";
          }
          enum af41 {
            description
              "Assured forwarding class 4, low drop precedence";
          }
          enum af42 {
            description
              "Assured forwarding class 4, medium drop precedence";
          }
          enum af43 {
            description
              "Assured forwarding class 4, high drop precedence";
          }
          enum ef {
            description
              "Expedited forwarding";
          }
          enum be {
            description
              "Best effort forwarding";
          }
          enum cs1 {
            description
              "Class selector 1";
          }
          enum cs2 {
            description
              "Class selector 2";
          }
          enum cs3 {
            description
              "Class selector 3";
          }
          enum cs4 {
            description
              "Class selector 4";
          }
          enum cs5 {
            description
              "Class selector 5";
          }
          enum cs6 {
            description
              "Class selector 6";
          }
          enum cs7 {
            description
              "Class selector 7";
          }
        }
      }
      leaf echo-interval {
        description
          "Seconds between sending keepalive messages on an idle path";
        type uint8 {
          range "60..200" {
            error-message "Invalid value for attribute 'echo-interval'. Valid values are in range:[60,200]";
          }
        }
      }
      leaf n3-requests {
        description
          "Total number of transmissions allowed for a control message";
        type uint8 {
          range "1..8" {
            error-message "Invalid value for attribute 'n3-requests'. Valid values are in range:[1,8]";
          }
        }
      }
      leaf temporary-rejection-guard-timer {
        description
          "Seconds before reattempt in case of temporary rejection\\. Value:[0.0-20.0] default:4.0 granularity:0.1";
        type string {
          pattern '((0.[0-9])|([0-9])|([1-9].[0-9])|(1[0-9])|(1[0-9].[0-9])|(20)|(20.0))' {
            error-message "Value must be a number from 0.0 to 20.0";
          }
        }
      }
      leaf temporary-rejection-retry {
        description
          "Max number of reattempts in case of temporary rejection\\. Value:[0-10] default:3";
        type uint8 {
          range "0..10" {
            error-message "Invalid value for attribute 'temporary-rejection-retry'. Valid values are in range:[0,10]";
          }
        }
      }
      leaf no-path-failure {
        description
          "Disable path failure";
        type empty;
      }
      leaf no-path-management {
        description
          "Disable path management";
        type empty;
      }
      container no-path-management-for-peer {
        description
          "Deactivate path management for peer";
        list address {
          max-elements 40;
          key "name";
          leaf name {
            description
              "Deactive path management for peer address";
            type eip-prefix;
          }
        }
      }
      leaf no-peer-restart {
        description
          "Disable path failure on recovery change";
        type empty;
      }
      leaf path-detection-sliding-window-size {
        description
          "Determine the range that indicates a signal race condition";
        type uint8 {
          range "0..128" {
            error-message "Invalid value for attribute 'path-detection-sliding-window-size'. Valid values are in range:[0,128]";
          }
        }
      }
      leaf t3-response-time {
        description
          "Seconds between control message retries";
        type string {
          pattern '(([1-9])|([1-2][0-9])|(30))' {
            error-message "Value must be a number from 1 to 30.";
          }
        }
      }
      leaf transaction-timeout {
        description
          "Seconds a GTP response entry is stored";
        type uint8 {
          range "5..60" {
            error-message "Invalid value for attribute 'transaction-timeout'. Valid values are in range:[5,60]";
          }
        }
      }
      list instance {
        max-elements 31;
        key "name";
        uses external-interface-type;
      }
      leaf identify-sender-by-source-address {
        description
          "Enable identification of sender by source address";
        type empty;
      }
      action gtp-path-status {
        description
          "Show status of GTP paths";
        output {
          leaf result {
            type string;
            mandatory true;
          }
        }
      }
    }
    container sx {
      status current {
        yexte:preliminary;
      }
      description
        "Sx interface settings";
      presence "sx need presence";
      uses sx-n4-interface-type;
    }
    action gtp-path-status {
      description
        "Show status of GTP paths";
      output {
        leaf result {
          type string;
          mandatory true;
        }
      }
    }
    container gn-c {
      description
        "Gn control plane interface";
      presence "gn-c need presence";
      leaf logical-interface {
        description
          "Reference to the logical-interface in [epg node logical-interface]";
        type leafref {
          path "/epg/node/logical-interface/name";
        }
        mandatory true;
        must 'not (/epg/node/logical-interface[name=current()]/ipv6-address)' {
          error-message "This interface does not support a logical interface with IPv6 address";
        }
      }
      leaf diffserv {
        description
          "DSCP (DiffServ Code Point) for GTP packets";
        type enumeration {
          enum af11 {
            description
              "Assured forwarding class 1, low drop precedence";
          }
          enum af12 {
            description
              "Assured forwarding class 1, medium drop precedence";
          }
          enum af13 {
            description
              "Assured forwarding class 1, high drop precedence";
          }
          enum af21 {
            description
              "Assured forwarding class 2, low drop precedence";
          }
          enum af22 {
            description
              "Assured forwarding class 2, medium drop precedence";
          }
          enum af23 {
            description
              "Assured forwarding class 2, high drop precedence";
          }
          enum af31 {
            description
              "Assured forwarding class 3, low drop precedence";
          }
          enum af32 {
            description
              "Assured forwarding class 3, medium drop precedence";
          }
          enum af33 {
            description
              "Assured forwarding class 3, high drop precedence";
          }
          enum af41 {
            description
              "Assured forwarding class 4, low drop precedence";
          }
          enum af42 {
            description
              "Assured forwarding class 4, medium drop precedence";
          }
          enum af43 {
            description
              "Assured forwarding class 4, high drop precedence";
          }
          enum ef {
            description
              "Expedited forwarding";
          }
          enum be {
            description
              "Best effort forwarding";
          }
          enum cs1 {
            description
              "Class selector 1";
          }
          enum cs2 {
            description
              "Class selector 2";
          }
          enum cs3 {
            description
              "Class selector 3";
          }
          enum cs4 {
            description
              "Class selector 4";
          }
          enum cs5 {
            description
              "Class selector 5";
          }
          enum cs6 {
            description
              "Class selector 6";
          }
          enum cs7 {
            description
              "Class selector 7";
          }
        }
      }
      leaf echo-interval {
        description
          "Seconds between sending keepalive messages on an idle path";
        type uint8 {
          range "60..200" {
            error-message "Invalid value for attribute 'echo-interval'. Valid values are in range:[60,200]";
          }
        }
      }
      leaf n3-requests {
        description
          "Total number of transmissions allowed for a control message";
        type uint8 {
          range "1..8" {
            error-message "Invalid value for attribute 'n3-requests'. Valid values are in range:[1,8]";
          }
        }
      }
      leaf no-nsapi-in-create-response {
        description
          "Does not send nsapi in pdp create response";
        type empty;
      }
      leaf no-path-failure {
        description
          "Disable path failure";
        type empty;
      }
      leaf no-path-management {
        description
          "Disable path management";
        type empty;
      }
      container no-path-management-for-peer {
        description
          "Deactivate path management for peer";
        list address {
          max-elements 40;
          key "name";
          leaf name {
            description
              "Deactive path management for peer address";
            type eip-prefix;
          }
        }
      }
      leaf no-peer-restart {
        description
          "Disable path failure on recovery change";
        type empty;
      }
      leaf no-evolved-arp {
        description
          "Do not handle evolved ARP in GTP messages";
        type empty;
      }
      leaf path-detection-sliding-window-size {
        description
          "Determine the range that indicates a signal race condition";
        type uint8 {
          range "0..128" {
            error-message "Invalid value for attribute 'path-detection-sliding-window-size'. Valid values are in range:[0,128]";
          }
        }
      }
      container allocation-retention-priority {
        description
          "Settings for mapping parameters of allocation retention priority";
        leaf high-priority {
          description
            "High priority value for allocation retention priority mapping";
          type uint8 {
            range "1..13" {
              error-message "Invalid value for attribute 'high-priority'. Valid values are in range:[1,13]";
            }
          }
        }
        leaf medium-priority {
          description
            "Medium priority value for allocation retention priority mapping";
          type uint8 {
            range "2..14" {
              error-message "Invalid value for attribute 'medium-priority'. Valid values are in range:[2,14]";
            }
          }
        }
      }
      leaf t3-response-time {
        description
          "Seconds between control message retries";
        type string {
          pattern '(([1-9])|([1-2][0-9])|(30))' {
            error-message "Value must be a number from 1 to 30.";
          }
        }
      }
      leaf transaction-timeout {
        description
          "Seconds a GTP response entry is stored";
        type uint8 {
          range "5..60" {
            error-message "Invalid value for attribute 'transaction-timeout'. Valid values are in range:[5,60]";
          }
        }
      }
      list instance {
        max-elements 31;
        key "name";
        uses external-interface-type;
      }
      action gtp-path-status {
        description
          "Show status of GTP paths";
        output {
          leaf result {
            type string;
            mandatory true;
          }
        }
      }
    }
    container ga {
      description
        "Ga interface";
      presence "ga need presence";
      leaf logical-interface {
        description
          "Reference to the logical-interface in [epg node logical-interface]";
        type leafref {
          path "/epg/node/logical-interface/name";
        }
        mandatory true;
        must 'not (/epg/node/logical-interface[name=current()]/ipv6-address)' {
          error-message "This interface does not support a logical interface with IPv6 address";
        }
      }
    }
  }

  grouping external-interface-type {
    leaf name {
      description
        "Interface instance ID";
      type uint8 {
        range "1..31" {
          error-message "Invalid value for attribute 'name'. Valid values are in range:[1,31]";
        }
      }
    }
    leaf logical-interface {
      description
        "Reference to the logical-interface in [epg node logical-interface]";
      type leafref {
        path "/epg/node/logical-interface/name";
      }
      mandatory true;
      must 'not (/epg/node/logical-interface[name=current()]/ipv6-address)' {
        error-message "This interface does not support a logical interface with IPv6 address";
      }
    }
  }

  grouping pgw-interface-ipv6-type {
    leaf mtu {
      description
        "IPv6 Maximum transmission unit";
      type uint16 {
        range "1280..3022" {
          error-message "Invalid value for attribute 'mtu'. Valid values are in range:[1280,3022]";
        }
      }
      default "1500";
    }
    leaf no-generate-udp-checksum {
      description
        "If enabled, turns off udp checksum generation for IPv6";
      type empty;
    }
    leaf no-validate-udp-checksum {
      description
        "If enabled, turns off udp checksum validation for IPv6";
      type empty;
    }
  }

  grouping sharedippool-type {
    leaf name {
      description
        "Shared IP pool name";
      type string {
        pattern '[._0-9A-Za-z-]{1,121}' {
          error-message "Must be a string of 121 or fewer characters and may contain letters, numbers, decimals and dashes.";
        }
      }
    }
    leaf status {
      description
        "Shared IP pool block status";
      type enumeration {
        enum unblocked {
          description
            "Unblock PDP to allocate the IP address from the whole shared IP pool";
        }
        enum blocked {
          description
            "Block PDP to allocate the IP address from the whole shared IP pool";
        }
      }
    }
    list address {
      max-elements 99;
      key "name";
      uses sharedippool-address-type;
    }
    list ipv6-address {
      max-elements 99;
      key "name";
      uses sharedippool-ipv6-address-type;
    }
    leaf address-reuse-time {
      description
        "Timeout for reuse of IP addresses, use 0 to disable address-reuse-time";
      type uint16 {
        range "0..1800" {
          error-message "Invalid value for attribute 'address-reuse-time'. Valid values are in range:[0,1800]";
        }
      }
    }
    leaf round-robin-allocation {
      description
        "Enable round robin IP address allocation from shared IP pool";
      type empty;
    }
    action statistics {
      description
        "Name of shared-ip-pool";
      output {
        leaf result {
          type string;
          mandatory true;
        }
      }
    }
  }

  grouping sharedippool-address-type {
    leaf priority {
      description
        "Priority specifying which of multiple configured addresses is to be used first\\. A value from 1 to 999999, where a lower value takes precedence.";
      type string {
        pattern '[1-9][0-9]*' {
          error-message "String must match: ^[1-9][0-9]*$'";
        }
        length "1..6";
      }
      default "999999";
    }
    leaf name {
      description
        "IPv4 address range";
      type eipv4-prefix-optional;
    }
    leaf subnet-name {
      description
        "Ipv4 range subnet-name";
      type string {
        pattern '[.0-9A-Za-z_-]*' {
          error-message "Must contain only letters, numbers, underscores or dashes";
        }
        length "1..64";
      }
    }
    leaf status {
      description
        "IPv4 address range block status";
      type enumeration {
        enum unblocked {
          description
            "Unblock PDP to allocate IPv4 address from the specific range in shared IP pool";
        }
        enum blocked {
          description
            "Block PDP to allocate IPv4 address from the specific range in shared IP pool";
        }
      }
    }
    action statistics {
      description
        "Name of shared-ip-pool corresponding to the address range";
      output {
        leaf result {
          type string;
          mandatory true;
        }
      }
    }
  }

  grouping sharedippool-ipv6-address-type {
    leaf priority {
      description
        "Priority specifying which of multiple configured addresses is to be used first\\. A value from 1 to 999999, where a lower value takes precedence.";
      type string {
        pattern '[1-9][0-9]*' {
          error-message "String must match: ^[1-9][0-9]*$'";
        }
        length "1..6";
      }
      default "999999";
    }
    leaf name {
      description
        "IPv6 address range";
      type eipv6-prefix-optional;
    }
    leaf subnet-name {
      description
        "Ipv6 range subnet-name";
      type string {
        pattern '[.0-9A-Za-z_-]*' {
          error-message "Must contain only letters, numbers, underscores or dashes";
        }
        length "1..64";
      }
    }
    leaf status {
      description
        "IPv6 address range block state";
      type enumeration {
        enum unblocked {
          description
            "Unblock PDP to allocate IPv6 address from the specific range in shared IP pool";
        }
        enum blocked {
          description
            "Block PDP to allocate IPv6 address from the specific range in shared IP pool";
        }
      }
    }
    action statistics {
      description
        "Name of shared-ip-pool corresponding to the IPv6 address range";
      output {
        leaf result {
          type string;
          mandatory true;
        }
      }
    }
  }

  grouping qos-control-type {
    list service-profile {
      max-elements 256;
      key "name";
      uses qos-control-service-profile-type;
    }
    leaf maximum-bit-rate-uplink {
      description
        "Maximum bitrate uplink";
      type uint32 {
        range "64..1000000000" {
          error-message "Invalid value for attribute 'maximum-bit-rate-uplink'. Valid values are in range:[64,1000000000]";
        }
      }
    }
    leaf maximum-bit-rate-downlink {
      description
        "Maximum bitrate downlink";
      type uint32 {
        range "64..1000000000" {
          error-message "Invalid value for attribute 'maximum-bit-rate-downlink'. Valid values are in range:[64,1000000000]";
        }
      }
    }
    leaf enforce-only-licensed-bitrate {
      description
        "Enforce only licensed bitrate";
      type empty;
    }
    container local {
      description
        "Local QoS control";
      presence "local need presence";
      list profile {
        description
          "Local QoS control profile";
        key "name";
        leaf name {
          description
            "Profile name";
          type common-string-id;
        }
        container unconditional {
          description
            "Unconditional QoS";
          presence "unconditional need presence";
          leaf default-bearer-qos-profile {
            description
              "Default bearer QoS profile identifier";
            type leafref {
              path "../../../../default-bearer-profile/name";
            }
          }
        }
        container conditional {
          description
            "Conditional QoS";
          presence "conditional need presence";
          list condition {
            description
              "Condition";
            key "name";
            leaf name {
              description
                "Condition name";
              type common-string-id;
            }
            leaf default-bearer-qos-profile {
              description
                "Default bearer QoS profile identifier";
              type leafref {
                path "../../../../../default-bearer-profile/name";
              }
              mandatory true;
            }
            leaf-list rat-type {
              description
                "Radio access technology (RAT) type";
              ordered-by user;
              type common-rat-type;
            }
            must 'rat-type' {
              error-message "RAT-type must be configured";
            }
            leaf priority {
              description
                "Priority of the condition, where a lower value has precedence";
              type uint8 {
                range "1..64" {
                  error-message "Invalid value for attribute 'priority'. Valid values are in range:[1,64]";
                }
              }
              mandatory true;
              must 'count(/epg/pgw/qos-control/local/profile[name=current()/../../../name]/conditional/condition[priority=current()])=1' {
                error-message "Priority must be unique among all conditions that are part of a local QoS control profile";
              }
            }
          }
        }
      }
    }
    container bearer-creation {
      description
        "Bearer Creation setting";
      leaf retry-delay {
        description
          "Delay time in seconds before retry";
        type uint16 {
          range "30..900" {
            error-message "Invalid value for attribute 'retry-delay'. Valid values are in range:[30,900]";
          }
        }
      }
      leaf max-retries {
        description
          "Max number of retries";
        type uint8 {
          range "0..16" {
            error-message "Invalid value for attribute 'max-retries'. Valid values are in range:[0,16]";
          }
        }
      }
    }
    list default-bearer-profile {
      max-elements 256;
      key "name";
      uses qos-control-default-bearer-profile-type;
    }
    leaf bitrate-rounding {
      description
        "Bitrate conversion setting";
      type enumeration {
        enum up {
          description
            "Round up when converting bitrates from bps to kbps";
        }
        enum down {
          description
            "Round down when converting bitrates from bps to kbps";
        }
      }
      default "down";
    }
    container operator-specific-qci {
      description
        "operator-specific QCI settings";
      leaf-list gbr-qci {
        description
          "Specify if a QCI is a GBR";
        type uint8 {
          range "128..254" {
            error-message "Invalid value for attribute 'gbr-qci'. Valid values are in range:[128,254]";
          }
        }
        max-elements 127;
      }
    }
    container update {
      leaf max-rate {
        description
          "maximum rate for for time-conditioned QoS triggered updates. Specified in updates per second per psc-instance";
        type uint32 {
          range "1..1000" {
            error-message "Invalid value for attribute 'max-rate'. Valid values are in range:[1,1000]";
          }
        }
      }
    }
  }

  grouping qos-control-default-bearer-profile-type {
    leaf name {
      description
        "Profile name";
      type string {
        length "1..63";
      }
    }
    leaf qos-class-identifier {
      description
        "Class identifier";
      type uint8 {
        range "5..254" {
          error-message "Invalid value for attribute 'qos-class-identifier'. Valid values are in range:[5,254]";
        }
      }
    }
    leaf aggregated-mbr-uplink {
      description
        "Bitrate uplink value in kbps";
      type uint32 {
        range "1..1000000000" {
          error-message "Invalid value for attribute 'aggregated-mbr-uplink'. Valid values are in range:[1,1000000000]";
        }
      }
    }
    leaf aggregated-mbr-downlink {
      description
        "Bitrate downlink value in kbps";
      type uint32 {
        range "1..1000000000" {
          error-message "Invalid value for attribute 'aggregated-mbr-downlink'. Valid values are in range:[1,1000000000]";
        }
      }
    }
    container allocation-retention-priority {
      description
        "Allocation retention priority setting";
      leaf priority-level {
        description
          "Priority level";
        type uint8 {
          range "1..15" {
            error-message "Invalid value for attribute 'priority-level'. Valid values are in range:[1,15]";
          }
        }
      }
      leaf pre-emption-capability {
        description
          "pre-emption capability";
        type enumeration {
          enum enable {
            description
              "Enable pre-emption capability";
          }
          enum disable {
            description
              "Disable pre-emption capability";
          }
        }
      }
      leaf pre-emption-vulnerability {
        description
          "pre-emption vulnerability";
        type enumeration {
          enum enable {
            description
              "Enable pre-emption vulnerability";
          }
          enum disable {
            description
              "Disable pre-emption vulnerability";
          }
        }
      }
    }
  }

  grouping qos-control-service-profile-type {
    leaf name {
      description
        "Profile name";
      type string {
        length "1..63";
      }
    }
    leaf qos-class-identifier {
      description
        "Class identifier";
      type uint8 {
        range "1..254" {
          error-message "Invalid value for attribute 'qos-class-identifier'. Valid values are in range:[1,254]";
        }
      }
    }
    leaf maximum-bit-rate-uplink {
      description
        "Maximum bitrate uplink value in kbps";
      type uint32 {
        range "1..1000000000" {
          error-message "Invalid value for attribute 'maximum-bit-rate-uplink'. Valid values are in range:[1,1000000000]";
        }
      }
    }
    leaf maximum-bit-rate-downlink {
      description
        "Maximum bitrate downlink value in kbps";
      type uint32 {
        range "1..1000000000" {
          error-message "Invalid value for attribute 'maximum-bit-rate-downlink'. Valid values are in range:[1,1000000000]";
        }
      }
    }
    leaf guaranteed-bit-rate-uplink {
      description
        "Guaranteed bitrate uplink value in kbps";
      type uint32 {
        range "1..1000000000" {
          error-message "Invalid value for attribute 'guaranteed-bit-rate-uplink'. Valid values are in range:[1,1000000000]";
        }
      }
    }
    leaf guaranteed-bit-rate-downlink {
      description
        "Guaranteed bitrate downlink value in kbps";
      type uint32 {
        range "1..1000000000" {
          error-message "Invalid value for attribute 'guaranteed-bit-rate-downlink'. Valid values are in range:[1,1000000000]";
        }
      }
    }
    container allocation-retention-priority {
      description
        "Allocation retention priority setting";
      must '../../service-profile[name=current()/../name]/qos-class-identifier' {
        error-message "ARP can only be configured together with QCI";
      }
      presence "allocation-retention-priority need presence";
      leaf priority-level {
        description
          "Priority level";
        type uint8 {
          range "1..15" {
            error-message "Invalid value for attribute 'priority-level'. Valid values are in range:[1,15]";
          }
        }
      }
      leaf pre-emption-capability {
        description
          "pre-emption capability";
        type enumeration {
          enum enable {
            description
              "Enable pre-emption capability";
          }
          enum disable {
            description
              "Disable pre-emption capability";
          }
        }
      }
      leaf pre-emption-vulnerability {
        description
          "pre-emption vulnerability";
        type enumeration {
          enum enable {
            description
              "Enable pre-emption vulnerability";
          }
          enum disable {
            description
              "Disable pre-emption vulnerability";
          }
        }
      }
    }
  }

  grouping policy-control-type {
    container revalidation {
      description
        "Revalidation settings";
      leaf max-rate {
        description
          "Maximum rate the sessions are revalidated at\\. The value is in percent of the DAS maximum request rate";
        type uint8 {
          range "1..80" {
            error-message "Invalid value for attribute 'max-rate'. Valid values are in range:[1,80]";
          }
        }
      }
      leaf max-deviation {
        description
          "Maximum time ahead of the specified revalidation time the node is allowed to perform the revalidation\\. The value is in minutes";
        type uint8 {
          range "1..60" {
            error-message "Invalid value for attribute 'max-deviation'. Valid values are in range:[1,60]";
          }
        }
      }
      leaf margin {
        description
          "Margin added in calculation of revalidation start time\\. The value is in seconds";
        type uint8 {
          range "1..60" {
            error-message "Invalid value for attribute 'margin'. Valid values are in range:[1,60]";
          }
        }
      }
    }
    list gx-failure-profile {
      key "name";
      uses gx-failure-profile-type;
    }
    list gx-profile {
      description
        "Settings for standard and enhanced Gx";
      uses gx-profile-type;
      key "name";
    }
    list pcc-rule-template {
      description
        "Predefined PCC rule template";
      key "name";
      leaf name {
        description
          "Template name";
        type common-string-id;
      }
      uses pcc-rule-type;
    }
    list pcc-rule-group-template {
      description
        "Predefined PCC rule group template";
      key "name";
      leaf name {
        description
          "Template name";
        type common-string-id;
      }
      uses pcc-rule-group-late-verify-reference-type;
    }
    list rule-scope {
      description
        "Policy control rule scope";
      key "name";
      leaf name {
        description
          "Rule scope name";
        type common-string-id;
      }
      list pcc-rule {
        description
          "Predefined PCC rule";
        key "name";
        leaf name {
          description
            "Rule name";
          type common-string-id;
        }
        uses pcc-rule-type;
        leaf-list template {
          description
            "Template";
          type leafref {
            path "../../../pcc-rule-template/name";
          }
          ordered-by user;
        }
      }
      list pcc-rule-group {
        description
          "Predefined PCC rule group";
        key "name";
        leaf name {
          description
            "Group name";
          type common-string-id;
        }
        uses pcc-rule-group-type;
        leaf-list template {
          description
            "Template";
          type leafref {
            path "../../../pcc-rule-group-template/name";
          }
          ordered-by user;
        }
      }
    }
    container local {
      description
        "Local policy control";
      presence "local need presence";
      list profile {
        description
          "Profile";
        key "name";
        leaf name {
          description
            "Profile name";
          type common-string-id;
        }
        container unconditional {
          description
            "Unconditional rule";
          presence "unconditional need presence";
          leaf-list pcc-rule {
            description
              "PCC rule name";
            type common-string-id;
            min-elements 1;
          }
          leaf-list pcc-rule-group {
            description
              "PCC rule group name";
            type common-string-id;
          }
        }
        container conditional {
          description
            "Conditional rule";
          presence "conditional need presence";
          list action {
            description
              "Action";
            key "name";
            leaf name {
              description
                "Action name";
              type common-string-id;
            }
            leaf-list pcc-rule {
              description
                "PCC rules which will become active";
              ordered-by user;
              type common-string-id;
            }
            leaf-list pcc-rule-group {
              description
                "PCC rule groups which will become active";
              ordered-by user;
              type common-string-id;
            }
            must 'pcc-rule-group or pcc-rule' {
              error-message "at least one pcc-rule or pcc-rule-group be configured";
            }
          }
          list condition {
            description
              "Condition";
            key "name";
            leaf name {
              description
                "Condition name";
              type common-string-id;
            }
            leaf action {
              description
                "Action for condition";
              type common-string-id;
              mandatory true;
              must '../../action[name=current()]' {
                error-message "action must be configured under [epg pgw policy-control local profile conditional action]";
              }
            }
            leaf-list rat-type {
              description
                "Radio access technology (RAT) type";
              ordered-by user;
              type common-rat-type;
            }
            leaf service-control-odb {
              description
                "Service control (ODB) type";
              type common-service-control-odb;
            }
            must 'rat-type or service-control-odb' {
              error-message "RAT-type or Service-control-odb must be configured";
            }
          }
        }
      }
    }
    list application {
      description
        "Application identifier";
      key "name";
      leaf name {
        description
          "Application name";
        type common-string-id;
      }
      container uplink-filter {
        description
          "Uplink filters for a dedicated bearer";
        list filter {
          key "name";
          uses flow-filter-type;
        }
      }
    }
  }

  grouping gx-failure-profile-type {
    leaf name {
      description
        "Gx failure profile name";
      type string {
        length "1..128";
      }
    }
    container session-handling {
      description
        "Session handling settings";
      leaf default-ccr-initial-failure-action {
        description
          "Action to be taken by default for CCR-Initial failures";
        type leafref {
          path "../action/name";
        }
      }
      leaf default-ccr-update-failure-action {
        description
          "Action to be taken by default for CCR-Update failures";
        type leafref {
          path "../action/name";
        }
      }
      leaf server-restart-action {
        description
          "Action to be taken for all the sessions affected by a server restart";
        type leafref {
          path "../action/name";
        }
      }
      leaf connection-failure-action {
        description
          "Action to be taken for all the sessions affected by a connection failure";
        type leafref {
          path "../action/name";
        }
      }
      list condition {
        must 'message-type' {
          error-message "message-type is mandatory";
        }
        key "name";
        uses gx-failure-condition-type;
      }
      list action {
        key "name";
        uses gx-failure-action-type;
      }
    }
    container pcc-rule-handling {
      description
        "PCC rule failure handling settings";
      leaf default-installation-failure-action {
        description
          "Action to be taken by default for PCC rule installation failures";
        type leafref {
          path "../action/name";
        }
      }
      leaf default-modification-failure-action {
        description
          "Action to be taken by default for PCC rule modification failures";
        type leafref {
          path "../action/name";
        }
      }
      list action {
        description
          "Specify a set of possible failure actions";
        key "name";
        uses pcc-rule-failure-action-type;
      }
      list condition {
        description
          "Specify the request failures that trigger an associated action";
        key "name";
        uses pcc-rule-failure-condition-type;
      }
    }
  }

  grouping pcc-rule-group-type {
    leaf description {
      description
        "Free format description";
      type string;
    }
    leaf-list pcc-rule {
      description
        "PCC rule";
      type leafref {
        path "../../pcc-rule/name";
      }
    }
  }

  grouping pcc-rule-group-late-verify-reference-type {
    leaf description {
      description
        "Free format description";
      type string;
    }
    leaf-list pcc-rule {
      description
        "PCC rule";
      type common-string-id;
      min-elements 1;
    }
  }

  grouping pcc-rule-type {
    leaf description {
      description
        "Free format description";
      type string;
    }
    leaf application {
      description
        "Identifier referencing an operator defined application definition";
      type common-string-id;
    }
    leaf rating-group {
      description
        "Identifier for service-based charging purposes";
      type uint32;
    }
    leaf service-id {
      description
        "Identifier for service-based reporting purposes";
      type uint32;
    }
    container service-id-level-reporting {
      description
        "Service level reporting settings";
      container online {
        description
          "Online service level reporting settings";
        choice selection {
          leaf enable {
            description
              "Enable online service level reporting for this rule";
            type empty;
          }
          leaf disable {
            description
              "Disable online service level reporting for this rule";
            type empty;
          }
        }
      }
      container offline {
        description
          "Offline service level reporting settings";
        choice selection {
          leaf enable {
            description
              "Enable offline service level reporting for this rule";
            type empty;
          }
          leaf disable {
            description
              "Disable offline service level reporting for this rule";
            type empty;
          }
        }
      }
    }
    leaf precedence {
      description
        "Rule precedence";
      type uint32;
    }
    leaf monitoring-key {
      description
        "Identifier for usage monitoring and reporting";
      type common-string-id;
    }
    leaf network-instance {
      description
        "Identifier for network routing instance";
      type common-string-id;
    }
    container online {
      description
        "Online charging settings";
      leaf enable {
        description
          "Enable online charging for this rule";
        type empty;
      }
      leaf disable {
        description
          "Disable online charging for this rule";
        type empty;
      }
    }
    container offline {
      description
        "Offline charging settings";
      leaf disable {
        description
          "Disable offline charging for this rule";
        type empty;
      }
    }
    container service-qos {
      description
        "Service QoS";
      leaf profile {
        description
          "Service QoS profile identifier";
        type leafref {
          path "/epg/pgw/qos-control/service-profile/name";
        }
      }
      leaf shared-profile {
        description
          "Shared service QoS profile identifier";
        type leafref {
          path "/epg/pgw/qos-control/service-profile/name";
        }
      }
    }
    container default-bearer-qos {
      description
        "Default bearer QoS";
      presence "default-bearer-qos need presence";
      leaf profile {
        description
          "Default bearer QoS profile identifier";
        type leafref {
          path "/epg/pgw/qos-control/default-bearer-profile/name";
        }
        mandatory true;
      }
      leaf priority {
        description
          "Default bearer QoS profile priority";
        type uint32 {
          range "1..4294967295" {
            error-message "Invalid value for attribute 'priority'. Valid values are in range:[1,4294967295]";
          }
        }
        mandatory true;
      }
    }
    container service-chain {
      description
        "Service chain identifiers for traffic forwarding";
      leaf uplink {
        description
          "Service chain identifier for uplink traffic";
        type common-string-id;
      }
      leaf downlink {
        description
          "Service chain identifier for downlink traffic";
        type common-string-id;
      }
    }
    leaf gate-status {
      description
        "Set the gate for the PCC rule";
      type enumeration {
        enum open {
          description
            "Allow both uplink and downlink traffic";
        }
        enum closed {
          description
            "Don't allow any traffic";
        }
        enum open-uplink {
          description
            "Allow only uplink traffic";
        }
        enum open-downlink {
          description
            "Allow only downlink traffic";
        }
      }
    }
    leaf content-enrichment-rule {
      description
        "Rule to be applied for content enrichment";
      type leafref {
        path "/epg/pgw/packet-enforcement/content-enrichment/rule/name";
      }
    }
    leaf traffic-redirection-rule {
      description
        "Rule to be applied for traffic redirection";
      type leafref {
        path "/epg/pgw/packet-enforcement/traffic-redirection/rule/name";
      }
    }
    leaf-list user-plane-rule {
      description
        "Predefined user plane rule";
      type string {
        length "1..255";
      }
    }
    leaf bearer-binding-verification {
      description
        "Bearer binding verification";
      type enumeration {
        enum enable {
          description
            "Enable bearer binding verification in uplink direction";
        }
        enum disable {
          description
            "Disable bearer binding verification in uplink direction";
        }
      }
      status current {
        yexte:preliminary;
      }
    }
    leaf flow-direction {
      description
        "Set the flow direction for the PCC rule";
      type enumeration {
        enum uplink {
          description
            "Match only uplink traffic";
        }
        enum downlink {
          description
            "Match only downlink traffic";
        }
        enum bidirectional {
          description
            "Match uplink and downlink traffic";
        }
      }
      status current {
        yexte:preliminary;
      }
    }
  }

  grouping gx-failure-condition-type {
    leaf name {
      description
        "Failure condition name";
      type string;
    }
    leaf priority {
      description
        "Priority value for the request failure condition, where a lower value has precedence";
      type uint8 {
        range "1..128" {
          error-message "Invalid value for attribute 'priority'. Valid values are in range:[1,128]";
        }
      }
      mandatory true;
      must 'count(../../condition[priority=current()])=1' {
        error-message "Priority must be unique among all session handling conditions part of a gx failure profile";
      }
    }
    leaf action {
      description
        "Action to be taken for this condition";
      mandatory true;
      type leafref {
        path "../../action/name";
      }
    }
    list message-type {
      description
        "Message type for which the condition applies";
      key "name";
      leaf name {
        description
          "Message type name";
        type enumeration {
          enum ccr-initial {
            description
              "Credit Control Request Initial";
          }
          enum ccr-update {
            description
              "Credit Control Request Update";
          }
        }
      }
      leaf timeout {
        description
          "Condition applies when message times out";
        type empty;
      }
      leaf connection-failure {
        description
          "Condition applies when the request cannot be sent due to a connection failure";
        type empty;
      }
      leaf-list result-code {
        description
          "Result code or result code range for which the condition applies";
        type string {
          pattern '[0-9]{1,10}([-][0-9]{1,10})?' {
            error-message "Must be a result code or a range of result codes.";
          }
          length "1..64";
        }
        max-elements 64;
      }
      leaf-list experimental-result-code {
        description
          "Vendor id followed by ':' and experimental result code or result code range for which the condition applies.";
        type string {
          pattern '((3gpp)|(3gpp2)|(ericsson)|([1-9][0-9]{0,9}))[:][0-9]{1,10}([-][0-9]{1,10})?' {
            error-message "Must be a vendor id (<3gpp>|<3gpp2>|<ericsson>|<1-4294967295>) and ':' followed by result code or a range of result codes.";
          }
          length "1..64";
        }
        max-elements 64;
      }
    }
  }

  grouping pcc-rule-failure-action-type {
    leaf name {
      description
        "Failure action name";
      type string {
        length "1..64";
      }
      must '(../keep) or (../remove)' {
        error-message "When configuring an action, either 'keep' or 'remove' must be configured";
      }
    }
    choice action {
      container keep {
        description
          "Keep the old version of the PCC rule on failure";
        presence "keep need presence";
      }
      container remove {
        description
          "Remove the PCC rule on failure";
        presence "remove need presence";
      }
    }
    leaf rule-failure-code {
      description
        "rule-failure-code value to send to PCRF";
      type union {
        type enumeration {
          enum gw-pcef-malfunction {
            description
              "PCC rule could not be successfully installed, activated or enforced due to GW/PCEF malfunction";
          }
          enum resources-limitation {
            description
              "PCC rule could not be successfully installed, activated or enforced due to a limitation of resources at the PCEF";
          }
          enum max-nr-bearers-reached {
            description
              "PCC rule could not be successfully installed, activated or enforced due to the fact that the maximum number of bearers has been reached for the ip-can session";
          }
          enum resource-allocation-failure {
            description
              "PCC rule could not be successfully installed or maintained since the bearer establishment/modification failed, or the bearer was released";
          }
          enum incorrect-flow-information {
            description
              "PCC rule could not be successfully installed or modified at the PCEF because the provided flow information is not supported by the network";
          }
          enum ps-to-cs-handover {
            description
              "PCC rule could not be maintained because of PS to CS handover";
          }
          enum no-bearer-bound {
            description
              "Indicate that there is no ip-can bearer which the PCEF can bind the PCC rule(s) to";
          }
          enum filter-restrictions {
            description
              "Indicate that the flow-description AVP(s) cannot be handled by the PCEF because restrictions was not met";
          }
          enum an-gw-failed {
            description
              "Indicate that the an-gateway has failed and that the PCRF should refrain from sending policy decisions to the PCEF until it is informed that the s-gw has been recovered";
          }
        }
        type rule-failure-code-number-choice;
      }
    }
  }

  grouping pcc-rule-failure-condition-type {
    leaf name {
      description
        "PCC rule condition name";
      type string;
    }
    leaf priority {
      description
        "Priority value for the condition, where a lower value has precedence";
      type uint8 {
        range "1..64" {
          error-message "Invalid value for attribute 'priority'. Valid values are in range:[1,64]";
        }
      }
      mandatory true;
      must 'count(../../condition[priority=current()])=1' {
        error-message "Priority must be unique among all PCC rule handling conditions part of a gx failure profile";
      }
    }
    leaf action {
      description
        "Action to be taken for this PCC rule condition";
      type leafref {
        path "../../action/name";
      }
      mandatory true;
    }
    list operation-type {
      description
        "Operation type for which the PCC rule condition applies";
      key "name";
      leaf name {
        description
          "Operation type name";
        type enumeration {
          enum installation {
            description
              "Installation of a new PCC rule";
          }
          enum modification {
            description
              "Modification of an existing PCC rule";
          }
        }
        must '(../gtpv1-cause) or (../gtpv2-cause) or (../gtpv2-ran-cause) or (../gtpv2-nas-cause)' {
          error-message "When configuring operation-type, at least one cause must be configured";
        }
      }
      leaf-list gtpv1-cause {
        description
          "Cause code for GTPv1";
        type string {
          pattern '((129)|(1[3-9][0-9])|(2[0-4][0-9])|(25[0-5]))(-((129)|(1[3-9][0-9])|(2[0-4][0-9])|(25[0-5])))?' {
            error-message "Must be a number from 129 to 255 or a range";
          }
          length "1..64";
        }
      }
      leaf-list gtpv2-cause {
        description
          "Cause code for GTPv2";
        type string {
          pattern '((6[4-9])|([7-9][0-9])|(1[0-9][0-9])|(2[0-4][0-9])|(25[0-5]))(-((6[4-9])|([7-9][0-9])|(1[0-9][0-9])|(2[0-4][0-9])|(25[0-5])))?' {
            error-message "Must be a number from 64 to 255 or a range";
          }
          length "1..64";
        }
      }
      leaf-list gtpv2-ran-cause {
        description
          "Radio Network Layer cause code for GTPv2";
        type string {
          pattern '(([0-9]([0-9]?))|1[0-9]{2}|2[0-4][0-9]|25[0-5])(-(([0-9]([0-9]?))|1[0-9]{2}|2[0-4][0-9]|25[0-5]))?' {
            error-message "Must be a number from 0 to 255 or a range";
          }
          length "1..64";
        }
      }
      leaf-list gtpv2-nas-cause {
        description
          "NAS cause code for GTPv2";
        type string {
          pattern '(([0-9]([0-9]?))|1[0-9]{2}|2[0-4][0-9]|25[0-5])(-(([0-9]([0-9]?))|1[0-9]{2}|2[0-4][0-9]|25[0-5]))?' {
            error-message "Must be a number from 0 to 255 or a range";
          }
          length "1..64";
        }
      }
    }
  }

  grouping gx-failure-action-type {
    leaf name {
      description
        "Failure action name";
      type string {
        length "1..64";
      }
    }
    choice action {
      container terminate {
        description
          "Terminate the user session";
        presence "terminate need presence";
        leaf send-ccr-termination {
          description
            "Gracefully terminate the Gx+ PCC session";
          type empty;
        }
        leaf send-reactivation-requested {
          description
            "Use cause 'Reactivation Requested' in the GTP deletion message";
          type empty;
        }
        leaf gtpv1-cause {
          description
            "Cause code used for the GTPv1 rejection";
          type uint8 {
            range "192..240" {
              error-message "Invalid value for attribute 'gtpv1-cause'. Valid values are in range:[192,240]";
            }
          }
          default "204";
        }
        leaf gtpv2-cause {
          description
            "Cause code used for the GTPv2 rejection";
          type uint8 {
            range "64..239" {
              error-message "Invalid value for attribute 'gtpv2-cause'. Valid values are in range:[64,239]";
            }
          }
          default "72";
        }
      }
      container continue {
        description
          "Continue the user session";
        presence "continue need presence";
        container reestablish {
          description
            "Reestablish the Gx+ PCC session";
          must 'not (../retain)' {
            error-message "Reestablish is not compatible with Retain";
          }
          presence "reestablish need presence";
        }
        container retain {
          description
            "Retain the Gx+ PCC session";
          presence "retain need presence";
        }
        container local-policy-control {
          description
            "Use local policies";
          must 'not (../retain)' {
            error-message "local-policy-control is not compatible with Retain";
          }
          presence "local-policy-control need presence";
          leaf profile {
            description
              "Local policy control profile used when PCRF becomes unavailable";
            type common-string-id;
            must '/epg/pgw/policy-control/local/profile[name=current()]' {
              error-message "local profile must be configured under [epg pgw policy-control local profile]";
            }
          }
        }
      }
    }
  }

  grouping user-plane-pool-type {
    list pool {
      key "name";
      max-elements 256;
      leaf name {
        description
          "User plane pool name";
        type string;
      }
      must 'node-name' {
        error-message "node-name must be configured under [epg pgw user-plane-pool pool]";
      }
      list node-name {
        max-elements 256;
        key "name";
        uses user-plane-pool-node-type;
        leaf weight {
          description
            "Enable configure weight-factors for one user plane node";
          type uint8 {
            range "1..10" {
              error-message "Invalid value for attribute 'weight'. Valid values are in range:[1,10]";
            }
          }
          default "1";
        }
        leaf priority {
          description
            "Enable configure priority for one user plane node";
          type uint8 {
            range "1..255" {
              error-message "Invalid value for attribute 'priority'. Valid values are in range:[1,255]";
            }
          }
          default "1";
        }
      }
      list data-network {
        description
          "Data network profile";
        max-elements 9999;
        key "name";
        leaf name {
          type leafref {
            path "../../../../apn/name";
          }
        }
        container radius {
          presence "radius need presence";
          must "(/epg/pgw/apn[name=current()/../name]/radius/connect = 'upf-forwarding')" {
            error-message "radius connect must be upf-forwarding to configure radius under 'epg pgw user-plane-pool pool data-network'.";
          }
          leaf server-profile {
            type leafref {
              path "/epg/pgw/radius/server-profile/name";
            }
            mandatory true;
          }
          leaf client-address {
            type inet:ip-address;
            mandatory true;
          }
          leaf network-instance {
            type string;
            mandatory true;
          }
          leaf property-profile {
            type leafref {
              path "/epg/pgw/radius/property-profile/name";
            }
          }
          action statistics {
            description
              "Show RADIUS statistics";
            output {
              leaf result {
                type string;
                mandatory true;
              }
            }
          }
        }
      }
    }
  }

  grouping user-plane-pool-node-type {
    leaf name {
      type string;
      /*type leafref {
        path "../../../../user-plane/node-name/name";
      }*/
    }
  }

  grouping user-plane-selection-type {
    leaf default-pool {
      description
        "Default user plane pool";
      type leafref {
        path "../../user-plane-pool/pool/name";
      }
      mandatory true;
    }
    list selection-condition {
      key "name";
      max-elements 256;
      ordered-by user;
      uses selection-condition-type;
    }
  }

  grouping selection-condition-type {
    status current {
      yexte:preliminary;
    }
    leaf name {
      description
        "Selection condition name";
      type string {
        pattern '[.0-9A-Za-z_-]*' {
          error-message "Must contain only letters, numbers, underscores or dashes";
        }
        length "1..64";
      }
    }
    leaf-list data-network {
      max-elements 3000;
      type leafref {
        path "/epg/pgw/apn/name";
      }
    }
    leaf-list area-id {
      max-elements 500;
      type leafref {
        path "/epg/pgw/location/area/name";
      }
    }
    leaf selected-pool {
      description
        "Selected pool name";
      type leafref {
        path "../../../user-plane-pool/pool/name";
      }
    }
  }

  container epg {
    description
      "EPG settings";
    presence "epg need presence";
    container sgw {
      presence "sgw need presence";
      description
        "SGW settings";
      uses sgw-type;
    }
    container pgw {
      presence "pgw need presence";
      description
        "PGW settings";
      uses pgw-type;
    }
    container node {
      description
        "Node settings";
      presence "node need presence";
      uses node-type;
    }
    container user-plane {
      presence "upf need presence";
      description
        "User Plane Function settings (SGW-U, PGW-U, TDF-U, UPF)";
      uses user-plane-type;
    }
    action version {
      description
        "Show EPG software version";
      input {
        leaf level {
          description
            "EPG software version level";
          type enumeration {
            enum brief {
              description
                "Show brief version information";
            }
            enum detail {
              description
                "Show detailed version information";
            }
          }
          mandatory true;
        }
      }
      output {
        leaf result {
          type string;
          mandatory true;
        }
      }
    }
  }
}
