/*
    This is written manually.
*/

module ericsson-ospf-dev-ipr {
  yang-version "1.1";

  namespace "urn:rdns:com:ericsson:oammodel:ericsson-ospf-dev-ipr";

  prefix "ospfdevipr";

  import ericsson-contexts-ipos {
    prefix "ctxsipos";
  }

  import ericsson-context-ipos {
    prefix "ctxipos";
  }

  import ericsson-ospf-ipos {
    prefix "ospfipos";
  }
  import ietf-interfaces {
    prefix "if";
  }

  import ericsson-yang-extensions {
    prefix "yexte";
  }

  organization "Ericsson AB";
  contact "iposcli@ericsson.com";

  description
    "ericsson-system-dev-ipr
     Copyright (c) 2017 Ericsson AB.
     All rights reserved";

  revision "2019-07-04" {
    description
      "Update yang version 1.0 to 1.1";
    reference
      "rfc7950";
    yexte:version "1";
    yexte:release "0";
    yexte:correction "1";
  }

  revision "2017-12-29" {
    description   "initial revision";
    reference "rfc6020.txt.";
    yexte:version "1";
    yexte:release "0";
    yexte:correction "0";
  }

  deviation "/ctxsipos:contexts/ctxipos:context/ctxipos:router/ospfipos:ospf/ospfipos:area/ospfipos:interface" {
  deviate not-supported;
}

}
