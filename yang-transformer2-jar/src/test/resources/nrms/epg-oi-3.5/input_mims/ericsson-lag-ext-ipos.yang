module ericsson-lag-ext-ipos {
  yang-version "1.1";

  namespace "urn:rdns:com:ericsson:oammodel:ericsson-lag-ext-ipos";

  prefix "lagxipos";

  import ericsson-context-ipos {
    prefix "ctxipos";
  }

  import ietf-interfaces {
    prefix "if";
  }

  import iana-if-type {
    prefix "ianaift";
  }

  import ericsson-contexts-ipos {
    prefix "ctxsipos";
  }

  import ietf-yang-types {
    prefix "yang";
  }

  import ericsson-mirror-policy-ipos {
    prefix "mirrorpolicyipos";
  }

  import ericsson-yang-extensions {
    prefix "yexte";
  }

  organization
    "Ericsson AB";

  contact
    "Web:   <http://www.ericsson.com>";

  description
    "ericsson-lag-ext-ipos
     Copyright (c) 2019 Ericsson AB.
     All rights reserved";

  revision "2019-09-09" {
    description
      "delete useless condition";
    reference
      "rfc7950";
    yexte:version "1";
    yexte:release "1";
    yexte:correction "3";
  }

  revision "2019-07-04" {
    description
      "Update yang version 1.0 to 1.1";
    reference
      "rfc7950";
    yexte:version "1";
    yexte:release "1";
    yexte:correction "2";
  }

  revision "2019-03-27" {
    description
      "remove the test condition of svin-id";
    reference
      "rfc6020";
    yexte:version "1";
    yexte:release "1";
    yexte:correction "1";
  }

  revision "2018-09-04" {
    description
      "Add obsolete/deprecated/preliminary label to the
       description of the obsolete/deprecated/preliminary node";
    reference
      "rfc6020";
    yexte:version "1";
    yexte:release "1";
    yexte:correction "0";
  }

  revision "2018-06-19" {
    description
      "Change the description of key word.";
    reference
      "rfc6020";
    yexte:version "1";
    yexte:release "0";
    yexte:correction "5";
  }

  revision "2018-06-05" {
    description
      "Refine format for yang statements: when, must, path,
       pattern, augment, etc.";
    reference
      "rfc6020";
    yexte:version "1";
    yexte:release "0";
    yexte:correction "4";
  }

  revision "2018-04-19" {
    description
      "Add default value for period timeout as short,replace
       immediate with short-immediate,the new leaf
       short-immediate adds default value.";
    reference
      "rfc6020";
    yexte:version "1";
    yexte:release "0";
    yexte:correction "3";
  }

  revision "2018-03-20" {
    description
      "change range for minimum-links/maximum-links";
    reference
      "rfc6020";
    yexte:version "1";
    yexte:release "0";
    yexte:correction "2";
  }

  revision "2018-03-08" {
    description
      "add when sentences for POS type";
    reference
      "rfc6020";
    yexte:version "1";
    yexte:release "0";
    yexte:correction "1";
  }

  revision "2017-07-15" {
    description
      "IPOS-11938 New command for subscribe micro-bfd";
    reference
      "rfc6020";
    yexte:version "1";
    yexte:release "0";
    yexte:correction "0";
  }

  revision "2017-07-06" {
    description
      "add new container 'multi-chassis'in 'lag-grp'.";
    reference
      "rfc6020";
  }

  revision "2017-06-27" {
    description
      "add new container 'mirror'in 'lag-grp'.";
    reference
      "rfc6020";
  }

  revision "2017-04-13" {
    description
      "add new command 'track'.";
    reference
      "rfc6020";
  }

  revision "2017-02-20" {
    description
      "Need to support the parameter '9100' in the command
       'dot1q tunnel ethertype' under lag.";
    reference
      "rfc6020";
  }

  revision "2017-02-20" {
    description
      "add new command protect-group.";
    reference
      "rfc6020";
  }

  revision "2016-12-30" {
    description
      "For Side Effect difference modification.";
    reference
      "rfc6020";
  }

  revision "2016-03-29" {
    description
      "For CLI2Yang models data node sequence change.";
    reference
      "rfc6020";
  }

  revision "2015-12-07" {
    description
      "initial revision";
    reference
      "rfc6020";
  }

  feature economical {
    description
      "This feature indicates that the device supports
       economical in lag.";
  }

  feature link-pinning {
    description
      "This feature indicates that the device supports
       link-pinning in lag.";
  }

  feature load-balance {
    description
      "This feature indicates that the device supports
       load-balance in lag.";
  }

  grouping lag-grp {
    description
      "Unified link group configuration mode";
    /*
    mirror { <policy (mirror-name) { in | out } [ source-tag {
     dot1q (tag-id) | dot1ad (tag-id)}  ]> }
    */
    container mirror {
      description
        "Configure mirror policy or destination";
      list policy {
        key "policy-choice";
        max-elements 2;
        description
          "Configure mirror policy";
        leaf policy-choice {
          type enumeration {
            enum in {
              value 0;
              description
                "Inbound mirror policy";
            }
            enum out {
              value 1;
              description
                "Outbound mirror policy";
            }
          }
          description
            "Policy choice";
        }
        leaf mirror-name {
          type leafref {
            path "/ctxsipos:contexts/mirrorpolicyipos:"
            + "mirror-policy/mirrorpolicyipos:mirror-polname";
          }
          mandatory true;
          description
            "Mirror policy name";
        }
        container source-tag {
          description
            "Configure mirror source tag";
          choice source-tag {
            description
              "Ethernet type";
            case dot1q {
              leaf dot1q {
                type uint16 {
                  range "1..4094";
                }
                description
                  "Configure Dot1q vlan id";
              }
            }
            case dot1ad {
              leaf dot1ad {
                type uint16 {
                  range "1..4094";
                }
                description
                  "Configure Dot1ad vlan id";
              }
            }
          }
        }
      }
    }
    /*
    bind interface (intf-name) (intf-ctx)
    */
    container bind-interface {
      presence "";
      description
        "Bind an interface to the link group";
      leaf intf-name {
        type leafref {
          path "/if:interfaces/if:interface/if:name";
        }
        mandatory true;
        description
          "Interface name";
      }
      leaf intf-ctx {
        type leafref {
          path "/ctxsipos:contexts/ctxipos:context/ctxipos:"
          + "context-name";
        }
        mandatory true;
        description
          "Context name";
      }
    }
    /*
    mac-address { auto | port | mac-addr }
    */
    container mac-address {
      description
        "Configure MAC address";
      choice mac-address {
        default auto;
        description
          "";
        case auto {
          leaf auto {
            type empty;
            description
              "Specify software generated link group Source MAC
               address";
          }
        }
        case port {
          leaf port {
            type empty;
            description
              "Specify MAC address is to be inherited from a
               constituent port";
          }
        }
        case mac-addr {
          leaf mac-addr {
            type yang:mac-address;
            description
              "Source MAC Address";
          }
        }
      }
    }
    /*
    maximum-links (lag-num)
    */
    leaf maximum-links {
      type uint8 {
        range "1..16";
      }
      default "8";
      description
        "Specify the maximum number of active links in the
         group";
    }
    /*
    load-balance
    */
    leaf load-balance {
      if-feature load-balance;
      type boolean;
      default "true";
      description
        "Enable/Disable load-balance";
    }
    /*
    protect-group { incoming-port | round-robin }
    */
    container protect-group {
      description
        "Specify the protect group type";
      choice protect-group {
        default round-robin;
        description
          "";
        case incoming-port {
          leaf incoming-port {
            type empty;
            description
              "Incoming port";
          }
        }
        case round-robin {
          leaf round-robin {
            type empty;
            description
              "Round robin";
          }
        }
      }
    }
    /*
    minimum-links (uplinks-num)
    */
    leaf minimum-links {
      type uint8 {
        range "1..16";
      }
      default "1";
      description
        "Minimum number of link-ups required for a group to be
         up";
    }
    /*
    multi-chassis [ revertive hold-time (time-val) ]
    */
    container multi-chassis {
      presence "";
      description
        "Configure multi-chassis mode for this link group";
      container revertive {
        description
          "Configure multi-chassis revertive mode";
        leaf hold-time {
          type uint16 {
            range "0..1024";
          }
          description
            "Configure hold time to wait before trying to revert
             (in seconds)";
        }
      }
    }
    /*
    track { (track-name) <action compute-min-link> [ log ] |
     system-icr-traffic-reroute <action switch-lacp-selected-
     state> [ log ] }
    */
    container track {
      description
        "Configure link group track object";
      container track-name {
        presence "";
        description
          "Container track name";
        leaf track-name {
          type string;
          mandatory true;
          description
            "Object name";
        }
        leaf action-compute-min-link {
          type empty;
          mandatory true;
          description
            "Reevaluate minimum link criteria";
        }
        leaf log {
          type empty;
          description
            "Log the event";
        }
      }
      container system-icr-traffic-reroute {
        presence "";
        description
          "Container system ICR traffic reroute";
        leaf system-icr-traffic-reroute {
          type empty;
          mandatory true;
          description
            "System ICR traffic reroute object";
        }
        leaf action-switch-lacp-selected-state {
          type empty;
          mandatory true;
          description
            "Switch LACP selected state by ICR instruction";
        }
        leaf log {
          type empty;
          description
            "Log the event";
        }
      }
    }
    /*
    subscribe micro-bfd
    */
    leaf subscribe-micro-bfd {
      type empty;
      description
        "Micro BFD events for the link group";
    }
    /*
    lacp { admin-key (key-val) | damp-timeout (timeout-val) |
     periodic-timeout { short [immediate] [short-immediate] |
     long } | revertible | { passive | active } | ignore-system-
     id | system-id priority (priority-val) [mac-address (mac-
     addr)]}
    */
    container lacp {
      description
        "Configure LACP parameters";
      leaf admin-key {
        type uint16 {
          range "32767..65535";
        }
        description
          "Configure LACP administrative key";
      }
      leaf damp-timeout {
        type uint8 {
          range "0..10";
        }
        default "10";
        description
          "Timer to damp LAG state flapping from constituent
           state changes";
      }
      container periodic-timeout {
        description
          "Configure LACP periodic timeout";
        choice periodic-timeout {
          default short;
          description
            "";
          case short {
            container short {
              description
                "Configure LACP short periodic timeout";
              leaf immediate {
                type empty;
                status obsolete;
                description
                  "[OBSOLETE]Skip the expired state upon LACP
                   timeout";
              }
              leaf short-immediate {
                type boolean;
                default "false";
                description
                  "Skip the expired state upon LACP timeout";
              }
            }
          }
          case long {
            leaf long {
              type empty;
              description
                "Configure LACP long periodic timeout";
            }
          }
        }
      }
      leaf revertible {
        type boolean;
        default "true";
        description
          "Enable/Disable revertible";
      }
      choice lacp-choice {
        description
          "";
        case passive {
          leaf passive {
            type empty;
            description
              "Configure LACP in passive mode";
          }
        }
        case active {
          leaf active {
            type empty;
            description
              "Configure LACP in active mode";
          }
        }
      }
      leaf ignore-system-id {
        type empty;
        description
          "Configure LACP ignore system ID";
      }
      container system-id-priority {
        presence "";
        description
          "Configure LACP system priority";
        leaf priority-val {
          type uint16 {
            range "0..65534";
          }
          mandatory true;
          description
            "LACP system priority value";
        }
        leaf mac-address {
          type yang:mac-address;
          description
            "Configure LACP system MAC";
        }
      }
    }
    /*
    encapsulation dot1q
    */
    leaf encapsulation-dot1q {
      type empty;
      description
        "Encapsulate Dot1q";
    }
  }

  augment "/if:interfaces/if:interface" {
    description
      "ericsson-lag";
    /*
    link-group [ pos | economical | link-pinning ]
    */
    container link-group {
      when "../if:type = 'ianaift:ieee8023adLag'" {
        description
          "";
      }
      description
        "Define a link group";
      choice link-group-opt {
        description
          "";
        case pos {
          leaf pos {
            type empty;
            description
              "Define a POS type group";
          }
        }
        case economical {
          leaf economical {
            if-feature economical;
            type empty;
            description
              "Set circuit defaults to non-replicated and
               circuit homing";
          }
        }
        case link-pinning {
          leaf link-pinning {
            if-feature link-pinning;
            type empty;
            description
              "Set circuit defaults to replicated and circuit
               homing";
          }
        }
      }
      uses lag-grp;
    }
  }

}
