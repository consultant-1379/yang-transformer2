module ericsson-context-ipos {
  yang-version "1.1";

  namespace "urn:rdns:com:ericsson:oammodel:ericsson-context-ipos";

  prefix "ctxipos";

  import ericsson-types-ipos {
    prefix "typesipos";
  }

  import ietf-inet-types {
    prefix "inet";
  }

  import ericsson-contexts-ipos {
    prefix "ctxsipos";
  }

  import ericsson-yang-extensions {
    prefix "yexte";
  }

  organization
    "Ericsson AB";

  contact
    "Web:   <http://www.ericsson.com>";

  description
    "ericsson-context-ipos
     Copyright (c) 2019 Ericsson AB.
     All rights reserved";

  revision "2019-07-31" {
    description
      "YANG model ip log route and message correction";
    reference
      "rfc7950";
    yexte:version "2";
    yexte:release "7";
    yexte:correction "4";
  }

  revision "2019-07-04" {
    description
      "Update yang version 1.0 to 1.1";
    reference
      "rfc7950";
    yexte:version "2";
    yexte:release "7";
    yexte:correction "3";
  }

  revision "2019-03-28" {
    description
      "Add id for context name";
    reference
      "rfc6020";
    yexte:version "2";
    yexte:release "7";
    yexte:correction "2";
  }

  revision "2019-03-12" {
    description
      "Modified ip log protocol leaf for yang model";
    reference
      "rfc6020";
    yexte:version "2";
    yexte:release "7";
    yexte:correction "1";
  }

  revision "2019-02-28" {
    description
      "Added ip log route support logging filter yang model";
    reference
      "rfc6020";
    yexte:version "2";
    yexte:release "7";
    yexte:correction "0";
  }

  revision "2019-01-24" {
    description
      "Add management context command";
    reference
      "rfc6020";
    yexte:version "2";
    yexte:release "6";
    yexte:correction "1";
  }

  revision "2018-11-07" {
    description
      "Added OSPF yang model of Confd support for hidden
       commands";
    reference
      "rfc6020";
    yexte:version "2";
    yexte:release "6";
    yexte:correction "0";
  }

  revision "2018-10-23" {
    description
      "Add attribute 'ordered by user' for context";
    reference
      "rfc6020";
    yexte:version "2";
    yexte:release "5";
    yexte:correction "1";
  }

  revision "2018-09-06" {
    description
      "Add ip global-flags";
    reference
      "rfc6020";
    yexte:version "2";
    yexte:release "5";
    yexte:correction "0";
  }

  revision "2018-08-30" {
    description
      "SSR-4566 Add Apn service interface command in YANG model
       -- apn_svcs interface";
    reference
      "rfc6020";
    yexte:version "2";
    yexte:release "4";
    yexte:correction "0";
  }

  revision "2018-07-13" {
    description
      "YANG model description correction.";
    reference
      "rfc6020";
    yexte:version "2";
    yexte:release "3";
    yexte:correction "4";
  }

  revision "2018-06-15" {
    description
      "YANG model description correction.";
    reference
      "rfc6020";
    yexte:version "2";
    yexte:release "3";
    yexte:correction "3";
  }

  revision "2018-06-05" {
    description
      "Refine format for yang statements: when, must, path,
       pattern, augment, etc.";
    reference
      "rfc6020";
    yexte:version "2";
    yexte:release "3";
    yexte:correction "2";
  }

  revision "2018-05-08" {
    description
      "rollback vpn-rd type change";
    reference
      "rfc6020";
    yexte:version "2";
    yexte:release "3";
    yexte:correction "1";
  }

  revision "2018-04-27" {
    description
      "add fib optimization configuration";
    reference
      "rfc6020";
    yexte:version "2";
    yexte:release "3";
    yexte:correction "0";
  }

  revision "2018-04-20" {
    description
      "JIRA:SSR-6938 Addition of list rmr, leaves
       'interface','l2tp-peer' under list 'rmr' under context
       configuration mode";
    reference
      "rfc6020";
    yexte:version "2";
    yexte:release "2";
    yexte:correction "0";
  }

  revision "2018-02-07" {
    description
      "Updated maximum ECMPs configuration";
    reference
      "rfc6020";
    yexte:version "2";
    yexte:release "1";
    yexte:correction "1";
  }

  revision "2018-01-26" {
    description
      "Implement 'ip localhost' command in Confd";
    reference
      "rfc6020";
    yexte:version "2";
    yexte:release "1";
    yexte:correction "0";
  }

  revision "2018-01-24" {
    description
      "Add GC_FLAG_GLOBALCONFIG for the commands in
       dot1q_profile mode";
    reference
      "rfc6020";
    yexte:version "2";
    yexte:release "0";
    yexte:correction "1";
  }

  revision "2017-12-19" {
    description
      "add router-id";
    reference
      "rfc6020";
    yexte:version "2";
    yexte:release "0";
    yexte:correction "0";
  }

  revision "2017-12-04" {
    description
      "update pattern for VPN RD";
    reference
      "rfc6020";
    yexte:version "1";
    yexte:release "1";
    yexte:correction "4";
  }

  revision "2017-11-10" {
    description
      "update pattern and description for VPN RD";
    reference
      "rfc6020";
    yexte:version "1";
    yexte:release "1";
    yexte:correction "3";
  }

  revision "2017-10-25" {
    description
      "update revision for VPN RD description";
    reference
      "rfc6020";
    yexte:version "1";
    yexte:release "1";
    yexte:correction "2";
  }

  revision "2017-09-21" {
    description
      "4byte ASN in BGP VPN RD";
    reference
      "rfc6020";
    yexte:version "1";
    yexte:release "1";
    yexte:correction "1";
  }

  revision "2017-09-06" {
    description
      "Fix qos protocol model issue";
    reference
      "rfc6020";
    yexte:version "1";
    yexte:release "0";
    yexte:correction "1";
  }

  revision "2017-08-01" {
    description
      "qos protocol priority";
    reference
      "rfc6020";
    yexte:version "1";
    yexte:release "0";
    yexte:correction "0";
  }

  revision "2017-06-02" {
    description
      "New command for dot1q vcpe";
    reference
      "rfc6020";
  }

  revision "2017-06-02" {
    description
      "Peel off segment routing";
    reference
      "rfc6020";
  }

  revision "2017-05-24" {
    description
      "IPOS-11149:context and interface new command";
    reference
      "rfc6020";
  }

  revision "2017-04-01" {
    description
      "Peel off mld";
    reference
      "rfc6020";
  }

  revision "2017-03-29" {
    description
      "Add pattern for 'alias'";
    reference
      "rfc6020";
  }

  revision "2017-03-29" {
    description
      "add sub command 'maximum-routes' for context ipv6";
    reference
      "rfc6020";
  }

  revision "2017-03-07" {
    description
      "add dvsr container";
    reference
      "rfc6020";
  }

  revision "2017-02-23" {
    description
      "support domain alias";
    reference
      "rfc6020";
  }

  revision "2016-12-29" {
    description
      "Delete route-map name;some list modify can del";
    reference
      "rfc6020";
  }

  revision "2016-12-08" {
    description
      "Add a must condition for vpn-rd";
    reference
      "rfc6020";
  }

  revision "2016-07-08" {
    description
      "Add a feature name for subscriber";
    reference
      "rfc6020";
  }

  revision "2016-03-29" {
    description
      "For CLI2Yang models data node sequence change.";
    reference
      "rfc6020";
  }

  revision "2015-12-07" {
    description
      "initial revision";
    reference
      "rfc6020";
  }

  feature ancp {
    description
      "This feature indicates that the device supports ancp in
       context.";
  }

  feature ospf3 {
    description
      "This feature indicates that the device supports ospf3 in
       context.";
  }

  feature pim {
    description
      "This feature indicates that the device supports pim in
       context.";
  }

  feature rip {
    description
      "This feature indicates that the device supports rip in
       context.";
  }

  feature ripng {
    description
      "This feature indicates that the device supports ripng in
       context.";
  }

  feature subscriber {
    description
      "This feature indicates that the device supports
       subscriber in context.";
  }

  feature iplog {
    description
      "This feature indicates that the device supports ip log in
       context.";
  }

  grouping ctx-grp {
    description
      "Context configuration mode";
    /*
    vcpe profile (pol-str)
    */
    container vcpe {
      description
        "Virtual CPE";
      list profile {
        key "profile";
        description
          "Configure VCPE profile name";
        leaf profile {
          type string;
          description
            "VCPE profile name";
        }
        uses vcpe-profile-grp;
      }
    }
    /*
    ippm < twamp light >
    */
    container ippm {
      description
        "Configure IPPM";
      container twamp-light {
        description
          "Configure TWAMP light tests";
      }
    }
    /*
    description (cfg_ctx_desc_str)
    */
    leaf description {
      type string;
      description
        "Add descriptive text for this context";
    }
    /*
    domain (alias) [ advertise ]
    */
    list domain {
      key "alias";
      description
        "Add a subscriber service domain alias to the context";
      leaf alias {
        type string {
          pattern '[a-zA-Z0-9_.-]+';
        }
        description
          "Name of subscriber service domain alias in context";
      }
      leaf advertise {
        type empty;
        description
          "Advertise subscriber service domain alias in PPPoE
           discovery";
      }
    }
    /*
    subscriber { name (sub-str) | profile (prof-str) }
    */
    container subscriber {
      if-feature subscriber;
      description
        "Configure subscriber accounts and options";
      list name {
        key "name";
        description
          "Configure individual subscriber accounts";
        leaf name {
          type string;
          description
            "Subscriber account name";
        }
        uses sub-grp;
      }
      list profile {
        key "profile";
        description
          "Configure named subscriber profile";
        leaf profile {
          type string;
          description
            "Subscriber profile name";
        }
        uses sub-grp;
      }
    }
    /*
    router { rip (rip-inst) | ripng (rip-inst) | ancp}
    */
    container router {
      description
        "Configure a routing protocol";
      list rip {
        if-feature rip;
        key "rip";
        description
          "Routing Information Protocol (RIP)";
        leaf rip {
          type string;
          description
            "Instance name";
        }
      }
      list ripng {
        if-feature ripng;
        key "ripng";
        description
          "Routing Information Protocol (RIP)";
        leaf ripng {
          type string;
          description
            "Instance name";
        }
      }
      leaf ancp {
        if-feature ancp;
        type empty;
        description
          "Access Node Control (GSMP)";
      }
    }
    /*
    ospf3-maximum { paths (path-value) | neighbor-exchange
     (exchange-value) }
    */
    container ospf3-maximum {
      when "(../context-name = 'local')" {
        description
          "";
      }
      description
        "Configure OSPFv3 global limits";
      leaf paths {
        type uint8 {
          range "1..64";
        }
        description
          "Configure maximum number equal-cost route paths";
      }
      leaf neighbor-exchange {
        type uint32 {
          range "2..4294967295";
        }
        description
          "Maximum neighbors exchanging concurrently";
      }
    }
    /*
    qos protocol { arp | ntp } { priority (dscp-value) }
    */
    list qos-protocol {
      key "qos-protocol-choice";
      description
        "Protocol name";
      leaf qos-protocol-choice {
        type enumeration {
          enum arp {
            value 0;
            description
              "Address Resolution Protocol";
          }
          enum ntp {
            value 1;
            description
              "Network Time Protocol";
          }
        }
        description
          "Select the protocol";
      }
      leaf priority {
        type typesipos:dscp-value;
        mandatory true;
        description
          "Priority of the current protocol";
      }
    }
    /*
    optimize fib { ipv4 | ipv6 } { performance | space } { level
     (level-num) }
    */
    list optimize-fib {
      key "unicast-address-family-choice";
      description
        "Select and configure a FIB optimization algorithm";
      leaf unicast-address-family-choice {
        type enumeration {
          enum ipv4 {
            value 0;
            description
              "Select IPv4 unicast address family";
          }
          enum ipv6 {
            value 1;
            description
              "Select IPv6 unicast address family";
          }
        }
        mandatory true;
        description
          "Select a unicast address family";
      }
      choice optimized-algorithm-choice {
        mandatory true;
        description
          "Select an optimized algorithm";
        case performance {
          leaf performance {
            type empty;
            mandatory true;
            description
              "Select performance optimized algorithm";
          }
        }
        case space {
          leaf space {
            type empty;
            description
              "Select space optimized algorithm";
          }
        }
      }
      leaf level {
        type uint8 {
          range "0..9";
        }
        mandatory true;
        description
          "Configure the level of optimization <0-9>";
      }
    }
    /*
     < rmr {interface (ifname) l2tp-peer (peer_name)} >
    */
    list rmr {
      key "interface";
      description
        "RMR configuration command";
      leaf interface {
        type string;
        description
          "Specify RMR interface";
      }
      leaf l2tp-peer {
        type string;
        mandatory true;
        description
          "RMR transport mecahnism L2TP";
      }
    }
    /*
    dvsr
    */
    container dvsr {
      description
        "Container to hold DVSR profile configuration";
    }
    /*
    ip
    */
    container ip {
      description
        "IP configuration command";
      container pool {
        description
          "Configure per context IP pool";
        container falling-threshold {
          description
            "Configure per context IP pool falling threshold";
          list percentage {
            key "percent-index";
            description
              "Specify a context IP pool percentage falling
               threshold";
            leaf percent-index {
              type uint8 {
                range "1..2";
              }
              description
                "Percentage threshold index<1..2>";
            }
            leaf percent-size {
              type uint8 {
                range "1..100";
              }
              description
                "Percentage falling threshold value";
            }
            choice percentage-choice {
              description
                "";
              case trap {
                container trap {
                  description
                    "Generate SNMP trap";
                  leaf log {
                    type empty;
                    description
                      "Generate log message";
                  }
                }
              }
              case log {
                container log {
                  description
                    "Generate log message";
                  leaf trap {
                    type empty;
                    description
                      "Generate SNMP trap";
                  }
                }
              }
            }
          }
          container absolute {
            description
              "Specify a context IP pool absolute falling
               threshold";
            leaf abs-index {
              type uint8 {
                range "1";
              }
              description
                "Absolute threshold index";
            }
            leaf abs-size {
              type uint32 {
                range "1..4294967295";
              }
              description
                "Absolute falling threshold value";
            }
            choice absolute-choice {
              description
                "";
              case trap {
                container trap {
                  description
                    "Generate SNMP trap";
                  leaf log {
                    type empty;
                    description
                      "Generate log message";
                  }
                }
              }
              case log {
                container log {
                  description
                    "Generate log message";
                  leaf trap {
                    type empty;
                    description
                      "Generate SNMP trap";
                  }
                }
              }
            }
          }
        }
        leaf options-use-class-c-bcast-addrs {
          type empty;
          description
            "Allow class-C broadcast addresses in all configured
             IP pools";
        }
      }
      container log {
        when "../../context-name='local'" {
          description
            "";
        }
        if-feature iplog;
        description
          "Configure RIB log buffers";
        container route {
          presence "";
          description
            "Route API log buffer";
          container ipaddr {
            presence "";
            description
              "Filtered by IP address";
            leaf prefix1 {
              type typesipos:ipos-ip-prefix;
              description
                "Address followed by mask or prefix length";
            }
            leaf prefix2 {
              type typesipos:ipos-ip-prefix;
              description
                "Address followed by mask or prefix length";
            }
            leaf prefix3 {
              type typesipos:ipos-ip-prefix;
              description
                "Address followed by mask or prefix length";
            }
            leaf prefix4 {
              type typesipos:ipos-ip-prefix;
              description
                "Address followed by mask or prefix length";
            }
            leaf prefix5 {
              type typesipos:ipos-ip-prefix;
              description
                "Address followed by mask or prefix length";
            }
          }
          leaf log-to-file {
            type empty;
            description
              "Log record in file";
          }
          leaf protocol {
            type enumeration {
              enum bgp {
                value 0;
                description
                  "Filter by bgp";
              }
              enum isis {
                value 1;
                description
                  "Filter by isis";
              }
              enum ldp {
                value 2;
                description
                  "Filter by ldp";
              }
              enum ospf {
                value 3;
                description
                  "Filter by ospf";
              }
              enum ospf3 {
                value 4;
                description
                  "Filter by ospf3";
              }
              enum pim {
                value 5;
                description
                  "Filter by pim";
              }
              enum rip {
                value 6;
                description
                  "Filter by rip";
              }
              enum rsvp {
                value 7;
                description
                  "Filter by rsvp";
              }
              enum static {
                value 8;
                description
                  "Filter by static";
              }
            }
            description
              "Filter by src_proto";
          }
          leaf size {
            type uint16 {
              range "1..65535";
            }
            description
              "Set the size of the log buffer";
          }
        }
        container config {
          presence "";
          description
            "Configure API log buffer";
          leaf size {
            type uint16 {
              range "1..65535";
            }
            description
              "Set the size of the log buffer";
          }
        }
        container message {
          presence "";
          description
            "Message API log buffer";
          leaf log-to-file {
            type empty;
            description
              "Log record in file";
          }
          leaf size {
            type uint16 {
              range "1..65535";
            }
            description
              "Set the size of the log buffer";
          }
        }
        container eof {
          presence "";
          description
            "EOF log buffer";
          leaf size {
            type uint16 {
              range "1..65535";
            }
            description
              "Set the size of the log buffer";
          }
        }
        list protocol {
          key "protocol";
          description
            "Protocol log buffer";
          leaf protocol {
            type uint8 {
              range "1..254";
            }
            description
              "RIB protocol number <1..254>";
          }
          leaf size {
            type uint16 {
              range "1..65535";
            }
            description
              "Set the size of the log buffer";
          }
        }
        list slot {
          key "slot-num slot-choice";
          description
            "Line card log buffer";
          leaf slot-num {
            type typesipos:slot-number;
            description
              "Slot number";
          }
          leaf slot-choice {
            type enumeration {
              enum ingress {
                value 0;
                description
                  "Ingress log buffer";
              }
              enum egress {
                value 1;
                description
                  "Egress log buffer";
              }
            }
            description
              "Ingress or egress log buffer ";
          }
          leaf size {
            type uint16 {
              range "1..65535";
            }
            description
              "Set the size of the log buffer";
          }
        }
      }
      container global-flags {
        when "../../context-name='local'" {
          description
            "";
        }
        description
          "Configure RIB global_flag";
        leaf bfd-fsm-tracing-enable {
          type empty;
          description
            "Enable bfd fsm tracing";
        }
        leaf bfd-gen-fsm-diagram {
          type empty;
          description
            "BFD gen fsm diagram";
        }
        leaf debug-backtrace-symbols {
          type empty;
          description
            "Enable debug backtrace symbols";
        }
        leaf debug-dont-fflush {
          type empty;
          description
            "Enable debug dont fflush";
        }
        leaf debug-enable-all {
          type empty;
          description
            "Enable debug enable all";
        }
        leaf debug-to-file {
          type empty;
          description
            "Enable debug to file";
        }
        leaf dont-log-src-query {
          type empty;
          description
            "Do not log the src query";
        }
        leaf dont-log-to-memory {
          type empty;
          description
            "Do not log to memory";
        }
        leaf log-slots-enable-all {
          type empty;
          description
            "Enable all log slots";
        }
        leaf log-to-file {
          type empty;
          description
            "Log to file";
        }
        leaf log-to-file-reopen {
          type empty;
          description
            "Log to file reopen";
        }
      }
    }
    /*
    ipv6
    */
    container ipv6 {
      description
        "IPv6 configuration command";
    }
    /*
    router-id (id-spec)
    */
    leaf router-id {
      type inet:ipv4-address;
      description
        "Context level IP Router ID";
    }
  }

  grouping dot1q-profile-grp {
    description
      "Dot1q profile configuration mode";
    /*
    description (desc-str)
    */
    leaf description {
      type string;
      description
        "Set description string";
    }
  }

  grouping sub-grp {
    description
      "Subscriber configuration mode";
    /*
    ipv6 { nd-profile (profile-name) }
    */
    container ipv6 {
      presence "";
      description
        "Configure IPv6";
      leaf nd-profile {
        type string;
        mandatory true;
        description
          "Set the Neighbor Discovery profile";
      }
    }
    /*
    forward policy (pol-name) in
    */
    container forward-policy {
      presence "";
      description
        "Set forward policy to use";
      leaf pol-name {
        type string;
        mandatory true;
        description
          "Name of already created forward policy";
      }
      leaf in {
        type empty;
        mandatory true;
        description
          "Set inbound forward policy to use";
      }
    }
  }

  grouping vcpe-profile-grp {
    description
      "VCPE profile configuration";
    /*
    line-identifier access-circuit
    */
    leaf line-identifier-access-circuit {
      type empty;
      description
        "Line is identified as using access circuit";
    }
  }

  augment "/ctxsipos:contexts" {
    description
      "ericsson-context";
    /*
    context (context-name) [ vpn-rd (vpn-val) ] [ id (id-val) ]
    */
    list context {
      key "context-name";
      unique "id";
      ordered-by user;
      description
        "Configure an operational context";
      leaf context-name {
        type string;
        description
          "Specify a named context to configure";
      }
      leaf vpn-rd {
        type string {
          pattern '(((([0-9]|[1-9][0-9]|1[0-9][0-9]|'
          + '2[0-4][0-9]|25[0-5])\.){3}([0-9]|[1-9][0-9]|'
          + '1[0-9][0-9]|2[0-4][0-9]|25[0-5]))|(\d{1,5}|0(x|X)'
          + '([0-9a-fA-F]{1,4}))|(\d{1,10}|0(x|X)([0-9a-fA-F]{1,8}'
          + '))):(\d{1,10}|0(x|X)([0-9a-fA-F]{1,8}))';
        }
        must "../context-name!='local'" {
          error-message "Must configure in non-local context";
          description
            "Must configure in non-local context";
        }
        description
          "Configure a VPN context (VPN RD in ASN:nnnn or
           A.B.C.D:nn or ASN[L]:nn format)";
      }
      leaf id {
        type uint16 {
          range "3073..8191";
        }
        must "../../ctxsipos:service/ctxsipos:static-context-id="
        + "'true'" {
          error-message "Static context id should not be "
          + "configured without enabling static-context-id service "
          + "under service.";
          description
            "To config id, static-context-id must be true.";
        }
        must "../context-name!='local'" {
          error-message "Must configure in non-local context";
          description
            "Must configure in non-local context";
        }
        description
          "id";
      }
      uses ctx-grp;
    }
    /*
    management context (context-name)
    */
    container management {
      description
        "Configure management context";
      leaf context {
        type leafref {
          path "/ctxsipos:contexts/ctxipos:context/ctxipos:"
          + "context-name";
        }
        description
          "Set the management context";
      }
    }
    /*
    dot1q {profile (profile-name)}
    */
    list dot1q {
      key "profile";
      description
        "Dot1q configuration commands";
      leaf profile {
        type string;
        description
          "Specify Dot1q profile information";
      }
      uses dot1q-profile-grp;
    }
  }

}
