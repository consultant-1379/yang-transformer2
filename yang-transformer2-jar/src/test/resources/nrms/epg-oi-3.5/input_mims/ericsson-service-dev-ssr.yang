module ericsson-service-dev-ssr {
  yang-version "1.1";

  namespace "urn:rdns:com:ericsson:oammodel:ericsson-service-dev-ssr";

  prefix "servicedevssr";

  import ericsson-service-ipos {
    prefix "serviceipos";
  }

  import ericsson-context-ipos {
    prefix "ctxipos";
  }

  import ericsson-contexts-ipos {
    prefix "ctxsipos";
  }

  import ericsson-acl-ipos {
    prefix "aclipos";
  }

  import ericsson-yang-extensions {
    prefix "yexte";
  }

  organization
    "Ericsson AB";

  contact
    "Web:   <http://www.ericsson.com>";

  description
    "ericsson-service-dev-ipos
     Copyright (c) 2019 Ericsson AB.
     All rights reserved";

  revision "2019-07-04" {
    description
      "Update yang version 1.0 to 1.1";
    reference
      "rfc7950";
    yexte:version "1";
    yexte:release "0";
    yexte:correction "1";
  }

  revision "2019-03-19" {
    description
      "obsolete and deviate leaf service fabric-alarm-reload on SSR";
    reference
      "rfc6020";
    yexte:version "1";
    yexte:release "0";
    yexte:correction "0";
  }

  deviation "/ctxsipos:contexts/ctxsipos:service/serviceipos:fabric-alarm-reload" {
      deviate not-supported;
  }
}
