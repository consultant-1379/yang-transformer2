module ericsson-yang-extensions {
    yang-version "1.1";
    namespace "urn:rdns:com:ericsson:oammodel:ericsson-yang-extensions";
    prefix yexte ;

    organization  "Ericsson AB";
    contact "Ericsson first line support via email";
    description "The module defines Ericsson proprietary YANG extensions.

    Copyright (c) 2016 Ericsson AB. All rights reserved.

    Extensions MUST be defined with the following structure in the
    description statement:
        - What is this statement.
        - Newline,
        - This statement can be a substatement of the xxx statements with
        cardinality x..y.
        - This statement can have the following substatements with
        cardinality x..y.
        - Newline.
        - The argument its meaning and type. Preferably use YANG types and
        constraints to define the argument's type.
                ";

    revision "2019-07-04" {
	description
	  "Update yang version 1.0 to 1.1";
	reference
	  "rfc7950";
	yexte:version "2";
	yexte:release "3";
	yexte:correction "1";
    }

    revision "2018-05-17" {
        description "Added updated-description and user-group
            stepped back to yang version 1";
        yexte:version "2";
        yexte:release "3";
        yexte:correction "0";
    }

    revision "2018-02-14" {
        description "Added takes-effect and dependencies";
        yexte:version "2";
        yexte:release "2";
        yexte:correction "0";
    }

    revision "2018-02-06" {
        description "Updated description for resolution";
        yexte:version "2";
        yexte:release "1";
        yexte:correction "3";
    }

    revision "2017-06-06" {
        description "Added preliminary.";
        yexte:version "2";
        yexte:release "1";
        yexte:correction "2";
    }

    revision "2017-05-11" {
        description "Updated supported-features, static-data
        removed not-notifiable.";
        yexte:version "2";
        yexte:release "0";
        yexte:correction "2";
    }

    revision "2016-12-08" {
        description "Defined standard texts to be included in the description.
        Made resolution a substatement of range similar to tailf:step.
        Added module-conformance-import.";
        yexte:version "1";
        yexte:release "2";
        yexte:correction "0";
    }

        revision "2016-09-27" {
        description "Added static data";
        yexte:version "1";
        yexte:release "1";
        yexte:correction "0";
    }

    revision "2016-07-01" {
        description "Initial version";
        yexte:version "1";
        yexte:release "0";
        yexte:correction "0";
    }

    extension status-information {
        description "Contextual information related to the value of
            status.

            The statement MUST only be a substatement to the YANG
            status statement.
            Zero or one status-information statement per status is allowed.
            NO substatements are allowed.

            The value can be any text.";
        argument "text";
    }


    extension original-prefix {
        description
            "If the prefix for a YANG module has been modified e.g. to
            avoid prefix clashes the original prefix shall be placed in
            this statement.

            The statement MUST only be a substatement of the prefix
            substatement of the module statement.
            Zero or One original-prefix statement per prefix is allowed.
            NO substatements are allowed.

            The argument follows the same rules as the argument of
            the prefix statement.";
        argument "prefixString";
    }

    extension dependencies {
        description
            "Specifies dependencies that exists to other data nodes. E.g. a > b.

            The Description statement of the parent statement SHOULD contain
            the label 'Dependencies: ' followed by the text from the argument.
            The label and text are usually added automatically.

            The statement MUST only be a substatement of the leaf, leaf-list,
            container, list, anydata, anyxml, rpc, action statements.
            Zero or One dependencies statement is allowed per parent
            statement.
            NO substatements are allowed.
            The argument can be any text describing  depedndencies.";

        argument "dependencies-description";
    }

    extension disturbances {
        description
            "Specifies that a modification/execution MAY cause disturbances
            for ongoing traffic handled by system.

            The Description statement of the parent statement SHOULD contain
            the label 'Traffic disturbance: ' followed by the text from the argument.
            The label and text are usually added automatically.

            The statement MUST only be a substatement of the leaf, leaf-list,
            container, list, anydata, anyxml, rpc, action statements.
            Zero or One disturbances statement is allowed per parent
            statement.
            NO substatements are allowed.
            The argument can be any text describing
            what effects the modification/execution may have on ongoing traffic.";

        argument "disturbance-description";
    }

    extension precondition {
        description
            "Specification of the precondition(s) that must be met to
            allow modification/execution.

            The Description statement of the parent statement SHOULD contain
            the label 'Precondition: ' followed by the text from the argument.
            The label and text are usually added automatically.

            The statement MUST only be a substatement of the leaf, leaf-list,
            container, list, anydata, anyxml, rpc, action statements.
            Zero or One precondition statement is allowed per parent
            statement.
            NO substatements are allowed.

            The argument SHOULD take the form of a 'must' statement that when
            evaluated to True allows modification/execution of the parent statement.
            The condition refers to the configuration state of the running data store
            BEFORE executing the current transaction/rpc/action.
            A textual description of the precondition(s) is also allowed.";

        argument "precondition";
    }

    extension side-effects {
        description
            "Specifies that modification/execution MAY have side effects on the
            configuration itself.

            The Description statement of the parent statement SHOULD contain
            the label 'Side effect: ' followed by the text from the argument.
            The label and text are usually added automatically.

            The statement MUST only be a substatement of the leaf, leaf-list,
            container, list, anydata, anyxml, rpc, action statements.
            Zero or One side-effects statement is allowed per parent
            statement.
            NO substatements are allowed.

            The argument can be any text describing the side effects
            on the configuration that the modification/execution has.";

        argument "side-effects-description";
    }

    extension takes-effect {
        description
            "Specifies when a new value takes effect in the system.
            Note! Not when it is stored in the datastore, but when
            it effects the behavior of the system.

            The Description statement of the parent statement SHOULD contain
            the label 'Takes effect: ' followed by the text from the argument.
            The label and text are usually added automatically.

            The statement MUST only be a substatement of the leaf, leaf-list,
            container, list, anydata, anyxml, rpc, action statements.
            Zero or One takes-effect statement is allowed per parent
            statement.
            NO substatements are allowed.

            The argument can be any text. Usual values are:
                Next restart
                Next reconfiguration";

        argument "takes-effects-description";
    }

    extension version {
        description
            "The version number of the module/submodule,
            to be stepped when the module/submodule is
            changed in a backward incompatible way.

            The statement MUST only be a substatement to the revision statement.
            Parent MUST have exactly one version statement.
            NO substatements are allowed.

            value is of type uint32.";
       argument "value";
    }

    extension release {
        description
            "The release number of the module/submodule,
            to be stepped for each backward compatible change.
            When the version is stepped, the release is reset to 0.

            The statement MUST only be a substatement to the revision statement.
            Parent MUST have exactly one release statement.
            NO substatements are allowed.

            value is of type uint32.";
        argument "value";
    }

    extension correction {
        description
            "The correction number of the module/submodule,
            to be stepped for each backward compatible correction,
            when a later release already exists.
            When release is stepped or reset, correction is reset to 0.

            The statement MUST only be a substatement to the revision statement.
            Parent MUST have exactly one correction statement.
            NO substatements are allowed.

            value is of type uint32.";
        argument "value";
    }

    extension resolution {
        description
            "Used to further restrict the range of integer and decimal types.
            The allowed values for the type is further restricted to
            only those values that match the expression:

            'low' + n * 'resolution'

            where 'low' is the lowest allowed value in the range, n is a
            arbitrary non-negative integer.

            The Description statement of the parent statement SHOULD contain
            the textual label 'Resolution: ' followed by the text from the argument.
            The label and text are usually added automatically.

            The statement MUST only be a substatement of the range statement.
            Zero or one resolution statement per parent statement is
            allowed.
            NO substatements are allowed.

            The value is a positive integer value for integer based data types
            and for decimal64 based data types, the value is a decimal value
            with the same or less number of decimals that is specified for the type.";

        argument "value";
    }

    extension is-system-created {
        description "Indicates that the list or container cannot be
            created/deleted through the North Bound Interface (NBI). System
            created statements can have both read-only and read-write
            data node children.

            The Description statement of the parent statement SHOULD contain
            the text 'Is created/deleted by the system only.'.

            The statement MUST only be a substatement of the list, container
            statements.
            Zero or one is-system-created statement per parent statement is allowed.
            NO substatements are allowed.";
    }

    extension static-data {
        description "Indicates that a data node contains data that is
        	loaded by the system at system start and is only changed during
        	system start and cannot be created/deleted/changed through the
        	North Bound Interface (NBI) or CLI.

            The data MAY be marked as config true to allow leafref,
            when or must constraints to be based on it.

            When changing static-data backward compatibility
            MUST be considered. The following changes are considered
            backwards incompatible:
            - If a data node indicates support for a subfunction, changing
            it to remove support
            - Decreasing the valuespace of a whitelist (e.g. supported values)
            - Increasing the value space of a blacklist (e.g. prohibited values)

            The statement MUST only be a substatement of the leaf, leaf-list,
            container, list, anydata, anyxml statements.
            Zero or one static-data statement per parent statement is allowed.
            NO substatements are allowed.

            The argument is a boolean value indicating whether the data node
            is considered static-data or not. If static-data is not specified,
            the default is the same as the parent data node's value. For top
            level data nodes the default value is false.
            Note: Top level statements in augment or groupings do NOT inherit
            the static-data value from containing nodes, they default to
            static-data false.

            When the argument value is true, the Description statement of
            the parent statement SHOULD contain the text 'This data node (tree)
            cannot be changed in a running system.'.

            When the argument value is false the Description statement of
            the parent statement SHOULD contain the text 'This data node (tree)
            may be changed according to the model constraints.'.";

        argument value;
    }

    extension library-module {
        description
            "Indicates that this module (and all of its submodules) is
            intended as library module.
            The YAM SHOULD not contain any data nodes.
            Very strict compatibility rules SHALL apply to all YANG
            constructs importable from this YAM.
            The only changes allowed for a released revision of a
            library YAM are
            - adding new constructs e.g. types, groupings, features,
            identities, extensions
            - Error corrections (not interpretation changes, only clean errors)
            - Editorial updates that don't change behavior

            The statement MUST only be a substatement of the module statement.
            Zero or one library-module statement is allowed per
            parent statement.
            NO substatements are allowed.";
    }

    extension supported-feature {
        description
            "The extension declares that a feature is supported by a managed
            element.
            The extension SHALL only be used in modules derived from
            ericsson-supported-features.yang. It MUST be ignored in other YAMs.
            If multiple derived files are present the system supports
            the union of all features listed in these files.

            If a YAM containing features is not included in any
            supported-feature statements, all it's features are considered
            to be supported. (default is to support all features)

            If a YAM containing features is included in at least one
            supported-feature statement, the listed features are supported.

            If a YAM containing features is included in at least one
            supported-feature statement with the argument '<modname>:' AND
            it is NOT included in any supported-feature statements with an
            argument that includes a featurename, then none of its features
            are supported.

            If a YAM containing features is included in multiple
            supported-feature statements, some with an argument that includes
            a featurename AND ALSO some with the argument '<modname>:' that
            does not include a featurename, then the statements without
            featurenames are ignored, and the listed features are supported.

            The statement and its argument MUST be on a single line without
            any quotation marks, concatenation using '+' or comments as some
            programs will use simple, non-Yang-aware parsing to handle the file.
            E.g.
            yexte:supported-feature ericsson-fm:alert;

            The statement MUST only be a substatement of the module statement.
            Zero or More supported-features are allowed per parent statement.
            NO substatements are allowed.

            The argument has the format  <modulename>:[<featurename>]
            Example:
            'ietf-system:radius'     declares support for radius configuration
            'ietf-system:'           declares that no features of the
                                      ietf-system YAM are supported.";

        argument "supported-feature";
    }

    extension module-conformance-import {
        description
            "Indicates that the implementation imports reusable
            definitions from the YAM but does not implement any
            data nodes.

            The statement MUST only be a substatement of the module statement.
            Zero or One module-conformance-import are allowed per parent
            statement.
            NO substatements are allowed.

            The argument is the name of the YAM.";

        argument "yam-name";
    }

    extension is-passphrase  {
        description
            "The leaf or leaf-list holds a passphrase and its value
            MUST NOT be revealed.

            For a client interacting with the end user, the following
            may apply:
            - When the user enters a value for the attribute, '*' is
            displayed instead of the actual characters.
            - When the string value is received during a get operations,
            the value returned by the Managed Element (Netconf server) is
            displayed and that value may, or may not, have been replaced by
            asterisks.

            The statement MUST only be a substatement of the
            leaf-list, leaf statements.
            Zero or One is-passphrase statement is allowed per parent
            statement.
            NO substatements are allowed.";
    }

    extension preliminary  {
        description
            "The schema node is part of an early design effort.
            Preliminary nodes MUST be tested to ensure they do not cause
            stoppage or significant traffic disturbance.
            Preliminary nodes SHOULD be, but MAY NOT be fully functional.
            Preliminary nodes MAY be changed or removed in the future
            ignoring backward compatibility rules.
            Faults and problems with preliminary nodes MAY NOT always
            be handled during normal maintenance of the SW.

            The statement MUST only be a substatement of a
            status statement which has the argument  'current'.
            Zero or One preliminary statement is allowed per parent
            statement.
            NO substatements are allowed.";
    }

    extension user-group {
        description
            "Defines an access control user-group that usually allows access
            to a specific data node, rpc, action or notification. The
            user-group will be granted create, read, update, delete, exec access.

            Initial access control rules/rules-lists SHOULD be loaded
            that grant access. Access MUST also be granted to all child,
            grandchild etc. schema nodes down the containment tree.
            These predefined rule-lists SHOULD be named 'ericsson-xxx' to make
            them easily recognizable.
            Predefined access control rule-lists/rules should not, but may be
            modified by an OAM user. In this case the access rights granted
            to the user-group may change.

            The statement MUST only be a substatement of the leaf, leaf-list,
            container, list, anydata, anyxml, action, rpc, notification statements.
            Zero or one user-group statement per parent statement is allowed.
            NO substatements are allowed.

            The argument value is a string containing a space separated list
            of group names. Each and any of the groups SHOULD provide access to
            the parent schema node.
            The list of groupnames is not exhaustive, if a group's
            name does not appear in this list it MAY still be used to grant
            access to the parent schema node.";

        argument "access-granting-groups";
    }

    extension updated-description {
        description
            "Defines an updated description for a schema node.
            YANG allows changing the content and behavior of a schema node
            using deviations. In such a case the description of the
            schema node may also need to be updated. As YANG does not allow
            deviating the description statement this extension is to provide
            alternate text for the original description.

            The statement MUST only be a substatement of the
            description statement.
            Zero or one changed-description statement per parent statement is
            allowed.
            NO substatements are allowed.

            The argument value is a string containing an updated description
            text for the grandparent schema node.
            Tools will often replace the original description text with this
            argument while adding the sentence:
            Description replaced to reflect deviations";

        argument "description-text";
    }

}
