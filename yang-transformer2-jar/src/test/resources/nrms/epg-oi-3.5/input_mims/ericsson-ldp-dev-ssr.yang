module ericsson-ldp-dev-ssr {
  yang-version "1.1";

  namespace "urn:rdns:com:ericsson:oammodel:ericsson-ldp-dev-ssr";

  prefix "ldpdevssr";

  import ietf-inet-types {
    prefix "inet";
  }

  import ietf-interfaces {
    prefix "if";
  }

  import ericsson-contexts-ipos {
    prefix "ctxsipos";
  }

  import ericsson-types-ipos {
    prefix "typesipos";
  }

  import ericsson-context-ipos {
    prefix "ctxipos";
  }

  import ericsson-ldp-ipos {
    prefix "ldpipos";
  }

  import ericsson-yang-extensions {
    prefix "yexte";
  }

  organization
    "Ericsson AB";

  contact
    "Web:   <http://www.ericsson.com>";

  description
    "ericsson-ldp-dev-ipos
     Copyright (c) 2017 Ericsson AB.
     All rights reserved";

  revision "2019-07-04" {
    description
      "Update yang version 1.0 to 1.1";
    reference
      "rfc7950";
    yexte:version "1";
    yexte:release "0";
    yexte:correction "2";
  }

  revision "2017-11-09" {
    description
      "Change the prefix.";
    reference
      "rfc6020";
    yexte:version "1";
    yexte:release "0";
    yexte:correction "1";
  }

  revision "2017-05-04" {
    description
      "initial revision";
    reference
      "rfc6020";
    yexte:version "1";
    yexte:release "0";
    yexte:correction "0";
  }
  deviation "/ctxsipos:contexts/ctxipos:context/ctxipos:router/ldpipos:ldp/ldpipos:tunnel-shortcut" {
      deviate not-supported;
  }
  deviation "/ctxsipos:contexts/ctxipos:context/ctxipos:router/ldpipos:ldp/ldpipos:neighbor/ldpipos:neighbor-choice/ldpipos:targeted/ldpipos:tunnel-shortcut" {
      deviate not-supported;
  }
}
