module ericsson-mirror-policy-ipos {
  yang-version "1.1";

  namespace "urn:rdns:com:ericsson:oammodel:ericsson-mirror-policy-ipos";

  prefix "mirrorpolicyipos";

  import ericsson-context-ipos {
    prefix "ctxipos";
  }

  import ericsson-contexts-ipos {
    prefix "ctxsipos";
  }

  import ericsson-yang-extensions {
    prefix "yexte";
  }

  organization
    "Ericsson AB";

  contact
    "Web:   <http://www.ericsson.com>";

  description
    "ericsson-mirror-policy-ipos
     Copyright (c) 2019 Ericsson AB.
     All rights reserved";

  revision "2019-07-04" {
    description
      "Update yang version 1.0 to 1.1";
    reference
      "rfc7950";
    yexte:version "1";
    yexte:release "0";
    yexte:correction "3";
  }

  revision "2018-06-20" {
    description
      "YANG model description correction";
    reference
      "exec-cli command";
    yexte:version "1";
    yexte:release "0";
    yexte:correction "2";
  }

  revision "2018-06-05" {
    description
      "Refine format for yang statements: when, must, path,
       pattern, augment, etc.";
    reference
      "rfc6020";
    yexte:version "1";
    yexte:release "0";
    yexte:correction "1";
  }

  revision "2017-07-21" {
    description
      "destination/rate/maximum-length should be configured
       separately";
    reference
      "exec-cli command";
    yexte:version "1";
    yexte:release "0";
    yexte:correction "0";
  }

  revision "2017-05-10" {
    description
      "initial revision";
    reference
      "rfc6020";
  }

  grouping policy-mirror-grp {
    description
      "Mirror policy configuration mode";
    /*
    destination (dest-name)
    */
    leaf destination {
      type string {
        length "1..39";
      }
      description
        "Specify mirror destination";
    }
    /*
    rate (rate-num) burst (burst-num)
    */
    container rate {
      presence "";
      description
        "Maximum data rate";
      leaf rate {
        type uint32 {
          range "64..1000000";
        }
        mandatory true;
        description
          "Data rate in kbps";
      }
      leaf burst {
        type uint32 {
          range "1..4250000000";
        }
        mandatory true;
        description
          "Burst size";
      }
    }
    /*
    maximum-length (len-num)
    */
    leaf maximum-length {
      type uint16 {
        range "14..256";
      }
      description
        "Maximum mirror length";
    }
    /*
    ip access-group (acl-name) (mirror-ctxname)
    */
    list ip-access-group {
      when "../mirror-policy-choice='circuit'" {
        description
          "";
      }
      key "acl-name mirror-ctxname";
      max-elements 1;
      description
        "Specify access list";
      leaf acl-name {
        type string {
          length "1..39";
        }
        description
          "Policy access list name";
      }
      leaf mirror-ctxname {
        type leafref {
	  path "/ctxsipos:contexts/ctxipos:context/ctxipos:"
	  + "context-name";
        }
        description
          "Name of the context in which the policy access list
           is defined";
      }
      uses policy-group-grp;
    }
    /*
    ipv6 access-group (acl-name) (mirror-ctxname)
    */
    list ipv6-access-group {
      when "../mirror-policy-choice='circuit'" {
        description
          "";
      }
      key "acl-name mirror-ctxname";
      max-elements 1;
      description
        "Specify access list";
      leaf acl-name {
        type string {
          length "1..39";
        }
        description
          "Policy access list name";
      }
      leaf mirror-ctxname {
        type leafref {
	  path "/ctxsipos:contexts/ctxipos:context/ctxipos:"
	  + "context-name";
        }
        description
          "Name of the context in which the policy access list
           is defined";
      }
      uses policy-group-grp;
    }
  }

  grouping policy-group-grp {
    description
      "Policy class group configuration mode";
    /*
    class (class-name)
    */
    list class {
      key "class";
      description
        "ACL class name";
      leaf class {
        type string {
          length "1..39";
        }
        description
          "Policy ACL class name";
      }
      uses class-policy-mirror-grp;
    }
  }

  grouping class-policy-mirror-grp {
    description
      "Class configuration mode";
    /*
    destination (dest-name)
    */
    leaf destination {
      type string {
        length "1..39";
      }
      description
        "Specify mirror destination";
    }
    /*
    maximum-length (len-num)
    */
    leaf maximum-length {
      type uint16 {
        range "14..256";
      }
      description
        "Maximum mirror length";
    }
  }

  augment "/ctxsipos:contexts" {
    description
      "ericsson-mirror-policy";
    /*
    mirror policy { port | circuit } (mirror-polname)
    */
    list mirror-policy {
      key "mirror-polname";
      description
        "Configure mirror policy";
      leaf mirror-polname {
        type string {
          length "1..39";
        }
        description
          "Mirror policy name";
      }
      leaf mirror-policy-choice {
        type enumeration {
          enum port {
            value 0;
            description
              "Configure port mirror policy";
          }
          enum circuit {
            value 1;
            description
              "Configure circuit mirror policy";
          }
        }
        mandatory true;
        description
          "Configure port mirror policy choice";
      }
      uses policy-mirror-grp;
    }
  }

}
