module ericsson-contexts-dev-ssr {
  yang-version "1.1";

  namespace "urn:rdns:com:ericsson:oammodel:ericsson-contexts-dev-ssr";

  prefix "ctxsdevssr";

  import ericsson-contexts-ipos {
    prefix "ctxsipos";
  }

  import ericsson-yang-extensions {
    prefix "yexte";
  }

  organization
    "Ericsson AB";

  contact
    "Web:   <http://www.ericsson.com>";

  description
    "ericsson-context-dev-ssr
     Copyright (c) 2018 Ericsson AB.
     All rights reserved";

  revision "2019-07-04" {
    description
      "Update yang version 1.0 to 1.1";
    reference
      "rfc7950";
    yexte:version "1";
    yexte:release "0";
    yexte:correction "1";
  }

  revision "2018-01-25" {
    description
      "Creation of deviation file";
       yexte:version 1;
       yexte:release 0;
       yexte:correction 0;
  }

  deviation "/ctxsipos:contexts/ctxsipos:system/ctxsipos:confirmations" {
      deviate not-supported;
  }

  deviation "/ctxsipos:contexts-state" {
      deviate not-supported;
  }
}
