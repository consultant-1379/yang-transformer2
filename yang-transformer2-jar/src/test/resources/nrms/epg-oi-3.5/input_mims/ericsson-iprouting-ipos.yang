module ericsson-iprouting-ipos {
  yang-version "1.1";

  namespace "urn:rdns:com:ericsson:oammodel:ericsson-iprouting-ipos";

  prefix "iproutingipos";

  import ietf-inet-types {
    prefix "inet";
  }

  import ericsson-context-ipos {
    prefix "ctxipos";
  }

  import ietf-interfaces {
    prefix "if";
  }

  import ericsson-contexts-ipos {
    prefix "ctxsipos";
  }

  import ericsson-yang-extensions {
    prefix "yexte";
  }

  organization
    "Ericsson AB";

  contact
    "Web:   <http://www.ericsson.com>";

  description
    "ericsson-iprouting-ipos
     Copyright (c) 2019 Ericsson AB.
     All rights reserved";

  revision "2019-07-04" {
    description
      "Update yang version 1.0 to 1.1";
    reference
      "rfc7950";
    yexte:version "2";
    yexte:release "2";
    yexte:correction "4";
  }

  revision "2018-07-10" {
    description
      "Switch the position of log-only and threshold.";
    reference
      "rfc6020";
    yexte:version "2";
    yexte:release "2";
    yexte:correction "3";
  }

  revision "2018-06-20" {
    description
      "YANG model description correction";
    reference
      "rfc6020";
    yexte:version "2";
    yexte:release "2";
    yexte:correction "2";
  }

  revision "2018-06-05" {
    description
      "Refine format for yang statements: when, must, path,
       pattern, augment, etc.";
    reference
      "rfc6020";
    yexte:version "2";
    yexte:release "2";
    yexte:correction "1";
  }

  revision "2018-05-16" {
    description
      "Added ipv6 pool under context";
    reference
      "rfc6020";
    yexte:version "2";
    yexte:release "2";
    yexte:correction "0";
  }

  revision "2018-03-28" {
    description
      "Add soft-gre for ip under context";
    reference
      "rfc6020";
    yexte:version "2";
    yexte:release "1";
    yexte:correction "0";
  }

  revision "2018-01-29" {
    description
      "Delete the leaf discovery-interval range and add default
       value 600";
    reference
      "rfc6020";
    yexte:version "2";
    yexte:release "0";
    yexte:correction "1";
  }

  revision "2017-12-19" {
    description
      "delete router-id";
    reference
      "rfc6020";
    yexte:version "2";
    yexte:release "0";
    yexte:correction "0";
  }

  revision "2017-01-18" {
    description
      "initial revision";
    reference
      "rfc6020";
    yexte:version "1";
    yexte:release "0";
    yexte:correction "0";
  }

  augment "/ctxsipos:contexts" {
    description
      "ericsson-iprouting";
    /*
    ipv6
    */
    container ipv6 {
      description
        "Set IPv6 parameters";
      container path-mtu-discovery {
        description
          "Set path MTU discovery parameters";
        leaf discovery-interval {
          type uint32;
          default "600";
          description
            "Set discovery interval, 0 for disable and the valid
             range is 300 to 2000000000";
        }
      }
    }
    /*
    tcp
    */
    container tcp {
      description
        "Set TCP parameters";
      leaf path-mtu-discovery {
        type empty;
        description
          "Enable/disable TCP path MTU discovery";
      }
      container persist-state {
        description
          "Drop TCP sessions in persist too long";
        leaf min-system-memory {
          type uint16 {
            range "1..32767";
          }
          default "50";
          description
            "Drop sessions if system memory is less than this";
        }
        leaf timeout {
          type uint16 {
            range "1..32767";
          }
          default "600";
          description
            "Drop sessions that are in persist for longer than
             this";
        }
      }
      container keepalive {
        description
          "Modify TCP keepalive parameters";
        leaf idle {
          type uint16 {
            range "1..14400";
          }
          default "14400";
          description
            "Set keepalive idle time";
        }
        leaf interval {
          type uint16 {
            range "1..300";
          }
          default "150";
          description
            "Set keepalive interval time";
        }
        leaf count {
          type uint8 {
            range "1..32";
          }
          default "8";
          description
            "Set keepalive count";
        }
      }
    }
  }

  augment "/ctxsipos:contexts/ctxipos:context/ctxipos:ip" {
    description
      "ericsson-iprouting";
    /*
    default-network (def-prefix)
    */
    leaf default-network {
      type inet:ipv4-prefix;
      description
        "Flags networks as candidates for default routes";
    }
    /*
    martian (martian-prefix) [ ge (ge-value) | le (le-value) |
     eq (eq-value) ]
    */
    list martian {
      key "martian-prefix";
      description
        "Martian network, ignore routing information";
      leaf martian-prefix {
        type inet:ipv4-prefix;
        description
          "Martian network";
      }
      choice martian-opt {
        description
          "IPOS choice";
        case ge {
          leaf ge {
            type uint8 {
              range "1..32";
            }
            must "number(.) >= number(substring-after(../"
            + "martian-prefix, '/'))" {
              error-message "invalid length or prefix "
              + "range.Ensure 32 >= le-val >= ge-val >= len >= 0";
              description
                "";
            }
            description
              "Prefix length greater than or equal
               specification";
          }
        }
        case le {
          leaf le {
            type uint8 {
              range "1..32";
            }
            must "number(.) >= number(substring-after(../"
            + "martian-prefix, '/'))" {
              error-message "invalid length or prefix "
              + "range.Ensure 32 >= le-val >= ge-val >= len >= 0";
              description
                "";
            }
            description
              "Prefix length less than or equal specification";
          }
        }
        case eq {
          leaf eq {
            type uint8 {
              range "1..32";
            }
            must "number(.) >= number(substring-after(../"
            + "martian-prefix, '/'))" {
              error-message "invalid length or prefix "
              + "range.Ensure 32 >= le-val >= ge-val >= len >= 0";
              description
                "";
            }
            description
              "Prefix length equal specification";
          }
        }
      }
    }
    /*
    maximum-routes  { multicast (multicast) [ multicast-opt-set
     { threshold (threshold) [ mid-threshold (mid-threshold) ] |
     log-only } ] | { vpn (rt-num) | (rt-num) } [ vpn-rt-opt-set
     { threshold (threshold) [ mid-threshold (mid-threshold) ] |
     log-only } ] }
    */
    container maximum-routes {
      description
        "Maximum number of routes for a table";
      container multicast {
        description
          "Set maximum limit for unicast routes in multicast
           topology";
        leaf multicast {
          type uint32 {
            range "1..4294967295";
          }
          description
            "Route limit";
        }
        container multicast-opt-set {
          when "(../multicast)" {
            description
              "";
          }
          description
            "Set multicast option configuration.";
          choice multicast-opt-set {
            description
              "IPOS choice";
            case threshold {
              container threshold {
                description
                  "Percentage of limit to start high-threshold
                   warnings";
                leaf threshold {
                  type uint8 {
                    range "1..100";
                  }
                  mandatory true;
                  description
                    "High-threshold value";
                }
                leaf mid-threshold {
                  when "(../threshold)" {
                    description
                      "";
                  }
                  type uint8 {
                    range "1..100";
                  }
                  description
                    "Percentage of limit to start mid-threshold
                     warnings";
                }
              }
            }
            case log-only {
              leaf log-only {
                type empty;
                description
                  "Generate warning messages only";
              }
            }
          }
        }
      }
      container ipos-choice {
        description
          "container ipos-choice.";
        choice ipos-choice-choice {
          description
            "IPOS choice";
          case vpn {
            leaf vpn {
              when "../../../../ctxipos:context-name='local'" {
                description
                  "";
              }
              type uint32 {
                range "1..4294967295";
              }
              description
                "set maximum route limit for all non-local
                 context unicast table";
            }
          }
          case rt-num {
            leaf rt-num {
              type uint32 {
                range "1..4294967295";
              }
              description
                "route limit";
            }
          }
        }
        container vpn-rt-opt-set {
          when "((../vpn) or (../rt-num))" {
            description
              "";
          }
          description
            "Set vpn or route number option configuration.";
          choice vpn-rt-opt-set {
            description
              "IPOS choice";
            case threshold {
              container threshold {
                description
                  "Percentage of limit to start high-threshold
                   warnings";
                leaf threshold {
                  type uint8 {
                    range "1..100";
                  }
                  mandatory true;
                  description
                    "high-threshold value";
                }
                leaf mid-threshold {
                  when "(../threshold)" {
                    description
                      "";
                  }
                  type uint8 {
                    range "1..100";
                  }
                  description
                    "Percentage of limit to start mid-threshold
                     warnings";
                }
              }
            }
            case log-only {
              leaf log-only {
                type empty;
                description
                  "Generate warning messages only";
              }
            }
          }
        }
      }
    }
    /*
    mstatic-rpf-ip-addr (src-prefix) (rpf-ip-addr) [ (mrt-dist)
     ]
    */
    list mstatic-rpf-ip-addr {
      key "src-prefix rpf-ip-addr";
      description
        "Static route for multicast RPF lookup (IP address used
         for RPF lookup)";
      leaf src-prefix {
        type inet:ipv4-prefix;
        description
          "Source address and network mask";
      }
      leaf rpf-ip-addr {
        type inet:ipv4-address;
        description
          "RPF neighbor address or route";
      }
      leaf mrt-dist {
        type uint8 {
          range "1..255";
        }
        description
          "Administrative distance for mstatic";
      }
    }
    /*
    mstatic-rpf-ifname (src-prefix) (rpf-ifname) [ (mrt-dist) ]
    */
    list mstatic-rpf-ifname {
      key "src-prefix rpf-ifname";
      description
        "Static route for multicast RPF lookup (interface name
         used for RPF lookup).";
      leaf src-prefix {
        type inet:ipv4-prefix;
        description
          "Source address and network mask";
      }
      leaf rpf-ifname {
        type string;
        must "/if:interfaces/if:interface/if:name=concat(.,'@',../"
        + "../../ctxipos:context-name)" {
          error-message "The invalid interface, or the interface "
          + "deleted is being used";
          description
            "";
        }
        description
          "Interface name used for the RPF lookup.";
      }
      leaf mrt-dist {
        type uint8 {
          range "1..255";
        }
        description
          "Administrative distance for mstatic";
      }
    }
    /*
    soft-gre [ source (gre-src) ]
    */
    container soft-gre {
      presence "";
      description
        "Configure soft GRE";
      leaf source {
        type inet:ipv4-address;
        description
          "Source address for soft GRE tunnel";
      }
    }
  }

  augment "/ctxsipos:contexts/ctxipos:context/ctxipos:ipv6" {
    description
      "ericsson-iprouting";
    /*
    maximum-routes { multicast (multicast) [ multicast-opt-set {
     threshold (threshold) [ mid-threshold (mid-threshold) ] |
     log-only } ] | { vpn (rt-num) | (rt-num) } [ vpn-rt-opt-set
     { threshold (threshold) [ mid-threshold (mid-threshold) ] |
     log-only } ] }
    */
    container maximum-routes {
      description
        "Maximum number of routes for a table";
      container multicast {
        description
          "Set maximum limit for unicast routes in multicast
           topology";
        leaf multicast {
          type uint32 {
            range "1..4294967295";
          }
          description
            "Route limit";
        }
        container multicast-opt-set {
          when "(../multicast)" {
            description
              "";
          }
          description
            "Set multicast option configuration.";
          choice multicast-opt-set {
            description
              "IPOS choice";
            case threshold {
              container threshold {
                description
                  "Percentage of limit to start high-threshold
                   warnings";
                leaf threshold {
                  type uint8 {
                    range "1..100";
                  }
                  mandatory true;
                  description
                    "High-threshold value";
                }
                leaf mid-threshold {
                  when "(../threshold)" {
                    description
                      "";
                  }
                  type uint8 {
                    range "1..100";
                  }
                  description
                    "Percentage of limit to start mid-threshold
                     warnings";
                }
              }
            }
            case log-only {
              leaf log-only {
                type empty;
                description
                  "Generate warning messages only";
              }
            }
          }
        }
      }
      container ipos-choice {
        description
          "container ipos-choice.";
        choice ipos-choice-choice {
          description
            "IPOS choice";
          case vpn {
            leaf vpn {
              when "../../../../ctxipos:context-name='local'" {
                description
                  "";
              }
              type uint32 {
                range "1..4294967295";
              }
              description
                "set maximum route limit for all non-local
                 context unicast table";
            }
          }
          case rt-num {
            leaf rt-num {
              type uint32 {
                range "1..4294967295";
              }
              description
                "Route limit";
            }
          }
        }
        container vpn-rt-opt-set {
          when "((../vpn) or (../rt-num))" {
            description
              "";
          }
          description
            "Set vpn or route number option configuration.";
          choice vpn-rt-opt-set {
            description
              "IPOS choice";
            case threshold {
              container threshold {
                description
                  "Percentage of limit to start high-threshold
                   warnings";
                leaf threshold {
                  type uint8 {
                    range "1..100";
                  }
                  mandatory true;
                  description
                    "High-threshold value";
                }
                leaf mid-threshold {
                  when "(../threshold)" {
                    description
                      "";
                  }
                  type uint8 {
                    range "1..100";
                  }
                  description
                    "Percentage of limit to start mid-threshold
                     warnings";
                }
              }
            }
            case log-only {
              leaf log-only {
                type empty;
                description
                  "Generate warning messages only";
              }
            }
          }
        }
      }
    }
    /*
    pool threshold {absolute falling (first-threshold) { trap |
     log | trap-log } [(second-threshold) { trap | log | trap-log
     }] | percentage falling (first-threshold) { trap | log |
     trap-log } [(second-threshold) { trap | log | trap-log }]}
    */
    container pool-threshold {
      description
        "Configure IPv6 pool threshold";
      choice pool-threshold {
        description
          "Choice absolute or percentage";
        case absolute-falling {
          container absolute-falling {
            presence "";
            description
              "Configure falling threshold";
            leaf first-threshold {
              type uint32 {
                range "0..4294967295";
              }
              mandatory true;
              description
                "Falling threshold value";
            }
            choice trap-log-choice {
              mandatory true;
              description
                "Choice of trap and/or log";
              case trap {
                leaf trap {
                  type empty;
                  description
                    "Generate SNMP trap";
                }
              }
              case log {
                leaf log {
                  type empty;
                  description
                    "Generate log message";
                }
              }
              case trap-log {
                leaf trap-log {
                  type empty;
                  description
                    "Generate SNMP trap and log message";
                }
              }
            }
            container second-threshold-option {
              presence "";
              description
                "Configure second falling threshold";
              leaf second-threshold {
                type uint32 {
                  range "0..4294967295";
                }
                mandatory true;
                description
                  "Second falling threshold value";
              }
              choice trap-log-choice {
                mandatory true;
                description
                  "Choice of trap and/or log";
                case trap {
                  leaf trap {
                    type empty;
                    description
                      "Generate SNMP trap";
                  }
                }
                case log {
                  leaf log {
                    type empty;
                    description
                      "Generate log message";
                  }
                }
                case trap-log {
                  leaf trap-log {
                    type empty;
                    description
                      "Generate SNMP trap and log message";
                  }
                }
              }
            }
          }
        }
        case percentage-falling {
          container percentage-falling {
            presence "";
            description
              "Configure falling threshold";
            leaf first-threshold {
              type uint8 {
                range "0..100";
              }
              mandatory true;
              description
                "Falling threshold value";
            }
            choice trap-log-choice {
              mandatory true;
              description
                "Choice of trap and/or log";
              case trap {
                leaf trap {
                  type empty;
                  description
                    "Generate SNMP trap";
                }
              }
              case log {
                leaf log {
                  type empty;
                  description
                    "Generate log message";
                }
              }
              case trap-log {
                leaf trap-log {
                  type empty;
                  description
                    "Generate SNMP trap and log message";
                }
              }
            }
            container second-threshold-option {
              presence "";
              description
                "Configure second falling threshold";
              leaf second-threshold {
                type uint8 {
                  range "0..100";
                }
                mandatory true;
                description
                  "Second falling threshold value";
              }
              choice trap-log-choice {
                mandatory true;
                description
                  "Choice of trap and/or log";
                case trap {
                  leaf trap {
                    type empty;
                    description
                      "Generate SNMP trap";
                  }
                }
                case log {
                  leaf log {
                    type empty;
                    description
                      "Generate log message";
                  }
                }
                case trap-log {
                  leaf trap-log {
                    type empty;
                    description
                      "Generate SNMP trap and log message";
                  }
                }
              }
            }
          }
        }
      }
    }
  }

}
