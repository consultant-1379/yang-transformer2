module ericsson-rmon-ipos {
  yang-version "1.1";

  namespace "urn:rdns:com:ericsson:oammodel:ericsson-rmon-ipos";

  prefix "rmonipos";

  import ericsson-contexts-ipos {
    prefix "ctxsipos";
  }

  import ericsson-yang-extensions {
    prefix "yexte";
  }

  organization
    "Ericsson AB";

  contact
    "Web:   <http://www.ericsson.com>";

  description
    "This module contains a collection of YANG definitions for
     remote network monitoring. Copyright (c) 2019 Ericsson AB.
     All rights reserved";

  revision "2019-07-04" {
    description
      "Update yang version 1.0 to 1.1";
    reference
      "rfc7950";
    yexte:version "1";
    yexte:release "0";
    yexte:correction "2";
  }

  revision "2018-07-10" {
    description
      "YANG model description correction";
    reference
      "RFC 6020";
    yexte:version "1";
    yexte:release "0";
    yexte:correction "1";
  }

  revision "2017-07-03" {
    description
      "Update the description of alarm-sample-type.";
    reference
      "RFC 6020";
    yexte:version "1";
    yexte:release "0";
    yexte:correction "0";
  }

  revision "2016-12-27" {
    description
      "Initial revision";
    reference
      "RFC 2819";
  }

  augment "/ctxsipos:contexts" {
    description
      "ericsson-rmon";
    /*
    rmon
    */
    container rmon {
      description
        "RMON alarm and event configuration parameters";
      list alarm {
        key "alarm-index";
        description
          "The list of configured RMON alarms on the device";
        leaf alarm-index {
          type uint16 {
            range "1..65535";
          }
          description
            "Index that uniquely identifies an alarm event with
             an entry in the alarm list. Each such entry defines
             a diagnostic sample at a particular interval for an
             object on the device";
        }
        leaf alarm-oid {
          type string;
          mandatory true;
          description
            "The object identifier of the particular variable to
             be sampled";
        }
        leaf alarm-interval {
          type uint32 {
            range "1..2147483647";
          }
          mandatory true;
          description
            "The interval in seconds over which the data is
             sampled and compared with the rising and falling
             thresholds";
        }
        choice alarm-sample-type {
          mandatory true;
          description
            "The method of sampling the selected variable and
             calculating the value to be compared against the
             thresholds.";
          case delta {
            leaf delta {
              type empty;
              mandatory true;
              description
                "Compares the difference between successive
                 samples of the object value against the
                 threshold value";
            }
          }
          case absolute {
            leaf absolute {
              type empty;
              mandatory true;
              description
                "Compares the actual object value against the
                 threshold value";
            }
          }
        }
        leaf rising-threshold {
          type uint32 {
            range "0..2147483647";
          }
          mandatory true;
          description
            "A threshold for the sampled statistic.When the
             current sampled value is greater than or equal to
             this threshold, and the value at the last sampling
             interval was less than this threshold, a single
             event will be generated";
        }
        leaf rising-event {
          type uint16 {
            range "1..65535";
          }
          description
            "Index of the entry in the event list that is
             associated with the alarm event";
        }
        leaf falling-threshold {
          type uint32 {
            range "0..2147483647";
          }
          mandatory true;
          description
            "A threshold for the sampled statistic.When the
             current sampled value is less than or equal to this
             threshold, and the value at the last sampling
             interval was greater than this threshold, a single
             event will be generated";
        }
        leaf falling-event {
          type uint16 {
            range "1..65535";
          }
          description
            "Index of the entry in the event list that is
             associated with the alarm event";
        }
        leaf owner {
          type string {
            length "1..127";
          }
          description
            "Name of the alarm owner";
        }
      }
      list event {
        key "event-index";
        description
          "A list of events to be generated";
        leaf event-index {
          type uint16 {
            range "1..65535";
          }
          description
            "An index that uniquely identifies an entry in the
             event table";
        }
        leaf log {
          type empty;
          description
            "This event generates an entry in the RMON MIB log
             table";
        }
        leaf notify {
          type empty;
          description
            "This event generates an SNMP notification";
        }
        leaf owner {
          type string {
            length "1..127";
          }
          description
            "Owner of the event";
        }
        leaf description {
          type string {
            length "1..127";
          }
          description
            "A comment describing this event entry";
        }
      }
    }
  }

}
