module ericsson-schedulingprofile-du-cr {
    yang-version 1.1;
    namespace "urn:rdns:com:ericsson:oammodel:ericsson-schedulingprofile-du-cr";
    prefix "schedulingprofile";

    import _3gpp-common-managed-element {
        prefix me3gpp;
    }
    import _3gpp-common-top {
        prefix top3gpp;
    }
    import _3gpp-common-yang-types {
        prefix types3gpp;
    }
    import _3gpp-nr-nrm-gnbdufunction {
        prefix gnbdu3gpp;
    }
    import ericsson-uecc-du-cr {
        prefix uecc;
    }
    import ericsson-yang-extensions {
        prefix yexte;
    }
    import ietf-inet-types {
        prefix "inet";
    }

    organization
      "Ericsson AB";
    contact
      "Ericsson first line support via email";
    description
      "Defines the YANG mapping of the SchedulingProfile.
       
       Copyright (c) 2021 Ericsson AB. All rights reserved.";
    revision 2021-06-17 {
        description
          "First version.";
        yexte:version 0;
        yexte:release 1;
        yexte:correction 0;
    }

    yexte:module-status preliminary;

    grouping SchedulingProfileGrp {
        description
          "Represents the SchedulingProfile IOC.";
        leaf relativePriority {
            description
              "Relative priority associated with scheduling profile.";
            type int32 {
                range "1..256";
            }
            default "1";
            yexte:takes-effect "New connection";
            status current {
                yexte:preliminary;
            }
        }

        leaf relativePriorityMode {
            description
              "Input parameter for scheduling weight calculation.";
            type enumeration {
                enum RP_ONLY {
                    value 0;
                    description
                      "Scheduling weight impact from relativePriority attribute.";
                }
                enum PDB_ONLY {
                    value 1;
                    description
                      "Scheduling weight impact from packetDelayBudget attribute.";
                }
                enum RP_AND_PDB {
                    value 2;
                    description
                      "Scheduling weight impact from relativePriority and packetDelayBudget attributes.";
                }
            }
            default "RP_ONLY";
            yexte:takes-effect "New connection";
            status current {
                yexte:preliminary;
            }
        }

        leaf userLabel {
            description
              "Label for free use.";
            type string;
        }
    }

    augment "/me3gpp:ManagedElement/gnbdu3gpp:GNBDUFunction/uecc:UeCC" {
        list SchedulingProfile {
            description
              "Mapping from 5G QoS priorities to parameters that have impact on QoS.";

            key id;
            uses top3gpp:Top_Grp;
            max-elements 32;
            container attributes {
                uses SchedulingProfileGrp;
            }
        }
    }
}
