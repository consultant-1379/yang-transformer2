module ericsson-uecc-du-cr {
    yang-version 1.1;
    namespace "urn:rdns:com:ericsson:oammodel:ericsson-uecc-du-cr";
    prefix "uecc";

    import _3gpp-common-managed-element {
        prefix me3gpp;
    }
    import _3gpp-common-top {
        prefix top3gpp;
    }
    import _3gpp-common-yang-types {
        prefix types3gpp;
    }
    import _3gpp-nr-nrm-gnbdufunction {
        prefix gnbdu3gpp;
    }
    import ericsson-yang-extensions {
        prefix yexte;
    }
    import ietf-inet-types {
        prefix "inet";
    }

    organization
      "Ericsson AB";
    contact
      "Ericsson first line support via email";
    description
      "Defines the YANG mapping of the UE Connection Control.
       
       Copyright (c) 2021 Ericsson AB. All rights reserved.";
    revision 2021-06-17 {
        description
          "First version.";
        yexte:version 0;
        yexte:release 1;
        yexte:correction 0;
    }

    yexte:module-status preliminary;

    augment "/me3gpp:ManagedElement/gnbdu3gpp:GNBDUFunction" {
        description
          "Adds Ericsson IOC UeCC to 3gpp DU function.";
        list UeCC {
            description
              "Container class for UE connection control attributes and profile classes.
               
               The RDN of this MO must always be UeCC=1";
            key id;
            uses top3gpp:Top_Grp {
                refine id {
                    must '. = "1"' {
                        error-message
                          "RDN must be 1";
                    }
                }
            }
            max-elements 1;
        }
    }
}
