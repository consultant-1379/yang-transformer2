module _3gpp-nr-nrm-gnbdufunction {
  yang-version 1.1;
  namespace "urn:3gpp:sa5:_3gpp-nr-nrm-gnbdufunction";
  prefix "gnbdu3gpp";

  import _3gpp-common-managed-function { prefix mf3gpp; }
  import _3gpp-common-managed-element { prefix me3gpp; }
  import _3gpp-common-top { prefix top3gpp; }

  organization "3GPP SA5";
  description "Defines the YANG mapping of the GNBDUFunction Information
    Object Class (IOC) that is part of the NR Network Resource Model (NRM).";
  reference "3GPP TS 28.541 5G Network Resource Model (NRM)";

  revision 2019-08-21 {
    description "Initial revision.";
    reference "Based on
      3GPP TS 28.541 V15.X.XX";
  }

  grouping GNBDUFunctionGrp {
    description "Represents the GNBDUFunction IOC.";
    reference "3GPP TS 28.541";
    uses mf3gpp:ManagedFunctionGrp; 

    leaf gNBId {
      type int64 { range "0..4294967295"; }
      mandatory true;
      description "Identifies a gNB within a PLMN. The gNB Identifier (gNB ID)
        is part of the NR Cell Identifier (NCI) of the gNB cells.";
      reference "gNB ID in 3GPP TS 38.300, Global gNB ID in 3GPP TS 38.413";
    }

    leaf gNBIdLength {
      type int32 { range "22..32"; }
      mandatory true;
      description "Indicates the number of bits for encoding the gNB ID.";
      reference "gNB ID in 3GPP TS 38.300, Global gNB ID in 3GPP TS 38.413";
    }

    leaf gNBDUId {
      type int64 { range "0..68719476735"; }
      mandatory true;
      description "Uniquely identifies the DU at least within a gNB.";
      reference "3GPP TS 38.473";
    }
            
    leaf gNBDUName {
      type string { length "1..150"; }
      mandatory true;
      description "Identifies the Distributed Unit of an NR node";
      reference "3GPP TS 38.473";
    }		
  }

  augment "/me3gpp:ManagedElement" {

    list GNBDUFunction {
      key id;
      description "Represents the logical function DU of gNB or en-gNB.";
      reference "3GPP TS 28.541";
      uses top3gpp:Top_Grp;
      container attributes {
        uses GNBDUFunctionGrp;
      }
    }
  }
}
