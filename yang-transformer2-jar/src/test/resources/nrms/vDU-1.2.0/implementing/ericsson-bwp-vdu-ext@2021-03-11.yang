module ericsson-bwp-vdu-ext {
  yang-version 1.1;
  namespace urn:rdns:com:ericsson:oammodel:ericsson-bwp-vdu-ext;
  prefix bwp3gppext;

  import _3gpp-common-managed-element { prefix me3gpp; }
  import _3gpp-nr-nrm-gnbdufunction { prefix gnbdu3gpp; }
  import _3gpp-nr-nrm-bwp { prefix bwp3gpp; }
  import ericsson-yang-extensions { prefix yexte; }
  import _3gpp-common-yang-types { prefix types3gpp; }

  organization
    "Ericsson AB";
  contact
    "Ericsson first line support via email";
  description
    "The module defines the BWP data model additional leafs for the Ericsson vDU.

    Copyright (c) 2020 Ericsson AB. All rights reserved.";

  revision 2021-03-11 {
    description
      "Copy of ericsson-bwp-vdu-add@2020-12-17.yang";
    yexte:version 0;
    yexte:release 1;
    yexte:correction 0;
    reference
      "RFC 7950: The YANG 1.1 Data Modeling Language";
  }

  yexte:module-status preliminary;

  grouping BWPVduGrp {
    description "Ericsson extensions to the 3gpp BWP IOC.";
    reference "Ericsson documentation";
       
    leaf pZeroNomPuschGrant {
      description "Power control parameter P0 Nominal for PUSCH transmissions with grant. Only applicable for uplink bwpContext.";
      type int32 { range "-202..24"; }
      must ". mod 2 = 0" {
        description
          "The value must set with resolution/step of 2.";
      }
      default -100;
      reference "3GPP TS 38.331";
      units dBm;
    }

    leaf pZeroNomPucch {
      description "Power control parameter P0 Nominal for PUCCH transmissions. Only applicable for uplink bwpContext.";
      type int32 { range "-202..24"; }
      must ". mod 2 = 0" {
        description
          "The value must set with resolution/step of 2.";
      }
      default -114;
      reference "3GPP TS 38.331";
      units dBm;
    }

    leaf enable256QAM {
      description "Enables 256 QAM support in BWP.";
      type boolean;
      default false;
    }

    leaf pZeroUePuschOffset256Qam   {
      description "Power offset to target-received PUSCH PSD for 256-QAM-capable UEs.
      Relevant when 256-QAM MCS Table 5.1.3.1-2 in 3GPP TS 38.214 is used.
      Controls received SINR target.
      Only applicable if enable256QAM for uplink BWP is true.";
      type int32 { range "0..15"; }
      default 0;
      reference "3GPP TS 38.214";
      units dB;
    }
  }

  augment "/me3gpp:ManagedElement/gnbdu3gpp:GNBDUFunction/bwp3gpp:BWP/bwp3gpp:attributes" {
    description "Adds Ericsson attributes to 3gpp BWP";
    uses BWPVduGrp;
  }
}
