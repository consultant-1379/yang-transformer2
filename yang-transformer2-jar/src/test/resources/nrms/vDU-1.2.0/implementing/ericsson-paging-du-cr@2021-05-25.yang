module ericsson-paging-du-cr{
  yang-version 1.1;
  namespace "urn:rdns:com:ericsson:oammodel:ericsson-paging-du-cr";
  prefix "pagingducr";

  import _3gpp-common-managed-function { prefix mf3gpp; }
  import _3gpp-common-managed-element { prefix me3gpp; }
  import _3gpp-common-top { prefix top3gpp; }
  import _3gpp-nr-nrm-gnbdufunction { prefix gnbdu3gpp; }
  import ericsson-yang-extensions { prefix yexte; }
  
    organization
      "Ericsson AB";
    contact
      "Ericsson first line support via email";
    description
      "Defines the YANG mapping of the Paging.

       Copyright (c) 2021 Ericsson AB. All rights reserved.";
  revision 2021-05-25 {
    description 
	"Initial revision.";
    yexte:version 0;
    yexte:release 1;
    yexte:correction 0;
    reference "Based on
      3GPP TS 38.331 V15.X.XX";
  }

  grouping PagingGrp {
    description "Represents the paging IOC.";
    reference "3GPP TS 38.331";
    uses mf3gpp:ManagedFunctionGrp;
        
    leaf defaultPagingCycle {
      description "Paging cycle T. Used by the vDU and broadcasted in SIB1."; 
      type int32 { range "32 | 64 | 128 | 256";}
      default 128;
      yexte:takes-effect
        "Next cell unlock";
      reference "3GPP TS 38.331";
    }

    leaf n {
      description "Number of Paging Frames in the DRX Cycle.";
      type int32 { range "1 | 2 | 4 | 8 | 16";}
      default 1;
      yexte:takes-effect
        "Next cell unlock";
      reference "3GPP TS 38.331";
    }

    leaf nS{
      description "Number of Paging Occasion for one Paging Frame.";
      type int32 { range "1 | 2 | 4";}
      default 1;
       yexte:dependencies "For ESS cells, value 4 is not allowed.";
      yexte:takes-effect
        "Next cell unlock";
      reference "3GPP TS 38.331";
    }
  }

  augment "/me3gpp:ManagedElement/gnbdu3gpp:GNBDUFunction" {

    list Paging {
      description "Represents the configuration parameter for paging in a DU.";
      reference "3GPP TS 38.331";
      key id;
      max-elements 1;
      uses top3gpp:Top_Grp;
      container attributes {
        uses PagingGrp;
      }
    }
  }
}
