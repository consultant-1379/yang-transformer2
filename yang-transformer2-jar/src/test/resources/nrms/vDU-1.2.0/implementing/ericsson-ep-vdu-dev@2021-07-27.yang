module ericsson-ep-vdu-dev {
  yang-version 1.1;
  namespace urn:rdns:com:ericsson:oammodel:ericsson-ep-vdu-dev;
  prefix ep3gppdev;

  import _3gpp-common-managed-element { prefix me3gpp; }
  import _3gpp-nr-nrm-gnbcucpfunction { prefix gnbcucp3gpp; }
  import _3gpp-nr-nrm-gnbcuupfunction { prefix gnbcuup3gpp; }
  import _3gpp-nr-nrm-gnbdufunction { prefix gnbdu3gpp; }
  import _3gpp-nr-nrm-ep { prefix ep3gpp; }
  import ericsson-notifications { prefix notife; }
  import ericsson-yang-extensions { prefix yexte; }

  organization
    "Ericsson AB";
  contact
    "Ericsson first line support via email";
  description
    "The module defines 3GPP EP data model deviations for the Ericsson vDU.

    Copyright (c) 2020 Ericsson AB. All rights reserved.";

  revision 2021-07-27 {
    description
      "Bug Fix, leaf-list state notifiable compatibility issue. Adds extension notife:notifiable-state-data false to supportedGPs.";
    yexte:version 1;
    yexte:release 1;
    yexte:correction 0;
    reference
      "RFC 7950: The YANG 1.1 Data Modeling Language";
  }
  
  revision 2021-05-12 {
    description
      "Deviations on _3gpp-nr-nrm-ep.";
    yexte:version 0;
    yexte:release 1;
    yexte:correction 0;
    reference
      "RFC 7950: The YANG 1.1 Data Modeling Language";
  }

  deviation /me3gpp:ManagedElement/gnbcucp3gpp:GNBCUCPFunction {
    description
      "GNBCUCPFunction not supported in Ericsson vDU";
    deviate not-supported;
  }
  
  deviation /me3gpp:ManagedElement/gnbcuup3gpp:GNBCUUPFunction {
    description
      "GNBCUUPFunction not supported in Ericsson vDU";
    deviate not-supported;
  }
  
  deviation /me3gpp:ManagedElement/gnbdu3gpp:GNBDUFunction/ep3gpp:EP_F1U {
    description
      "EP_F1U not supported in Ericsson vDU";
    deviate not-supported;
  }
  
  deviation /me3gpp:ManagedElement/gnbdu3gpp:GNBDUFunction/ep3gpp:EP_F1C/ep3gpp:attributes/ep3gpp:supportedMeasurementsGPs/ep3gpp:supportedGPs {
    deviate add {
      notife:notifiable-state-data false;
    }
  }
}
