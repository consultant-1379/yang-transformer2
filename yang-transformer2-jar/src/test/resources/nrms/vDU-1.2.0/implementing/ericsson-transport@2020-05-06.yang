module ericsson-transport {
	yang-version 1.1;
	namespace urn:rdns:com:ericsson:oammodel:ericsson-transport;
	prefix tn;
	
	import ericsson-yang-extensions { prefix yexte; }	

  	organization "Ericsson AB";
	contact "Ericsson first line support via email.";
	description 
		"The module implements transport network.
		
		It is recommended to review design-time defaults including used groupings
		and deviate them based on implementation needs.

		Copyright (c) 2020 Ericsson AB. All rights reserved.";

	revision "2020-05-06" {
        //preliminary
	    description "
	    	- model using ietf-system";
		yexte:version 1;
		yexte:release 0;
		yexte:correction 0;
	}
	
	container transport {
		description
			"This is a container for common transport functions used";
                leaf transportId {
                        type string;
                        description
                                "Holds the name used when identifying the MO";
                }
	}
}
