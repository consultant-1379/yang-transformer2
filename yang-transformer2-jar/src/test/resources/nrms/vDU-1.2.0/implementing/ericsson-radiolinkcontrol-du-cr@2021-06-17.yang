module ericsson-radiolinkcontrol-du-cr {
    yang-version 1.1;
    namespace "urn:rdns:com:ericsson:oammodel:ericsson-radiolinkcontrol-du-cr";
    prefix "rlc";

    import _3gpp-common-managed-element {
        prefix me3gpp;
    }
    import _3gpp-common-top {
        prefix top3gpp;
    }
    import _3gpp-common-yang-types {
        prefix types3gpp;
    }
    import _3gpp-nr-nrm-gnbdufunction {
        prefix gnbdu3gpp;
    }
    import ericsson-uecc-du-cr {
        prefix uecc;
    }
    import ericsson-yang-extensions {
        prefix yexte;
    }
    import ietf-inet-types {
        prefix "inet";
    }

    organization
      "Ericsson AB";
    contact
      "Ericsson first line support via email";
    description
      "Defines the YANG mapping of the RadioLinkControl.
       
       Copyright (c) 2020 Ericsson AB. All rights reserved.";
    revision 2021-06-17 {
        description
          "First version.";
        yexte:version 0;
        yexte:release 1;
        yexte:correction 0;
    }

    yexte:module-status preliminary;

    augment "/me3gpp:ManagedElement/gnbdu3gpp:GNBDUFunction/uecc:UeCC" {
        list RadioLinkControl {
            description
              "Container for radio bearer configurations.
               
               The RDN of this MO must always be RadioLinkControl=1";
            key id;
            uses top3gpp:Top_Grp {
                refine id {
                    must '. = "1"' {
                        error-message
                          "RDN must be 1";
                    }
                }
            }
            max-elements 1;
        }
    }
}
