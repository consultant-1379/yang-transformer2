module _3gpp-common-managed-function {
  yang-version 1.1;
  namespace urn:3gpp:sa5:_3gpp-common-managed-function;
  prefix mf3gpp;
  
  organization "3GPP SA5";
  description "The module defines a base class/grouping for major 3GPP functions.";
  reference 
    "3GPP TS 28.622 
    Generic Network Resource Model (NRM)
    Integration Reference Point (IRP);
    Information Service (IS)
    
    3GPP TS 28.620 
    Umbrella Information Model (UIM)";

  revision 2019-06-18 {
    description "Initial revision";
    reference "Based on
      3GPP TS 28.620 V15.X.XX
      3GPP TS 28.622 V15.X.XX ";
  }
  
  grouping Function_Grp {    
    description "A base grouping for 3GPP functions.";

    leaf userLabel {
        type string;
        description "A user-friendly (and user assignable) name of this object.";
    }      
  }
  
  grouping ManagedFunctionGrp {
    description "Abstract root class to be inherited/reused by classes 
      representing 3GPP functions.";

    uses Function_Grp;
    
    container vnfParametersList {
      description "Contains the parameter set of the VNF 
        instance(s) corresponding to an NE.";
      presence "The presence of this container indicates that the ManagedFunction 
        represented is realized by one or more VNF instance(s). Otherwise it  
        shall be absent.";        
        
      leaf vnfInstanceId {
        type string ;
        mandatory true;
        description "VNF instance identifier";
        reference "ETSI GS NFV-IFA 008 v2.1.1: 
          Network Functions Virtualisation (NFV); Management and Orchestration; 
          Ve-Vnfm reference point - Interface and Information Model Specification
          section 9.4.2 
          
          ETSI GS NFV-IFA 015 v2.1.2: Network Functions Virtualisation (NFV); 
          Management and Orchestration; Report on NFV Information Model
          section B2.4.2.1.2.3";
      }
      
      leaf vnfdId {
        type string ;
        description "Identifier of the VNFD on which the VNF instance is based.
          The absence of the leaf or a string length of zero for vnfInstanceId 
          means the VNF instance(s) does not exist (e.g. has not been 
          instantiated yet, has already been terminated).";
        reference "ETSI GS NFV-IFA 008 v2.1.1: 
          Network Functions Virtualisation (NFV); Management and Orchestration; 
          Ve-Vnfm reference point - Interface and Information Model Specification
          section 9.4.2"; 
      }
      
      leaf flavourId {
        type string ;
        description "Identifier of the VNF Deployment Flavour applied to this 
          VNF instance.";
        reference "ETSI GS NFV-IFA 008 v2.1.1: 
          Network Functions Virtualisation (NFV); Management and Orchestration; 
          Ve-Vnfm reference point - Interface and Information Model Specification
          section 9.4.3"; 
      }
      
      leaf autoScalable                        {
        type boolean ;
        mandatory true;
        description "Indicator of whether the auto-scaling of this 
          VNF instance is enabled or disabled.";
      } 
    }
    
    container peeParametersList {
      description "Contains the parameter set for the control 
        and monitoring of power, energy and environmental parameters of 
        ManagedFunction instance(s).";
      presence "Present supported if the control and monitoring of PEE 
        parameters is supported by the ManagedFunction or sub-class instance.";
        
      leaf siteIdentification {
        type string;
        mandatory true;
        description "The identification of the site where the 
          ManagedFunction resides.";
      }
      
      leaf siteLatitude {
        type decimal64 {
          fraction-digits 4;
          range "-90.0000..+90.0000";        
        }
        description "The latitude of the site where the ManagedFunction 
          instance resides, based on World Geodetic System (1984 version) 
          global reference frame (WGS 84). Positive values correspond to 
          the northern hemisphere. This attribute is optional in case of 
          BTSFunction and RNCFunction instance(s).";
      }
      
      leaf siteLongitude {
        type decimal64 {
          fraction-digits 4;
          range "-180.0000..+180.0000";        
        }
        description "The longitude of the site where the ManagedFunction 
          instance resides, based on World Geodetic System (1984 version) 
          global reference frame (WGS 84). Positive values correspond to 
          degrees east of 0 degrees longitude. This attribute is optional in 
          case of BTSFunction and RNCFunction instance(s).";
      }
      
      leaf siteDescription {
        type string;
        mandatory true;
        description "An operator defined description of the site where 
          the ManagedFunction instance resides.";
      }
      
      leaf equipmentType {
        type string;
        mandatory true;
        description "The type of equipment where the managedFunction 
          instance resides.";
        reference "clause 4.4.1 of ETSI ES 202 336-12";
      }
      
      leaf environmentType {
        type string;
        mandatory true;
        description "The type of environment where the managedFunction 
          instance resides.";
        reference "clause 4.4.1 of ETSI ES 202 336-12";
      }
      
      leaf powerInterface {
        type string;
        mandatory true;
        description "The type of power.";
        reference "clause 4.4.1 of ETSI ES 202 336-12";
      } 
    }
    
    leaf priorityLabel {
      mandatory true;
      type uint32;
    }
  }
}
