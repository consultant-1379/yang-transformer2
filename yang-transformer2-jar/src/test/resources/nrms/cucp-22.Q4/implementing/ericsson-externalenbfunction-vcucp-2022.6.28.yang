// Generated by eyang-preprocessor (1.22.0-48 2022-01-20 09:10:06 CET) on Jun 30, 2022, 8:31:37 AM
module ericsson-externalenbfunction-vcucp {
    yang-version 1.1;
    namespace "urn:rdns:com:ericsson:oammodel:ericsson-externalenbfunction-vcucp";
    prefix "extenb";

    import tailf-common {
        prefix tailf;
    }
    import _3gpp-common-managed-element {
        prefix "me3gpp";
    }
    import _3gpp-nr-nrm-gnbcucpfunction {
        prefix "gnbcucp3gpp";
    }
    import _3gpp-common-yang-types {
        prefix "types3gpp";
    }
    import _3gpp-common-top {
        prefix "top3gpp";
    }
    import _3gpp-common-yang-extensions {
        prefix yext3gpp;
    }
    import ericsson-common-types-vcucp {
        prefix "commontypes";
    }
    import ericsson-eutranetwork-vcucp {
        prefix "eutranet";
    }
    import ericsson-yang-extensions {
        prefix "yexte";
    }
    import ericsson-notifications {
        prefix "notife";
    }

    organization
        "Ericsson AB";
    contact
        "Ericsson first line support via email";
    description
        "The module defines the ExternaleNBFunction data model for the Ericsson vCU-CP.

        Copyright (c) 2021-2022 Ericsson AB. All rights reserved.";

    revision 2022-06-28 {
        description
            "Removed module-status preliminary.
             Removed preliminary status from isRemoveAllowed and noRelationTimeStamp.";
        yexte:version 1;
        yexte:release 5;
        yexte:correction 0;
        reference
            "RFC 7950: The YANG 1.1 Data Modeling Language";
    }

    revision 2022-03-14 {
        description
            "Adds attributes isRemoveAllowed and noRelationTimeStamp.
            Update description for pLMNId.";
        yexte:version 1;
        yexte:release 4;
        yexte:correction 0;
        reference
            "RFC 7950: The YANG 1.1 Data Modeling Language";
    }

    revision 2021-11-05 {
        description
            "Fix the dependencies tags, changed eNodeBId to eNBId.";
        yexte:version 1;
        yexte:release 3;
        yexte:correction 1;
        reference
            "RFC 7950: The YANG 1.1 Data Modeling Language";
    }

    revision 2021-10-15 {
        description
            "Extend externalenbfunction cardinality to 512.";
        yexte:version 1;
        yexte:release 3;
        yexte:correction 0;
        reference
            "RFC 7950: The YANG 1.1 Data Modeling Language";
    }

    revision 2021-05-06 {
        description
            "Remove is-system-created from MO and configurable attributes.
             Add yext3gpp:inVariant to eNBId.";
        yexte:version 1;
        yexte:release 2;
        yexte:correction 0;
        reference
            "RFC 7950: The YANG 1.1 Data Modeling Language";
    }

    revision 2021-03-30 {
        description
            "Add Ericsson descriptions and tags to attributes.";
        yexte:version 1;
        yexte:release 1;
        yexte:correction 1;
        reference
            "RFC 7950: The YANG 1.1 Data Modeling Language";
    }

    revision 2021-03-22 {
        description
            "Parity with ECIM R1A79.";
        yexte:version 1;
        yexte:release 1;
        yexte:correction 0;
        reference
            "RFC 7950: The YANG 1.1 Data Modeling Language";
    }

    revision 2021-01-20 {
        description
            "Add extensions is-system-created.";
        yexte:version 1;
        yexte:release 0;
        yexte:correction 0;
        reference
            "RFC 7950: The YANG 1.1 Data Modeling Language";
    }

    revision 2021-01-11 {
        description
            "Initial version of the ExternalENBFunction model.";
        yexte:version 0;
        yexte:release 1;
        yexte:correction 0;
        reference
            "RFC 7950: The YANG 1.1 Data Modeling Language";
    }

    grouping ExternalENBFunctionGrp {
        description "Represents the ExternalENBFunction IOC.";
        leaf eNBId {
            description "The ID of an RBS within a Public Land Mobile Network (PLMN).";
            mandatory true;
            yext3gpp:inVariant;
            type int32 {
                range "0..1048575";
            }
            yexte:dependencies
                "Combination of pLMNId and eNBId attributes must be unique across "+
                "ExternalENodeBFunction MO instances.";
            tailf:info 'Dependencies: Combination of pLMNId and eNBId attributes must be unique across ExternalENodeBFunction MO instances, The ID of an RBS within a Public Land Mobile Network (PLMN).';
        }

        leaf isRemoveAllowed {
            description
                "Whether ANR function can remove MO instance.

                Setting does not restrict operator to remove MO instance.
                Set to true for MO instances created by ANR.";
            type boolean;
            default false;
        }

        leaf noRelationTimeStamp {
            description
                "Point in time when this MO instance has no relation to " +
                "GNBCUCPFunction anymore.

                Periodic check compares this timestamp with " +
                "AnrFunction::removeEnbTime.

                Format: EPOCH time - Number of seconds since 1970-01-01 00:00:00 UTC.";
            config false;
            type int64;
            notife:notifiable-state-data false;
            tailf:meta-data notife:notifiable-state-data {
                tailf:meta-value false;
            }
        }

        list pLMNId {
            description
                "PLMN identifier part of global RAN node identity.

                This and eNBId form the global eNodeB ID.

                Must not be empty.

                Note: Value MCC=001, MNC=01 means PLMN is not initiated. " +
                "This value cannot be used as a valid PLMN Identity.";
            key "mcc mnc";
            max-elements 1;
            uses types3gpp:PLMNId;
            yexte:dependencies
                "Combination of pLMNId and eNBId attributes must be unique across "+
                "ExternalENodeBFunction MO instances.";
            yexte:takes-effect "New connection";
            tailf:info 'Takes effect: New connection, Dependencies: Combination of pLMNId and eNBId attributes must be unique across ExternalENodeBFunction MO instances, PLMN identifier part of global RAN node identity. This and eNBId form the global eNodeB ID. Must not be empty. Note: Value MCC=001, MNC=01 means PLMN is not initiated. This value cannot be used as a valid PLMN Identity.';
        }

        uses commontypes:UserLabelGrp;
    }

    augment "/me3gpp:ManagedElement/gnbcucp3gpp:GNBCUCPFunction/eutranet:EUtraNetwork" {
        list ExternalENBFunction {
            description
                "Representation of an eNodeB.

                This MO is created automatically. Can also be created and "+
                "deleted manually.

                Created automatically when X2 interface is set up, unless it "+
                "already exists.
                Deleted automatically.

                When created automatically, the RDN of this MO is "+
                "ExternalENBFunction=auto&lt;mcc&gt;_&lt;mnc&gt;_&lt;mncLength&gt;_&lt;eNodeBId&gt;.";
            key id;
            max-elements 512;
            uses top3gpp:Top_Grp;
            container attributes {
                uses ExternalENBFunctionGrp;
            }
        }
    }
}
