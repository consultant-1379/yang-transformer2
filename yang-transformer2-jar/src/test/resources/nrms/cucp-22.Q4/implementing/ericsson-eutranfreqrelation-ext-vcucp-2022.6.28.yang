// Generated by eyang-preprocessor (1.22.0-48 2022-01-20 09:10:06 CET) on Jun 30, 2022, 8:31:37 AM
module ericsson-eutranfreqrelation-ext-vcucp {
    yang-version 1.1;
    namespace urn:rdns:com:ericsson:oammodel:ericsson-eutranfreqrelation-ext-vcucp;
    prefix eutranfreqrel3gppext;

    import tailf-common {
        prefix tailf;
    }
    import _3gpp-common-managed-element {
        prefix me3gpp;
    }
    import _3gpp-common-yang-types {
        prefix types3gpp;
    }
    import _3gpp-nr-nrm-gnbcucpfunction {
        prefix gnbcucp3gpp;
    }
    import _3gpp-nr-nrm-nrcellcu {
        prefix nrcellcu3gpp;
    }
    import _3gpp-nr-nrm-eutranfreqrelation {
        prefix eutranfreqrel3gpp;
    }
    import _3gpp-nr-nrm-nrfreqrelation {
        prefix nrfreqrel3gpp;
    }
    import _3gpp-common-yang-extensions {
        prefix yext3gpp;
    }
    import ericsson-eutranetwork-vcucp {
        prefix eutranet;
    }
    import ericsson-eutranfrequency-vcucp {
        prefix eutranfrequency;
    }
    import ericsson-mcpc-vcucp {
        prefix mcpc;
    }
    import ericsson-mcpc-pcell-eutran-freq-rel-profile-vcucp {
        prefix mcpcpcelleutranfreqrelprofile;
    }
    import ericsson-uemc-vcucp {
        prefix uemcvcucp;
    }
    import ericsson-uemceutranfreqrelprofile-vcucp {
        prefix uemceutranfreqrelprofilevcucp;
    }
    import ericsson-yang-extensions {
        prefix yexte;
    }

    organization
        "Ericsson AB";
    contact
        "Ericsson first line support via email";
    description
        "The module defines the EUtranFreqRelation data model extensions for the Ericsson vCU-CP.

        Copyright (c) 2021-2022 Ericsson AB. All rights reserved.";

    revision 2022-06-28 {
        description
            "Removed module-status preliminary.
             Removed preliminary status from anrMeasOn";
        yexte:version 1;
        yexte:release 5;
        yexte:correction 0;
        reference
            "RFC 7950: The YANG 1.1 Data Modeling Language";
    }

    revision 2022-03-14 {
        description
             "Added attribute anrMeasOn.
             Description changed and takes-effect changed for cellReselectionPriority.
             Attribute cellReselectionSubPriority from 3gpp is now supported";
        yexte:version 1;
        yexte:release 4;
        yexte:correction 0;
        reference
            "RFC 7950: The YANG 1.1 Data Modeling Language";
    }

    revision 2021-11-05 {
        description
             "Description changed and dependencies tag added for mcpcPCellEUtranFreqRelProfileRef.
             Removed the takes-effect tag for qRxLevMin.
             Description changed and dependencies tag added for ueMCEUtranFreqRelProfileRef.";
        yexte:version 1;
        yexte:release 3;
        yexte:correction 0;
        reference
            "RFC 7950: The YANG 1.1 Data Modeling Language";
    }

    revision 2021-05-28 {
        description
             "Correct must statment on cellReselectionPriority.";
        yexte:version 1;
        yexte:release 2;
        yexte:correction 1;
        reference
            "RFC 7950: The YANG 1.1 Data Modeling Language";
    }

    revision 2021-05-06 {
        description
            "Remove is-system-created and restricted extensions from configurable attributes.
             Add yext3gpp:inVariant to eUtranFrequencyRef.";
        yexte:version 1;
        yexte:release 2;
        yexte:correction 0;
        reference
            "RFC 7950: The YANG 1.1 Data Modeling Language";
    }

    revision 2021-05-05 {
        description
            "Correct must statement for MO reference.";
        yexte:version 1;
        yexte:release 1;
        yexte:correction 4;
        reference
            "RFC 7950: The YANG 1.1 Data Modeling Language";
    }

    revision 2021-04-23 {
        description
            "Correct must statement for MO reference.";
        yexte:version 1;
        yexte:release 1;
        yexte:correction 3;
        reference
            "RFC 7950: The YANG 1.1 Data Modeling Language";
    }

    revision 2021-03-30 {
        description
            "Add Ericsson descriptions and tags to attributes.";
        yexte:version 1;
        yexte:release 1;
        yexte:correction 2;
        reference
            "RFC 7950: The YANG 1.1 Data Modeling Language";
    }

    revision 2021-03-24 {
        description
            "Correct must statements for MO references.";
        yexte:version 1;
        yexte:release 1;
        yexte:correction 1;
        reference
            "RFC 7950: The YANG 1.1 Data Modeling Language";
    }

    revision 2021-03-22 {
        description
            "Parity with ECIM R1A79.";
        yexte:version 1;
        yexte:release 1;
        yexte:correction 0;
        reference
            "RFC 7950: The YANG 1.1 Data Modeling Language";
    }

    revision 2021-01-20 {
        description
            "Add extensions is-system-created and restricted.";
        yexte:version 1;
        yexte:release 0;
        yexte:correction 0;
        reference
            "RFC 7950: The YANG 1.1 Data Modeling Language";
    }

    revision 2021-01-11 {
        description
            "Initial version of the EUtranFreqRelation model.";
        yexte:version 0;
        yexte:release 1;
        yexte:correction 0;
        reference
            "RFC 7950: The YANG 1.1 Data Modeling Language";
    }

    deviation /me3gpp:ManagedElement/gnbcucp3gpp:GNBCUCPFunction/nrcellcu3gpp:NRCellCU/eutranfreqrel3gpp:EUtranFreqRelation/eutranfreqrel3gpp:attributes/eutranfreqrel3gpp:cellReselectionPriority {
        // Replace deviate for removing the Mandatory statement is deliberately added here instead of the -ext file since the YANG validator gives an error if this is separated from the default value statement (not present for this attribute).
        deviate replace {
            mandatory false;
        }
        deviate add {
            must 'count(../../../nrfreqrel3gpp:NRFreqRelation[current() = nrfreqrel3gpp:attributes/nrfreqrel3gpp:cellReselectionPriority]) = 0' {
                error-message
                    "Same cellReselectionPriority cannot be reused for different RAT frequency relations (NRFreqRelations and EUtranFreqRelations) under the same NRCellCU.";
            }
            yexte:updated-description
                "Absolute priority of the carrier frequency used by the cell " +
                "reselection procedure.

                This attribute is broadcast in SIB5 and referred to for setting " +
                "CellReselectionPriority in RRCRelease message.
                Value 0 means lowest priority. The value must be unique between " +
                "RATs. This means that equal priorities between RATs are not " +
                "supported.
                If empty, value is not broadcast in SIB5.";
            yexte:initial-value 6;
            yexte:dependencies
                "The cellReselectionPriority must be unique between NRFreqRelations "+
                "and EUtranFreqRelations under the same NRCellCU.";
            yexte:takes-effect
                "New connection for RRCRelease message.
                Otherwise, immediately.";
        }
    }

    deviation /me3gpp:ManagedElement/gnbcucp3gpp:GNBCUCPFunction/nrcellcu3gpp:NRCellCU/eutranfreqrel3gpp:EUtranFreqRelation/eutranfreqrel3gpp:attributes/eutranfreqrel3gpp:cellReselectionSubPriority {
        deviate add {
            yexte:updated-description
                "Subpriority value of E-UTRA carrier frequency.

                Subpriority value added to value of cellReselectionPriority to " +
                "obtain absolute priority of carrier frequency.
                If empty, this attribute is not broadcast in SIB5.
                This attribute is broadcast accompanied by cellReselectionPriority " +
                "in SIB5 and referred to for setting CellReselectionSubPriority in " +
                "RRCRelease message.";
            yexte:takes-effect
                "New connection for RRCRelease message.
                Otherwise, immediately.";
        }
    }

    deviation /me3gpp:ManagedElement/gnbcucp3gpp:GNBCUCPFunction/nrcellcu3gpp:NRCellCU/eutranfreqrel3gpp:EUtranFreqRelation/eutranfreqrel3gpp:attributes/eutranfreqrel3gpp:pMax {
        // Replace deviate for removing the Mandatory statement is deliberately added here instead of the -ext file since the YANG validator gives an error if this is separated from the default value statement.
        deviate replace {
            mandatory false;
        }
        deviate add {
            default 23;
            yexte:updated-description
                "Parameter used to calculate Pcompensation at cell reselection.

                Corresponds to parameter PEMAX in 3GPP TS 38.101.";
            yexte:takes-effect
                "Next cell unlock";
        }
    }

    deviation /me3gpp:ManagedElement/gnbcucp3gpp:GNBCUCPFunction/nrcellcu3gpp:NRCellCU/eutranfreqrel3gpp:EUtranFreqRelation/eutranfreqrel3gpp:attributes/eutranfreqrel3gpp:qQualMin {
        // Replace deviate for removing the Mandatory statement is deliberately added here instead of the -ext file since the YANG validator gives an error if this is separated from the default value statement.
        deviate replace {
            mandatory false;
            type int32 {
                range "-43..-12";
            }
        }
        deviate add {
            default -34;
            yexte:updated-description
                "Minimum required quality level in cell (dB).

                This attribute is broadcast in SIB5.";
            yexte:takes-effect
                "Next cell unlock";
        }
    }

    deviation /me3gpp:ManagedElement/gnbcucp3gpp:GNBCUCPFunction/nrcellcu3gpp:NRCellCU/eutranfreqrel3gpp:EUtranFreqRelation/eutranfreqrel3gpp:attributes/eutranfreqrel3gpp:qRxLevMin {
        // Replace deviate for removing the Mandatory statement is deliberately added here instead of the -ext file since the YANG validator gives an error if this is separated from the default value statement.
        deviate replace {
            mandatory false;
        }
        deviate add {
            default -140;
            must ". mod 2 = 0" {
                error-message
                    "qRxLevMin must be set with resolution/step of 2.";
            }
            yexte:updated-description
                "Minimum received RSRP level for cell reselection.

                Corresponds to parameter Qrxlevmin in 3GPP TS 38.304.";
        }
    }

    deviation /me3gpp:ManagedElement/gnbcucp3gpp:GNBCUCPFunction/nrcellcu3gpp:NRCellCU/eutranfreqrel3gpp:EUtranFreqRelation/eutranfreqrel3gpp:attributes/eutranfreqrel3gpp:tReselectionEutra {
        // Replace deviate for removing the Mandatory statement is deliberately added here instead of the -ext file since the YANG validator gives an error if this is separated from the default value statement.
        deviate replace {
            mandatory false;
        }
        deviate add {
            default 2;
            yexte:updated-description
                "Time for evaluation of criteria before reselection can be done.";
            yexte:takes-effect
                "Next cell unlock";
        }
    }

    deviation /me3gpp:ManagedElement/gnbcucp3gpp:GNBCUCPFunction/nrcellcu3gpp:NRCellCU/eutranfreqrel3gpp:EUtranFreqRelation/eutranfreqrel3gpp:attributes/eutranfreqrel3gpp:tReselectionEutraSfHigh {
        deviate replace {
            mandatory false;
        }
        deviate add {
            yexte:updated-description
                "Speed-dependent scaling factor for TreselectionEUTRA.

                For E-UTRAN cell reselection, concerned mobility control related "+
                "parameter is multiplied with this factor if UE is in high mobility "+
                "state.
                If empty, no t-ReselectionEUTRA-SF will be broadcast in SIB5.";
            yexte:takes-effect
                "New connection";
        }
    }

    deviation /me3gpp:ManagedElement/gnbcucp3gpp:GNBCUCPFunction/nrcellcu3gpp:NRCellCU/eutranfreqrel3gpp:EUtranFreqRelation/eutranfreqrel3gpp:attributes/eutranfreqrel3gpp:tReselectionEutraSfMedium {
        deviate replace {
            mandatory false;
        }
        deviate add {
            yexte:updated-description
                "Speed-dependent scaling factor for TreselectionEUTRA.

                For E-UTRAN cell reselection, concerned mobility control related "+
                "parameter is multiplied with this factor if UE is in medium mobility "+
                "state.
                If empty, no t-ReselectionEUTRA-SF will be broadcast in SIB5.";
            yexte:takes-effect
                "New connection";
        }
    }

    deviation /me3gpp:ManagedElement/gnbcucp3gpp:GNBCUCPFunction/nrcellcu3gpp:NRCellCU/eutranfreqrel3gpp:EUtranFreqRelation/eutranfreqrel3gpp:attributes/eutranfreqrel3gpp:threshXHighP {
        // Replace deviate for removing the Mandatory statement is deliberately added here instead of the -ext file since the YANG validator gives an error if this is separated from the default value statement.
        deviate replace {
            mandatory false;
        }
        deviate add {
            default 4;
            must ". mod 2 = 0" {
                error-message
                    "threshXHighP must be set with resolution/step of 2.";
            }
            yexte:updated-description
                "RSRP threshold level for reselection to higher priority.

                Each frequency of E-UTRAN can have a specific threshold.";
            yexte:takes-effect
                "Next cell unlock";
        }
    }

    deviation /me3gpp:ManagedElement/gnbcucp3gpp:GNBCUCPFunction/nrcellcu3gpp:NRCellCU/eutranfreqrel3gpp:EUtranFreqRelation/eutranfreqrel3gpp:attributes/eutranfreqrel3gpp:threshXHighQ {
        deviate replace {
            mandatory false;
        }
        deviate add {
            yexte:updated-description
                "RSRQ threshold level for reselection to higher priority.

                The threshold used by the UE when reselecting towards a higher "+
                "priority frequency X from the current serving frequency.
                Each frequency of E-UTRAN can have a specific threshold.
                If the attribute is set to empty, the value is not broadcast in SIB5.";
            yexte:dependencies
                "Must be empty if NRCellCU::threshServingLowQ is empty or set if "+
                "NRCellCU::threshServingLowQ is set.";
            yexte:takes-effect
                "Next cell unlock";
        }
    }

    deviation /me3gpp:ManagedElement/gnbcucp3gpp:GNBCUCPFunction/nrcellcu3gpp:NRCellCU/eutranfreqrel3gpp:EUtranFreqRelation/eutranfreqrel3gpp:attributes/eutranfreqrel3gpp:threshXLowP {
        // Replace deviate for removing the Mandatory statement is deliberately added here instead of the -ext file since the YANG validator gives an error if this is separated from the default value statement.
        deviate replace {
            mandatory false;
        }
        deviate add {
            default 0;
            must ". mod 2 = 0" {
                error-message
                    "threshXLowP must be set with resolution/step of 2.";
            }
            yexte:updated-description
                "RSRP threshold level for reselection to lower priority.

                Each frequency of E-UTRAN can have a specific threshold.";
            yexte:takes-effect
                "Next cell unlock";
        }
    }

    deviation /me3gpp:ManagedElement/gnbcucp3gpp:GNBCUCPFunction/nrcellcu3gpp:NRCellCU/eutranfreqrel3gpp:EUtranFreqRelation/eutranfreqrel3gpp:attributes/eutranfreqrel3gpp:threshXLowQ {
        deviate add {
            yexte:updated-description
                "RSRQ threshold level for reselection to lower priority.

                The threshold used by the UE when reselecting towards a lower "+
                "priority frequency X from the current serving frequency.
                Each frequency of E-UTRAN can have a specific threshold.
                If the attribute is set to empty, the value is not broadcast in SIB5.";
            yexte:dependencies
                "Must be empty if NRCellCU::threshServingLowQ is empty or set if "+
                "NRCellCU::threshServingLowQ is set.";
            yexte:takes-effect
                "Next cell unlock";
        }
    }

    deviation /me3gpp:ManagedElement/gnbcucp3gpp:GNBCUCPFunction/nrcellcu3gpp:NRCellCU/eutranfreqrel3gpp:EUtranFreqRelation/eutranfreqrel3gpp:attributes/eutranfreqrel3gpp:eUtranFrequencyRef {
        deviate add {
            must "re-match(current(), 'ManagedElement=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,GNBCUCPFunction=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,EUtraNetwork=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,EUtranFrequency=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?') and
                  re-match(current(), concat('ManagedElement=', ../../../../../me3gpp:id, ',.*')) and
                  re-match(current(), concat('.*GNBCUCPFunction=', ../../../../gnbcucp3gpp:id, ',.*')) and
                  count(../../../../eutranet:EUtraNetwork[re-match(current(), concat('.*EUtraNetwork=', eutranet:id, ',.*'))]/eutranfrequency:EUtranFrequency[re-match(current(), concat('.*EUtranFrequency=', eutranfrequency:id))]) &gt; 0" {
                error-message
                    "eUtranFrequencyRef must refer to an EUtranFrequency under the same GNBCUCPFunction.";
            }
            yexte:updated-description
                "Reference to an instance of EUtranFrequency MO.

                Must be unique among EUtranFreqRelations under an NRCellCU.";
            yext3gpp:inVariant;
        }
    }

    deviation /me3gpp:ManagedElement/gnbcucp3gpp:GNBCUCPFunction/nrcellcu3gpp:NRCellCU/eutranfreqrel3gpp:EUtranFreqRelation {
        deviate add {
            max-elements 16;
            yexte:updated-description
                "Mobility relation between NR cell and an E-UTRAN frequency.";
        }
    }

    grouping EUtranFreqRelationVCUCPGrp {
        description "Ericsson extensions to the 3gpp EUtranFreqRelation.";
        reference "Ericsson documentation";

        leaf allowedMeasBandwidth {
            description
                "Maximum allowed measurement bandwidth on a carrier frequency.

                 Value indicates number of resource blocks and corresponds to channel bandwidth 1.4 MHz, 3 MHz, 5 MHz, 10 MHz, 15 MHz and 20 MHz respectively specified in 3GPP TS 36.104, Evolved Universal Terrestrial Radio Access (E-UTRA); Base Station (BS) radio transmission and reception.";
            type int32 {
                range "6 | 15 | 25 | 50 | 75 | 100";
            }
            units "PRB";
            default 6;
            reference "3GPP TS 38.331";
            yexte:takes-effect
                "Next cell unlock";
            tailf:info 'Takes effect: Next cell unlock, Maximum allowed measurement bandwidth on a carrier frequency. Value indicates number of resource blocks and corresponds to channel bandwidth 1.4 MHz, 3 MHz, 5 MHz, 10 MHz, 15 MHz and 20 MHz respectively specified in 3GPP TS 36.104, Evolved Universal Terrestrial Radio Access (E-UTRA); Base Station (BS) radio transmission and reception.';
        }

        list allowedPlmnList {
            key "mcc mnc";
            max-elements 15;
            description
                "Lists all Public Land Mobile Network (PLMN) IDs allowed for this "+
                "frequency relation.

                According to UE Mobility Restriction List, a UE not supporting a PLMN "+
                "included in allowedPlmnList does not use frequency.

                If empty, frequency has no restrictions for PLMN.

                PLMN ID consists of MobileCountryCode (MCC, 3 digits) and "+
                "MobileNetworkCode (MNC, 2 or 3 digits).";
            uses types3gpp:PLMNId;
            yexte:disturbances
                "Changing this attribute can cause loss of traffic.";
            yexte:takes-effect
                "New connection";
            tailf:info 'Takes effect: New connection, Traffic Disturbance: Changing this attribute can cause loss of traffic, Lists all Public Land Mobile Network (PLMN) IDs allowed for this frequency relation. According to UE Mobility Restriction List, a UE not supporting a PLMN included in allowedPlmnList does not use frequency. If empty, frequency has no restrictions for PLMN. PLMN ID consists of MobileCountryCode (MCC, 3 digits) and MobileNetworkCode (MNC, 2 or 3 digits).';
        }

        leaf anrMeasOn {
            description
                "Whether ANR measurement on frequency is enabled.";
            type boolean;
            default true;
        }

        leaf eUtranFallbackPrioEc {
            description
                "Priority of E-UTRAN frequencies for emergency calls.

                Priority is among all frequencies related to the cell for UEs in "+
                "connected mode.
                Sets priority to alternative target frequency to which release is "+
                "made with redirection.

                Value 0 means lowest priority.
                Value 7 means highest priority.
                If empty, the frequency is excluded.";
            type int32 {
                range "0..7";
            }
            yexte:initial-value 0;
        }

        leaf mcpcPCellEUtranFreqRelProfileRef {
            description
                "Reference to instance of McpcPCellEUtranFreqRelProfile MO.

                If non-empty, attributes from referenced MO instance are used.
                If empty, attribute default values according to MO class definition "+
                "are used.";
            type types3gpp:DistinguishedName;
            must "re-match(current(), 'ManagedElement=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,GNBCUCPFunction=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,Mcpc=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,McpcPCellEUtranFreqRelProfile=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?') and
                    re-match(current(), concat('ManagedElement=', ../../../../../me3gpp:id, ',.*')) and
                    re-match(current(), concat('.*GNBCUCPFunction=', ../../../../gnbcucp3gpp:id, ',.*')) and
                    count(../../../../mcpc:Mcpc[re-match(current(), concat('.*Mcpc=', mcpc:id, ',.*'))]/mcpcpcelleutranfreqrelprofile:McpcPCellEUtranFreqRelProfile[re-match(current(), concat('.*McpcPCellEUtranFreqRelProfile=', mcpcpcelleutranfreqrelprofile:id))]) &gt; 0" {
                description
                "The reference must point at a "+
                "McpcPCellEUtranFreqRelProfile entry.

                An example of a valid value is
                ManagedElement=1,GNBCUCPFunction=1,Mcpc=1,McpcPCellEUtranFreqRelProfile=1";
                error-message
                "mcpcPCellEUtranFreqRelProfileRef must refer to an McpcPCellEUtranFreqRelProfile under the same GNBCUCPFunction.";
            }
            yexte:dependencies
                "Referenced McpcPCellEUtranFreqRelProfile must be under Mcpc MO under "+
                "same GNBCUCPFunction as NRCellCU.";
            yexte:takes-effect
                "Next usage.";
            tailf:info 'Takes effect: Next usage, Dependencies: Referenced McpcPCellEUtranFreqRelProfile must be under Mcpc MO under same GNBCUCPFunction as NRCellCU, Reference to instance of McpcPCellEUtranFreqRelProfile MO. If non-empty, attributes from referenced MO instance are used. If empty, attribute default values according to MO class definition are used.';
        }

        leaf presenceAntennaPort1 {
            description
                "Use of Antenna Port 1 in neighboring cells.

                Value true means UE expects at least two cell-specific antenna ports "+
                "are used in neighboring cells.";
            type boolean;
            default false;
            reference
                "3GPP TS 38.331";
            yexte:takes-effect
                "Next cell unlock";
            tailf:info 'Takes effect: Next cell unlock, Use of Antenna Port 1 in neighboring cells. Value true means UE expects at least two cell-specific antenna ports are used in neighboring cells.';
        }

        leaf ueMCEUtranFreqRelProfileRef {
            description
                "Reference to an instance of UeMCEUtranFreqRelProfile MO.

                If non-empty, attributes from referred MO instance are used.
                If empty, default values according to MO class definition are used.

                Referenced UeMCEUtranFreqRelProfile must be under UeMC MO under same "+
                "GNBCUCPFunction as NRCellCU that EUtranFreqRelation belongs to.";
            type types3gpp:DistinguishedName;
            must "re-match(current(), 'ManagedElement=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,GNBCUCPFunction=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,UeMC=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,UeMCEUtranFreqRelProfile=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?') and
                    re-match(current(), concat('ManagedElement=', ../../../../../me3gpp:id, ',.*')) and
                    re-match(current(), concat('.*GNBCUCPFunction=', ../../../../gnbcucp3gpp:id, ',.*')) and
                    count(../../../../uemcvcucp:UeMC[re-match(current(), concat('.*UeMC=', uemcvcucp:id, ',.*'))]/uemceutranfreqrelprofilevcucp:UeMCEUtranFreqRelProfile[re-match(current(), concat('.*UeMCEUtranFreqRelProfile=', uemceutranfreqrelprofilevcucp:id))]) &gt; 0" {
                description
                    "The reference must point at a "+
                    "UeMCEUtranFreqRelProfile entry.

                    An example of a valid value is
                    ManagedElement=1,GNBCUCPFunction=1,UeMC=1,UeMCEUtranFreqRelProfile=1";
                error-message
                    "ueMCEUtranFreqRelProfileRef must refer to an UeMCEUtranFreqRelProfile under the same GNBCUCPFunction.";
            }
            yexte:dependencies
                "Referenced UeMCEUtranFreqRelProfile must be under UeMC MO under same "+
                "GNBCUCPFunction as NRCellCU.";
            yexte:takes-effect
                "Next usage.";
            tailf:info 'Takes effect: Next usage, Dependencies: Referenced UeMCEUtranFreqRelProfile must be under UeMC MO under same GNBCUCPFunction as NRCellCU, Reference to an instance of UeMCEUtranFreqRelProfile MO. If non-empty, attributes from referred MO instance are used. If empty, default values according to MO class definition are used. Referenced UeMCEUtranFreqRelProfile must be under UeMC MO under same GNBCUCPFunction as NRCellCU that EUtranFreqRelation belongs to.';
        }

        leaf voicePrio {
            description
                "Prioritizes E-UTRAN frequencies among all frequencies related to the "+
                "cell for UEs in connected mode.

                Sets priority to which frequency to perform mobility to for a voice "+
                "session.

                Value 0 means lowest priority.
                Value 7 means highest priority.
                Value empty means that the frequency is excluded.";
            type int32 {
                range "0..7";
            }
            yexte:initial-value 0;
            yexte:takes-effect
                "New connection";
            tailf:info 'Takes effect: New connection, Prioritizes E-UTRAN frequencies among all frequencies related to the cell for UEs in connected mode. Sets priority to which frequency to perform mobility to for a voice session. Value 0 means lowest priority. Value 7 means highest priority. Value empty means that the frequency is excluded.';
        }
    }

    augment "/me3gpp:ManagedElement/gnbcucp3gpp:GNBCUCPFunction/nrcellcu3gpp:NRCellCU/eutranfreqrel3gpp:EUtranFreqRelation/eutranfreqrel3gpp:attributes" {
        description "Adds Ericsson attributes to 3gpp EUtranFreqRelation.";
        uses EUtranFreqRelationVCUCPGrp;
    }
}
