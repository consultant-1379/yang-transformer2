// Generated by eyang-preprocessor (1.22.0-48 2022-01-20 09:10:06 CET) on Jun 30, 2022, 8:31:44 AM
module ericsson-rrc-vcucp {
    yang-version 1.1;
    namespace urn:rdns:com:ericsson:oammodel:ericsson-rrc-vcucp;
    prefix rrcvcucp;

    import tailf-common {
        prefix tailf;
    }
    import _3gpp-common-managed-element {
        prefix me3gpp;
    }
    import _3gpp-nr-nrm-gnbcucpfunction {
        prefix gnbcucp3gpp;
    }
    import _3gpp-common-top {
        prefix top3gpp;
    }
    import ericsson-yang-extensions {
        prefix yexte;
    }
    import ericsson-uecc-vcucp {
        prefix ueccvcucp;
    }

    organization
      "Ericsson AB";
    contact
      "Ericsson first line support via email";
    description
      "The module defines the Rrc data model for the Ericsson vCU-CP.

       Copyright (c) 2022 Ericsson AB. All rights reserved.";

    revision 2022-06-28 {
        description
            "Removed module-status preliminary.
             Removed preliminary status from Rrc.";
        yexte:version 0;
        yexte:release 2;
        yexte:correction 0;
        reference
            "RFC 7950: The YANG 1.1 Data Modeling Language";
    }

    revision 2022-03-14 {
        description
            "Initial version of the Rrc model.";
        yexte:version 0;
        yexte:release 1;
        yexte:correction 0;
        reference
            "RFC 7950: The YANG 1.1 Data Modeling Language";
    }

    augment "/me3gpp:ManagedElement/gnbcucp3gpp:GNBCUCPFunction/ueccvcucp:UeCC" {
        list Rrc {
            description
                "Container class for RRC UE configuration classes.

                MO instance Rrc=1 is created automatically when parent MO is "+
                "created, unless created manually in the same transaction as "+
                "parent MO.

                The RDN of this MO must be Rrc=1.";
            key id;
            max-elements 1;
            uses top3gpp:Top_Grp {
                refine id {
                    must '. = "1"' {
                        error-message
                            "The RDN of this MO must always be Rrc=1";
                    }
                }
            }
            yexte:precondition
                "Rrc=1 instance can only be created in the same transaction as "+
                "parent MO and must not be deleted unless parent MO is deleted.";
            tailf:info 'Precondition: Rrc=1 instance can only be created in the same transaction as parent MO and must not be deleted unless parent MO is deleted, Container class for RRC UE configuration classes. MO instance Rrc=1 is created automatically when parent MO is created, unless created manually in the same transaction as parent MO. The RDN of this MO must be Rrc=1.';
        }
    }
}
