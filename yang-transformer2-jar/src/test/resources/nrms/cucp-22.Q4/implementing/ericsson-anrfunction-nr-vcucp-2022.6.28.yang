// Generated by eyang-preprocessor (1.22.0-48 2022-01-20 09:10:06 CET) on Jun 30, 2022, 8:31:35 AM
module ericsson-anrfunction-nr-vcucp {
    yang-version 1.1;
    namespace "urn:rdns:com:ericsson:oammodel:ericsson-anrfunction-nr-vcucp";
    prefix anrfunctionnr;

    import tailf-common {
        prefix tailf;
    }
    import _3gpp-common-managed-element {
        prefix "me3gpp";
    }
    import _3gpp-nr-nrm-gnbcucpfunction {
        prefix "gnbcucp3gpp";
    }
    import ericsson-anrfunction-vcucp {
        prefix "anrfunction";
    }
    import _3gpp-common-top {
        prefix "top3gpp";
    }
    import ericsson-yang-extensions {
        prefix "yexte";
    }

    organization
        "Ericsson AB";
    contact
        "Ericsson first line support via email";
    description
        "The module defines the AnrFunctionNR data model for the Ericsson vCU-CP.

        Copyright (c) 2021-2022 Ericsson AB. All rights reserved.";

    revision 2022-06-28 {
        description
            "Removed module-status preliminary.";
        yexte:version 1;
        yexte:release 1;
        yexte:correction 0;
        reference
            "RFC 7950: The YANG 1.1 Data Modeling Language";
    }

    revision 2021-11-05 {
        description
            "Added anrAutoCreateXnForEndc, and anrCgiMeasInterFreqMode attributes.
            gNBIdLength is marked obsolete ";
        yexte:version 1;
        yexte:release 0;
        yexte:correction 0;
        reference
            "RFC 7950: The YANG 1.1 Data Modeling Language";
    }

    revision 2021-06-08 {
        description
            "Changed error message for a must statement.";
        yexte:version 0;
        yexte:release 1;
        yexte:correction 1;
        reference
            "RFC 7950: The YANG 1.1 Data Modeling Language";
    }

    revision 2021-04-30 {
        description
            "Initial version of the AnrFunctionNR model.";
        yexte:version 0;
        yexte:release 1;
        yexte:correction 0;
        reference
            "RFC 7950: The YANG 1.1 Data Modeling Language";
    }

    typedef AnrCgiMeasInterFreqMode {
        description
          "ANR with CGI measurement operation for RBS.";
        type enumeration {
            enum DISABLED {
                value 0;
                description
                  "ANR with CGI measurement for inter-frequency is disabled for RBS.";
            }
            enum FR1 {
                value 1;
                description
                  "ANR with CGI measurement for inter-frequency is enabled for RBS on FR1.";
            }
        }
    }
    grouping AnrFunctionNRGrp {
        description
            "Represents the AnrFunctionNR IOC.";

        leaf anrAutoCreateXnForEndc {
            description
              "Whether NR Automated Neighbor Relations feature can create Xn for NR "
            + "neighbor relation for EN-DC.

               If true, Xn is created automatically for lightweight NR neighbor "
            + "relations created by NR Automated Neighbor Relations feature for "
            + "EN-DC over X2.";
            type boolean;
            default false;
        }

        leaf anrCgiMeasInterFreqMode {
            description
              "ANR with CGI measurement for inter-frequency for RBS.";
            type AnrCgiMeasInterFreqMode;
            default DISABLED;
        }

        leaf anrCgiMeasIntraFreqEnabled {
            description
                "Whether ANR with CGI measurement for intra frequency is enabled for
                 the Managed Function.";
            type boolean;
            default false;
            yexte:takes-effect "Next usage.";
            tailf:info 'Takes effect: Next usage, Whether ANR with CGI measurement for intra frequency is enabled for the Managed Function.';
        }

        leaf anrEndcX2Enabled {
            description
              "Whether ANR for EN-DC over X2 is enabled for NR for the Managed Function.
               Only takes effect when ANR feature is enabled.";
            type boolean;
            default false;
            yexte:takes-effect "Next usage.";
            tailf:info 'Takes effect: Next usage, Whether ANR for EN-DC over X2 is enabled for NR for the Managed Function. Only takes effect when ANR feature is enabled.';
        }

        leaf gNBIdLength {
            description
              "Length of gNodeB ID bit string representation.";
            type int32 {
                range "22..32";
            }
            status obsolete {
                yexte:status-information
                    "Since 21.Q4. Planned to be removed.";
            }
            tailf:info 'Status Info: Since 21.Q4. Planned to be removed, Obsolete, Length of gNodeB ID bit string representation.';
        }
    }

    augment "/me3gpp:ManagedElement/gnbcucp3gpp:GNBCUCPFunction/anrfunction:AnrFunction" {
        list AnrFunctionNR {
            description
              "NR Automated Neighbor Relation (ANR) functions.
              The RDN of this MO must always be AnrFunctionNR=1.";
            key id;
            max-elements 1;
            uses top3gpp:Top_Grp {
                refine id {
                    must '. = "1"' {
                        error-message
                          "The RDN of this MO must always be AnrFunctionNR=1";
                    }
                }
            }
            container attributes {
                uses AnrFunctionNRGrp;
            }
        }
    }
}
