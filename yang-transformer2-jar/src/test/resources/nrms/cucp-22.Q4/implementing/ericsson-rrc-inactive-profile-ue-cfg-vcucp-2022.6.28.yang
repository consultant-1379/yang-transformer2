// Generated by eyang-preprocessor (1.22.0-48 2022-01-20 09:10:06 CET) on Jun 30, 2022, 8:31:43 AM
module ericsson-rrc-inactive-profile-ue-cfg-vcucp {
    yang-version 1.1;
    namespace urn:rdns:com:ericsson:oammodel:ericsson-rrc-inactive-profile-ue-cfg-vcucp;
    prefix rrcinactiveprofileuecfgvcucp;

    import tailf-common {
        prefix tailf;
    }
    import _3gpp-common-managed-element {
        prefix me3gpp;
    }
    import _3gpp-nr-nrm-gnbcucpfunction {
        prefix gnbcucp3gpp;
    }
    import _3gpp-common-top {
        prefix top3gpp;
    }
    import ericsson-yang-extensions {
        prefix yexte;
    }
    import ericsson-uecc-vcucp {
        prefix ueccvcucp;
    }
    import ericsson-rrc-inactive-profile-vcucp {
        prefix rrcinactiveprofilevcucp;
    }
    import ericsson-common-types-vcucp {
        prefix commontypes;
    }

    organization
        "Ericsson AB";
    contact
        "Ericsson first line support via email";
    description
        "The module defines the RrcInactiveProfileUeCfg data model for the Ericsson vCU-CP.

        Copyright (c) 2022 Ericsson AB. All rights reserved.";

    revision 2022-06-28 {
        description
            "Removed module-status preliminary.
             Removed preliminary status from RrcInactiveProfileUeCfg.";
        yexte:version 0;
        yexte:release 2;
        yexte:correction 0;
        reference
            "RFC 7950: The YANG 1.1 Data Modeling Language";
    }

    revision 2022-03-14 {
        description
            "Initial version of the RrcInactiveProfileUeCfg model.";
        yexte:version 0;
        yexte:release 1;
        yexte:correction 0;
        reference
            "RFC 7950: The YANG 1.1 Data Modeling Language";
    }

    typedef ResumeMsgRedOptions {
        description
            "SCell and UE measurement configuration options for RRCResume message.";
        status current {
            yexte:preliminary;
        }

        type enumeration {
            enum EXCL_SCELLS_IN_NON_ESS_CELL {
                value 0;
                description
                    "SCell configuration is excluded from RRCResume message in non-ESS "+
                    "cell.

                    After RRC Resume procedure is complete, configuration is sent in "+
                    "RRCReconfiguration message.";
            }

            enum EXCL_UE_MEAS_IN_NON_ESS_CELL {
                value 1;
                description
                    "UE measurement configuration is excluded from RRCResume message in "+
                    "non-ESS cell.

                    After RRC Resume procedure is complete, configuration is sent in "+
                    "RRCReconfiguration message.";
            }

            enum EXCL_SCELLS_IN_ESS_CELL {
                value 2;
                description
                    "SCell configuration is excluded from RRCResume message in ESS cell.

                    After RRC Resume procedure is complete, configuration is sent in "+
                    "RRCReconfiguration message.";
            }

            enum EXCL_UE_MEAS_IN_ESS_CELL {
                value 3;
                description
                    "UE measurement configuration is excluded from RRCResume message in "+
                    "ESS cell.

                    After RRC Resume procedure is complete, configuration is sent in "+
                    "RRCReconfiguration message.";
            }
        }
    }

    grouping RrcInactiveProfileUeCfgGrp {
        description
            "Represents the RrcInactiveProfileUeCfg IOC.";

        leaf periodicRnaUpdateCount {
            description
                "Indicates the amount of periodic RNA update procedure before UE "+
                "becomes RRC_IDLE.

                If set to 0, UE becomes RRC_INACTIVE when RRCResumeRequest message is "+
                "received.
                If set to n and is greater than 0,
                - UE becomes RRC_IDLE when nth RRCResumeRequest message is received.
                - UE becomes RRC_INACTIVE every time an RRCResumeRequests message is "+
                "received, except for nth one.";
            type int32 {
                range "0..5";
            }
            default 1;
            yexte:takes-effect
                "New connection";
            tailf:info 'Takes effect: New connection, Indicates the amount of periodic RNA update procedure before UE becomes RRC_IDLE. If set to 0, UE becomes RRC_INACTIVE when RRCResumeRequest message is received. If set to n and is greater than 0, - UE becomes RRC_IDLE when nth RRCResumeRequest message is received. - UE becomes RRC_INACTIVE every time an RRCResumeRequests message is received, except for nth one.';
        }

        leaf periodicRnaUpdateTimer {
            description
                "Configuration of t380.

                Value of t380 for UE is calculated based on this attribute and "+
                "Periodic Registration Update timer provided by Core Network.";
            type int32 {
                range "5|10|20|30|60|120|360|720";
            }
            default 60;
            units minute;
            yexte:takes-effect
                "New connection";
            tailf:info 'Takes effect: New connection, Configuration of t380. Value of t380 for UE is calculated based on this attribute and Periodic Registration Update timer provided by Core Network.';
        }

        leaf-list prefUeGroupList {
            max-elements 8;
            description
                "Preference UE group list.

                List of preference UE group identifiers.

                If empty, the MO instance matches preference UE group identifiers "+
                "not defined in prefUeGroupList of any other MO instances under "+
                "parent MO instance.";
            type int32 {
                range "1..255";
            }
            yexte:dependencies
                "Combinations of pair of preference UE group Identifier in "+
                "prefUeGroupList and UE group identifier in ueGroupList must be "+
                "unique among RrcInactiveProfileUeCfg instances under same parent "+
                "RrcInactiveProfile instance.

                For all preference UE group identifiers in prefUeGroupList "+
                "attributes under same parent RrcInactiveProfile MO instance, exactly "+
                "one RrcInactiveProfileUeCfg MO instance must exist that combines the "+
                "given preference UE group identifier with an empty ueGroupList.";
            yexte:takes-effect
                "New connection";
            must "count(../../../RrcInactiveProfileUeCfg/attributes[prefUeGroupList = current() and count(ueGroupList) = 0 ]) = 1" {
                error-message
                    "Exactly one RrcInactiveProfileUeCfg instance under RrcInactiveProfile must combine a specific preference UE group identifier in attribute prefUeGroupList with an empty ueGroupList.";
            }
            tailf:info 'Takes effect: New connection, Dependencies: Combinations of pair of preference UE group Identifier in prefUeGroupList and UE group identifier in ueGroupList must be unique among RrcInactiveProfileUeCfg instances under same parent RrcInactiveProfile instance.

                For all preference UE group identifiers in prefUeGroupList attributes under same parent RrcInactiveProfile MO instance, exactly one RrcInactiveProfileUeCfg MO instance must exist that combines the given preference UE group identifier with an empty ueGroupList, Preference UE group list. List of preference UE group identifiers. If empty, the MO instance matches preference UE group identifiers not defined in prefUeGroupList of any other MO instances under parent MO instance.';
        }

        leaf rrcInactiveStateSupport {
            description
                "Whether RRC Inactive state is supported.

                Applies to RRC Release procedure triggered by user plane and control "+
                "plane inactivity.";
            type boolean;
            default true;
            yexte:takes-effect
                "New connection";
            tailf:info 'Takes effect: New connection, Whether RRC Inactive state is supported. Applies to RRC Release procedure triggered by user plane and control plane inactivity.';
        }

        leaf-list rrcResumeMsgSizeRed {
            max-elements 4;
            description
                "Size reduction options for RRCResume message in NR SA deployment.

                If empty, no message size reduction is applied. Both SCell "+
                "configuration and UE measurement configuration are sent in RRCResume "+
                "message.";
            type ResumeMsgRedOptions;
            yexte:initial-value EXCL_SCELLS_IN_ESS_CELL;
            yexte:initial-value EXCL_UE_MEAS_IN_ESS_CELL;
            status current {
                yexte:preliminary;
            }
            yexte:takes-effect
                "New connection";
            tailf:info 'Takes effect: New connection, Preliminary, Size reduction options for RRCResume message in NR SA deployment. If empty, no message size reduction is applied. Both SCell configuration and UE measurement configuration are sent in RRCResume message.';
        }

        leaf-list ueGroupList {
            max-elements 16;
            description
                "UE group list.

                List of UE group identifiers.

                If empty, the MO instance matches all UE group identifiers.";
            type int32 {
                range "1..255";
            }
            yexte:dependencies
                "Combinations of pair of preference UE group Identifier in "+
                "prefUeGroupList and UE group identifier in ueGroupList must be "+
                "unique among RrcInactiveProfileUeCfg instances under same parent "+
                "RrcInactiveProfile instance.

                Combination of a UE group identifier in UeGroupList and empty "+
                "prefUeGroupList must be unique among RrcInactiveProfileUeCfg "+
                "instances under same parent RrcInactiveProfile instance.";
            yexte:takes-effect
                "New connection";

            must "count(../prefUeGroupList) &gt; 0 or
                  count(../../../RrcInactiveProfileUeCfg/attributes[ueGroupList = current() and count(prefUeGroupList) = 0]) &lt;= 1" {
                error-message
                    "Only one RrcInactiveProfileUeCfg instance under an RrcInactiveProfile can combine a specific UE group identifier in attribute ueGroupList with an empty prefUeGroupList.";
            }
            tailf:info 'Takes effect: New connection, Dependencies: Combinations of pair of preference UE group Identifier in prefUeGroupList and UE group identifier in ueGroupList must be unique among RrcInactiveProfileUeCfg instances under same parent RrcInactiveProfile instance.

                Combination of a UE group identifier in UeGroupList and empty prefUeGroupList must be unique among RrcInactiveProfileUeCfg instances under same parent RrcInactiveProfile instance, UE group list. List of UE group identifiers. If empty, the MO instance matches all UE group identifiers.';
        }
    }

    augment "/me3gpp:ManagedElement/gnbcucp3gpp:GNBCUCPFunction/ueccvcucp:UeCC/rrcinactiveprofilevcucp:RrcInactiveProfile" {
        list RrcInactiveProfileUeCfg {
            key id;
            uses top3gpp:Top_Grp;
            max-elements 8;
            description
                "Configuration of RRC inactive profile for UE groups.

                MO instance RrcInactiveProfileUeCfg=Base is created " +
                "automatically when parent MO is created, unless created " +
                "manually in the same transaction as parent MO.

                Attributes prefUeGroupList and ueGroupList must be empty in " +
                "instance RrcInactiveProfileUeCfg=Base but cannot all be empty " +
                "in other instances of RrcInactiveProfileUeCfg under same " +
                "parent RrcInactiveProfile.";
            yexte:precondition
                "RrcInactiveProfileUeCfg=Base MO instance can only be created " +
                "in the same transaction as parent MO and must not be deleted " +
                "unless parent MO is deleted. Other instances can be created " +
                "and deleted manually.

                Maximum 7 RrcInactiveProfileUeCfg instances, with RDN "+
                "different from Base, can be created.";

            must "count(../RrcInactiveProfileUeCfg) &lt; 8 or
                  count(../RrcInactiveProfileUeCfg/id[. = 'Base']) = 1" {
                error-message
                    "Maximum 7 RrcInactiveProfileUeCfg instances under RrcInactiveProfile can be created with RDN different from Base.";
            }

            must "./id != 'Base' or ( count(./attributes/prefUeGroupList) = 0 and count(./attributes/ueGroupList) = 0 )" {
                error-message
                    "prefUeGroupList and ueGroupList must be empty in the Base Configuration Instance.";
            }

            must "./id = 'Base' or not( count(./attributes/prefUeGroupList) = 0 and count(./attributes/ueGroupList) = 0 )" {
                error-message
                    "prefUeGroupList and ueGroupList can only be empty in the Base Configuration Instance.";
            }

            must "count(../RrcInactiveProfileUeCfg/attributes[prefUeGroupList = current()/attributes/prefUeGroupList  and ueGroupList = current()/attributes/ueGroupList] ) &lt;= 1" {
                error-message
                    "The combinations of a pair of UE group identifier in ueGroupList and preference UE group identifier in prefUeGroupList must be unique among RrcInactiveProfileUeCfg under a RrcInactiveProfile.";
            }

            container attributes {
                uses RrcInactiveProfileUeCfgGrp;
                uses commontypes:UserLabelGrp;
            }
            tailf:info 'Precondition: RrcInactiveProfileUeCfg=Base MO instance can only be created in the same transaction as parent MO and must not be deleted unless parent MO is deleted. Other instances can be created and deleted manually.

                Maximum 7 RrcInactiveProfileUeCfg instances, with RDN different from Base, can be created, Configuration of RRC inactive profile for UE groups. MO instance RrcInactiveProfileUeCfg=Base is created automatically when parent MO is created, unless created manually in the same transaction as parent MO. Attributes prefUeGroupList and ueGroupList must be empty in instance RrcInactiveProfileUeCfg=Base but cannot all be empty in other instances of RrcInactiveProfileUeCfg under same parent RrcInactiveProfile.';
        }
    }
}
