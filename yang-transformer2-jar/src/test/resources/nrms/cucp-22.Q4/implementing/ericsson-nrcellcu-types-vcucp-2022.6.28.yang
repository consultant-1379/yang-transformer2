// Generated by eyang-preprocessor (1.22.0-48 2022-01-20 09:10:06 CET) on Jun 30, 2022, 8:31:41 AM
module ericsson-nrcellcu-types-vcucp {
    yang-version 1.1;
    namespace urn:rdns:com:ericsson:oammodel:ericsson-nrcellcu-types-vcucp;
    prefix nrcellcutypes;

    import ericsson-yang-extensions {
        prefix yexte;
    }

    organization
      "Ericsson AB";
    contact
      "Ericsson first line support via email";
    description
      "The module defines common NR cell types for the Ericsson vCU-CP.

       Copyright (c) 2021-2022 Ericsson AB. All rights reserved.";

    revision 2022-06-28 {
        description
            "Removed module-status preliminary.";
        yexte:version 0;
        yexte:release 3;
        yexte:correction 0;
        reference
            "RFC 7950: The YANG 1.1 Data Modeling Language";
    }

    revision 2021-03-18 {
        description
          "Parity with ECIM R1A79.";
        yexte:version 0;
        yexte:release 2;
        yexte:correction 0;
        reference
          "RFC 7950: The YANG 1.1 Data Modeling Language";
    }

    revision 2021-01-11 {
        description
          "Add common types used by NR cells within vCU-CP.";
        yexte:version 0;
        yexte:release 1;
        yexte:correction 0;
        reference
          "RFC 7950: The YANG 1.1 Data Modeling Language";
    }

    typedef NRCellState {
        description
          "Cell states.";
        type enumeration {
            enum IDLE {
                value 0;
                description
                  "The resource is not currently in use.";
                reference
                  "ITU-T Rec. X.731";
            }
            enum INACTIVE {
                value 1;
                description
                  "The cell is known by both the gNodeB-DU and the gNodeB-CU-CP.

                   The cell shall not serve UEs.";
                reference
                  "3GPP TS 38.401";
            }
            enum ACTIVE {
                value 2;
                description
                  "The cell is known by both the gNodeB-DU and the gNodeB-CU-CP.

                   The cell should try to provide service to the UEs.";
                reference
                  "3GPP TS 38.401";
            }
        }
    }

    typedef NRCellServiceState {
        description
          "Cell service state.";
        type enumeration {
            enum OUT_OF_SERVICE {
                value 0;
                description
                  "Cell is not operational and cannot serve UE instances.

                   The gNodeB Distributed Unit (gNodeB-DU) is trying to make cell operational.";
                reference
                  "3GPP TS 38.401";
            }
            enum IN_SERVICE {
                value 1;
                description
                  "Cell is operational and can serve UE instances.";
                reference
                  "3GPP TS 38.401";
            }
        }
    }

    typedef MsgRedOptions {
        description
          "Measurement configuration options in single RRCReconfiguration "
        + "messages in NR SA deployment.";
        status current {
            yexte:preliminary;
        }

        type enumeration {
            enum NO_MSG_RED {
                value 0;
                description
                  "No message size reduction.

                   SCells and measurement configuration are included in one single "
                + "RRCReconfiguration message.";
            }

            enum HO_ESS_MSG_RED_LEVEL1 {
                value 1;
                description
                  "SCells and measurement configuration are sent in subsequent "
                + "RRCReconfiguration message.

                   Applies to handover at poor coverage and initial context setup in "
                + "ESS cell.";
            }
        }
    }

    grouping LwNeighborRelInfo {
        description
          "Lightweight representation of an NR neighbor relation.";

        leaf cellLocalId {
            description
              "Together with gNodeB identifier, identifies an NR cell within PLMN.";
            type int32 {
                range "0..16383";
            }
        }

        leaf gNBId {
            description
              "Identifies a gNodeB within PLMN.";
            type int64 {
                range "0..4294967295";
            }
        }

        leaf gNBIdLength {
            description
              "Number of bits for encoding gNodeB ID.";
            type int32 {
                range "22..32";
            }
        }

        leaf mcc {
            description
              "Mobile Country Code identifies home country of mobile subscriber.

               MCC consists of three decimal digits. The first digit of MCC "
            + "identifies geographic region. (Values 1 and 8 in the first digit are "
            + "not allowed.)";
            type string {
                length 3;
            }
            reference
              "3GPP TS 28.541";
        }

        leaf mnc {
            description
              "MNC identifies home PLMN of mobile subscription.

               MNC consists of two or three decimal digits. For example, MNC of 001 "
            + "is not same as MNC of 01.";
            type string {
                length "2..3";
            }
            reference
              "3GPP TS 28.541";
        }

        leaf nRPCI {
            description
              "Physical cell ID of external NR cell.";
            type int32 {
                range "0..1007";
            }
        }
    }
}
