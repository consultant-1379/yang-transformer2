// Generated by eyang-preprocessor (1.22.0-48 2022-01-20 09:10:06 CET) on Jun 30, 2022, 8:31:39 AM
module ericsson-mcpc-pcell-nr-freq-rel-profile-ue-cfg-vcucp {
    yang-version 1.1;
    namespace "urn:rdns:com:ericsson:oammodel:ericsson-mcpc-pcell-nr-freq-rel-profile-ue-cfg-vcucp";
    prefix "mcpcpcellnrfreqrelprofileuecfg";

    import tailf-common {
        prefix tailf;
    }
    import _3gpp-common-managed-element {
        prefix "me3gpp";
    }
    import _3gpp-nr-nrm-gnbcucpfunction {
        prefix "gnbcucp3gpp";
    }
    import _3gpp-common-top {
        prefix "top3gpp";
    }
    import ericsson-yang-extensions {
        prefix "yexte";
    }
    import ericsson-mcpc-vcucp {
        prefix "mcpc";
    }
    import ericsson-mcpc-pcell-nr-freq-rel-profile-vcucp {
        prefix "mcpcpcellnrfreqrelprofile";
    }
    import ericsson-common-types-vcucp {
        prefix "commontypes";
    }

    organization
        "Ericsson AB";
    contact
        "Ericsson first line support via email";
    description
        "The module defines the McpcPCellNrFreqRelProfileUeCfg data model for the Ericsson vCU-CP.

        Copyright (c) 2022 Ericsson AB. All rights reserved.";

    revision 2022-06-28 {
        description
            "Removed module-status preliminary.
             Removed preliminary status from McpcPCellNrFreqRelProfileUeCfg.";
        yexte:version 0;
        yexte:release 2;
        yexte:correction 0;
        reference
            "RFC 7950: The YANG 1.1 Data Modeling Language";
    }

    revision 2022-03-14 {
        description
            "Initial version of the McpcPCellNrFreqRelProfileUeCfg model";
        yexte:version 0;
        yexte:release 1;
        yexte:correction 0;
        reference
            "RFC 7950: The YANG 1.1 Data Modeling Language";
    }

    grouping McpcPCellNrFreqRelProfileUeCfgGrp {
        description
            "Represents the McpcPCellNrFreqRelProfileUeCfg IOC.";

        leaf inhibitMeasForCellCandidate {
            description
                "Whether UE measurement searching for PCell candidate on this "+
                "frequency is inhibited.";
            type boolean;
            default false;
            yexte:takes-effect
                "Next usage.";
            tailf:info 'Takes effect: Next usage, Whether UE measurement searching for PCell candidate on this frequency is inhibited.';
        }

        leaf-list prefUeGroupList {
            max-elements 8;
            ordered-by user;
            description
                "Preference UE group list.

                List of preference UE group identifiers.

                If empty, the MO instance matches preference UE group identifiers "+
                "not defined in prefUeGroupList of any other MO instances under "+
                "parent MO instance.";
            type int32 {
                range "1..255";
            }
            yexte:dependencies
                "Combinations of pair of preference UE group Identifier in "+
                "prefUeGroupList and UE group identifier in ueGroupList must be "+
                "unique among McpcPCellNrFreqRelProfileUeCfg instances under same "+
                "parent McpcPCellNrFreqRelProfile instance.

                For all preference UE group identifiers in prefUeGroupList "+
                "attributes under same parent McpcPCellNrFreqRelProfile MO instance, "+
                "exactly one McpcPCellNrFreqRelProfileUeCfg MO instance must exist "+
                "that combines the given preference UE group identifier with an empty "+
                "ueGroupList.";
            yexte:disturbances
                "Changing this attribute can cause loss of traffic.";
            yexte:takes-effect
                "Next usage.";
            must "count(../../../McpcPCellNrFreqRelProfileUeCfg/attributes[prefUeGroupList = current()
                    and count(ueGroupList) = 0] ) = 1" {
                error-message
                    "Exactly one McpcPCellNrFreqRelProfileUeCfg instance under an "+
                    "McpcPCellNrFreqRelProfile must combine a specific preference UE "+
                    "group identifier in attribute prefUeGroupList with an empty ueGroupList.";
            }
            tailf:info 'Takes effect: Next usage, Traffic Disturbance: Changing this attribute can cause loss of traffic, Dependencies: Combinations of pair of preference UE group Identifier in prefUeGroupList and UE group identifier in ueGroupList must be unique among McpcPCellNrFreqRelProfileUeCfg instances under same parent McpcPCellNrFreqRelProfile instance.

                For all preference UE group identifiers in prefUeGroupList attributes under same parent McpcPCellNrFreqRelProfile MO instance, exactly one McpcPCellNrFreqRelProfileUeCfg MO instance must exist that combines the given preference UE group identifier with an empty ueGroupList, Preference UE group list. List of preference UE group identifiers. If empty, the MO instance matches preference UE group identifiers not defined in prefUeGroupList of any other MO instances under parent MO instance.';
        }

        container rsrpCandidateA5Offsets {
            description
                "Downlink RSRP A5 measurement offsets when searching for PCell candidate.";
            uses commontypes:ReportConfigA5RsrpOffsets;
            yexte:takes-effect
                "Next usage.";
            tailf:info 'Takes effect: Next usage, Downlink RSRP A5 measurement offsets when searching for PCell candidate.';
        }

        leaf-list ueConfGroupList {
            max-elements 32;
            ordered-by user;
            description
                "UE configuration group list.

                List of UE configuration group identifiers.

                If empty, the MO instance matches all UE configuration group "+
                "identifiers.

                Which UE configuration group type that is applied is defined by "+
                "attribute ueConfGroupType in parent MO class instance.";
            type int32 {
                range "1..255";
            }
            yexte:dependencies
                "A given UE configuration group identifier can be defined in only one "+
                "ueConfGroupList among McpcPCellNrFreqRelProfileUeCfg instances under "+
                "same parent McpcPCellNrFreqRelProfile instance.";
            yexte:disturbances
                "Changing this attribute can cause loss of traffic.";
            yexte:takes-effect
                "Next usage.";
            must "count(../../../McpcPCellNrFreqRelProfileUeCfg/attributes[ueConfGroupList = current() ]) &lt;= 1" {
                error-message
                    "Only one McpcPCellNrFreqRelProfileUeCfg instance under an "+
                    "McpcPCellNrFreqRelProfile can include a specific UE configuration "+
                    "group identifier in attribute ueConfGroupList.";
            }
            tailf:info 'Takes effect: Next usage, Traffic Disturbance: Changing this attribute can cause loss of traffic, Dependencies: A given UE configuration group identifier can be defined in only one ueConfGroupList among McpcPCellNrFreqRelProfileUeCfg instances under same parent McpcPCellNrFreqRelProfile instance, UE configuration group list. List of UE configuration group identifiers. If empty, the MO instance matches all UE configuration group identifiers. Which UE configuration group type that is applied is defined by attribute ueConfGroupType in parent MO class instance.';
        }

        leaf-list ueGroupList {
            max-elements 16;
            ordered-by user;
            description
                "UE group list.

                List of UE group identifiers.

                If empty, the MO instance matches all UE group identifiers.";
            type int32 {
                range "1..255";
            }
            yexte:dependencies
                "Combinations of pair of preference UE group Identifier in "+
                "prefUeGroupList and UE group identifier in ueGroupList must be "+
                "unique among McpcPCellNrFreqRelProfileUeCfg instances under same "+
                "parent McpcPCellNrFreqRelProfile instance.

                Combination of a UE group identifier in UeGroupList and empty "+
                "prefUeGroupList must be unique among McpcPCellNrFreqRelProfileUeCfg "+
                "instances under same parent McpcPCellNrFreqRelProfile instance.";
            yexte:disturbances
                "Changing this attribute can cause loss of traffic.";
            yexte:takes-effect
                "Next usage.";
            must "count(../prefUeGroupList) &gt; 0 or
                  count(../../../McpcPCellNrFreqRelProfileUeCfg/attributes[ueGroupList = current()
                    and count(prefUeGroupList) = 0] ) &lt;= 1" {
                error-message
                    "Only one McpcPCellNrFreqRelProfileUeCfg instance under an "+
                    "McpcPCellNrFreqRelProfile can combine a specific UE group "+
                    "identifier in attribute ueGroupList with an empty prefUeGroupList.";
            }
            tailf:info 'Takes effect: Next usage, Traffic Disturbance: Changing this attribute can cause loss of traffic, Dependencies: Combinations of pair of preference UE group Identifier in prefUeGroupList and UE group identifier in ueGroupList must be unique among McpcPCellNrFreqRelProfileUeCfg instances under same parent McpcPCellNrFreqRelProfile instance.

                Combination of a UE group identifier in UeGroupList and empty prefUeGroupList must be unique among McpcPCellNrFreqRelProfileUeCfg instances under same parent McpcPCellNrFreqRelProfile instance, UE group list. List of UE group identifiers. If empty, the MO instance matches all UE group identifiers.';
        }
    }

    augment "/me3gpp:ManagedElement/gnbcucp3gpp:GNBCUCPFunction/mcpc:Mcpc/mcpcpcellnrfreqrelprofile:McpcPCellNrFreqRelProfile" {
        list McpcPCellNrFreqRelProfileUeCfg {
            description
                "Mobility control at poor coverage (MCPC) for PCell, UE "+
                "configuration group.

                Applies to UEs which use the cell as PCell. Attributes are "+
                "used on NR frequency relation level.

                MO instance McpcPCellNrFreqRelProfileUeCfg=Base is created "+
                "automatically when parent MO is created, unless created "+
                "manually in the same transaction as parent MO.

                Attributes prefUeGroupList, ueGroupList and ueConfGroupList "+
                "must be empty in instance McpcPCellNrFreqRelProfileUeCfg=Base "+
                "but cannot all be empty in other instances of "+
                "McpcPCellNrFreqRelProfileUeCfg under same parent "+
                "McpcPCellNrFreqRelProfile.";
            yexte:precondition
                "McpcPCellNrFreqRelProfileUeCfg=Base MO instance can only be "+
                "created in the same transaction as parent MO and cannot be "+
                "deleted unless parent MO is deleted. Other instances can be "+
                "created and deleted manually.

                Maximum 31 McpcPCellNrFreqRelProfileUeCfg instances, with RDN "+
                "different from Base, can be created.";
            must "count(../McpcPCellNrFreqRelProfileUeCfg) &lt; 32 or
                  count(../McpcPCellNrFreqRelProfileUeCfg/id[. = 'Base'] ) = 1" {
                error-message
                    "Maximum 31 McpcPCellNrFreqRelProfileUeCfg instances under an "+
                    "McpcPCellNrFreqRelProfile can be created with RDN different from Base.";
            }
            must "count(../McpcPCellNrFreqRelProfileUeCfg/attributes[prefUeGroupList = current()/attributes/prefUeGroupList
                    and ueGroupList = current()/attributes/ueGroupList] ) &lt;= 1" {
                error-message
                    "The combinations of a pair of UE group identifier in ueGroupList "+
                    "and preference UE group identifier in prefUeGroupList must be "+
                    "unique among McpcPCellNrFreqRelProfileUeCfg under an "+
                    "McpcPCellNrFreqRelProfile.";
            }
            must "./id != 'Base'
                  or ( count(./attributes/ueConfGroupList) = 0
                       and count(./attributes/ueGroupList) = 0
                       and count(./attributes/prefUeGroupList) = 0 )" {
                error-message
                    "McpcPCellNrFreqRelProfileUeCfg::prefUeGroupList, ueGroupList and "+
                    "ueConfGroupList must be empty in the McpcPCellNrFreqRelProfileUeCfg=Base "+
                    "instance.";
            }
            must "./id = 'Base'
                  or not ( count(./attributes/ueConfGroupList) = 0
                           and count(./attributes/ueGroupList) = 0
                           and count(./attributes/prefUeGroupList) = 0 )" {
                error-message
                    "McpcPCellNrFreqRelProfileUeCfg::prefUeGroupList, ueGroupList "+
                    "and ueConfGroupList can only be empty in the "+
                    "McpcPCellNrFreqRelProfileUeCfg=Base instance.";
            }
            key id;
            max-elements 32;
            uses top3gpp:Top_Grp;
            container attributes {
                uses McpcPCellNrFreqRelProfileUeCfgGrp;
                uses commontypes:UserLabelGrp;
            }
            tailf:info 'Precondition: McpcPCellNrFreqRelProfileUeCfg=Base MO instance can only be created in the same transaction as parent MO and cannot be deleted unless parent MO is deleted. Other instances can be created and deleted manually.

                Maximum 31 McpcPCellNrFreqRelProfileUeCfg instances, with RDN different from Base, can be created, Mobility control at poor coverage (MCPC) for PCell, UE configuration group. Applies to UEs which use the cell as PCell. Attributes are used on NR frequency relation level. MO instance McpcPCellNrFreqRelProfileUeCfg=Base is created automatically when parent MO is created, unless created manually in the same transaction as parent MO. Attributes prefUeGroupList, ueGroupList and ueConfGroupList must be empty in instance McpcPCellNrFreqRelProfileUeCfg=Base but cannot all be empty in other instances of McpcPCellNrFreqRelProfileUeCfg under same parent McpcPCellNrFreqRelProfile.';
        }
    }
}
