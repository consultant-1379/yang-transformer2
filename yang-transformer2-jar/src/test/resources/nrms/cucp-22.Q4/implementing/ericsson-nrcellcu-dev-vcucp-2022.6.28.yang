// Generated by eyang-preprocessor (1.22.0-48 2022-01-20 09:10:06 CET) on Jun 30, 2022, 8:31:39 AM
module ericsson-nrcellcu-dev-vcucp {
    yang-version 1.1;
    namespace urn:rdns:com:ericsson:oammodel:ericsson-nrcellcu-dev-vcucp;
    prefix nrcellcu3gppdev;

    import _3gpp-common-yang-types {
        prefix types3gpp;
    }
    import _3gpp-common-managed-element {
        prefix me3gpp;
    }
    import _3gpp-nr-nrm-gnbcucpfunction {
        prefix gnbcucp3gpp;
    }
    import _3gpp-nr-nrm-nrcellcu {
        prefix nrcellcu3gpp;
    }
    import ericsson-yang-extensions {
        prefix yexte;
    }

    organization
        "Ericsson AB";
    contact
        "Ericsson first line support via email";
    description
        "The module defines the NRCellCU data model deviations for the Ericsson vCU-CP.

        Copyright (c) 2020-2022 Ericsson AB. All rights reserved.";

    revision 2022-06-28 {
        description
            "Removed module-status preliminary.";
        yexte:version 1;
        yexte:release 1;
        yexte:correction 0;
        reference
            "RFC 7950: The YANG 1.1 Data Modeling Language";
    }

    revision 2021-11-15 {
        description
            "Replaced 3GPP variant of pLMNInfoList to custom type due to update of  _3gpp-nr-nrm-nrcellcu module.";
        yexte:version 1;
        yexte:release 0;
        yexte:correction 0;
        reference
            "RFC 7950: The YANG 1.1 Data Modeling Language";
    }

    revision 2021-08-19 {
        description
            "Changed min-elements for pLMNInfoList to 0.";
        yexte:version 0;
        yexte:release 3;
        yexte:correction 0;
        reference
            "RFC 7950: The YANG 1.1 Data Modeling Language";
    }

    revision 2021-01-11 {
        description
            "Remove support for pLMNInfoList:sNssai.";
        yexte:version 0;
        yexte:release 2;
        yexte:correction 0;
        reference
            "RFC 7950: The YANG 1.1 Data Modeling Language";
    }

    revision 2020-11-18 {
        description
            "Deviations on _3gpp-nr-nrm-nrcellcu.";
        yexte:version 0;
        yexte:release 1;
        yexte:correction 0;
        reference
            "RFC 7950: The YANG 1.1 Data Modeling Language";
    }

    deviation /me3gpp:ManagedElement/gnbcucp3gpp:GNBCUCPFunction/nrcellcu3gpp:NRCellCU/nrcellcu3gpp:ManagedNFService {
        description
            "Managed Network Function Service is not supported for NRCellCU.";
        deviate not-supported;
    }

    deviation /me3gpp:ManagedElement/gnbcucp3gpp:GNBCUCPFunction/nrcellcu3gpp:NRCellCU/nrcellcu3gpp:PerfMetricJob {
        description
            "Performance Metric Job is not supported for NRCellCU.";
        deviate not-supported;
    }

    deviation /me3gpp:ManagedElement/gnbcucp3gpp:GNBCUCPFunction/nrcellcu3gpp:NRCellCU/nrcellcu3gpp:ThresholdMonitor {
        description
            "Threshold Monitor is not supported for NRCellCU.";
        deviate not-supported;
    }

    deviation /me3gpp:ManagedElement/gnbcucp3gpp:GNBCUCPFunction/nrcellcu3gpp:NRCellCU/nrcellcu3gpp:TraceJob {
        description
        "Trace Job is not supported for NRCellCU.";
        deviate not-supported;
    }

    deviation /me3gpp:ManagedElement/gnbcucp3gpp:GNBCUCPFunction/nrcellcu3gpp:NRCellCU/nrcellcu3gpp:attributes/nrcellcu3gpp:SupportedPerfMetricGroup {
        description
            "Supported Performance Metrics is not supported for NRCellCU.";
        deviate not-supported;
    }

    deviation /me3gpp:ManagedElement/gnbcucp3gpp:GNBCUCPFunction/nrcellcu3gpp:NRCellCU/nrcellcu3gpp:attributes/nrcellcu3gpp:vnfParametersList {
        description
            "NRCellCU::vnfParametersList is not supported.";
        deviate not-supported;
    }

    deviation /me3gpp:ManagedElement/gnbcucp3gpp:GNBCUCPFunction/nrcellcu3gpp:NRCellCU/nrcellcu3gpp:attributes/nrcellcu3gpp:peeParametersList {
        description
            "NRCellCU::peeParametersList is not supported.";
        deviate not-supported;
    }

    deviation /me3gpp:ManagedElement/gnbcucp3gpp:GNBCUCPFunction/nrcellcu3gpp:NRCellCU/nrcellcu3gpp:attributes/nrcellcu3gpp:priorityLabel {
        description
            "NRCellCU::priorityLabel is not supported.";
        deviate not-supported;
    }

    deviation /me3gpp:ManagedElement/gnbcucp3gpp:GNBCUCPFunction/nrcellcu3gpp:NRCellCU/nrcellcu3gpp:attributes/nrcellcu3gpp:nRFrequencyRef {
        deviate replace {
            config true;
        }
    }

    deviation /me3gpp:ManagedElement/gnbcucp3gpp:GNBCUCPFunction/nrcellcu3gpp:NRCellCU/nrcellcu3gpp:attributes/nrcellcu3gpp:pLMNInfoList {
        description
            "NRCellCU::pLMNInfoList is not supported because of required keys sd and sst.";
        deviate not-supported;
    }
}
