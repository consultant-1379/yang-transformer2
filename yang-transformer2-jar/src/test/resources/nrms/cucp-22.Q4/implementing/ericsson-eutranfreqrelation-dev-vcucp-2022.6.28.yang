// Generated by eyang-preprocessor (1.22.0-48 2022-01-20 09:10:06 CET) on Jun 30, 2022, 8:31:37 AM
module ericsson-eutranfreqrelation-dev-vcucp {
    yang-version 1.1;
    namespace urn:rdns:com:ericsson:oammodel:ericsson-eutranfreqrelation-dev-vcucp;
    prefix eutranfreqrel3gppdev;

    import _3gpp-common-managed-element {
        prefix me3gpp;
    }
    import _3gpp-nr-nrm-gnbcucpfunction {
        prefix gnbcucp3gpp;
    }
    import _3gpp-nr-nrm-nrcellcu {
        prefix nrcellcu3gpp;
    }
    import _3gpp-nr-nrm-eutranfreqrelation {
        prefix eutranfreqrel3gpp;
    }
    import ericsson-nrcellcu-ext-vcucp {
        prefix nrcellcu3gppext;
    }
    import ericsson-yang-extensions {
        prefix yexte;
    }

    organization
        "Ericsson AB";
    contact
        "Ericsson first line support via email";
    description
        "The module defines the EUtranFreqRelation data model deviations for the Ericsson vCU-CP.

        Copyright (c) 2021-2022 Ericsson AB. All rights reserved.";

    revision 2022-06-28 {
        description
            "Removed module-status preliminary.";
        yexte:version 1;
        yexte:release 2;
        yexte:correction 0;
        reference
            "RFC 7950: The YANG 1.1 Data Modeling Language";
    }

    revision 2022-03-14 {
        description
            "Remove deviation for not supporting cellReselectionSubPriority.";
        yexte:version 1;
        yexte:release 1;
        yexte:correction 0;
        reference
            "RFC 7950: The YANG 1.1 Data Modeling Language";
    }

    revision 2021-06-06 {
        description
            "Add must statements related to threshXHighQ and threshXLowQ.";
        yexte:version 1;
        yexte:release 0;
        yexte:correction 1;
        reference
            "RFC 7950: The YANG 1.1 Data Modeling Language";
    }

    revision 2021-03-19 {
        description
            "Parity with ECIM R1A79.";
        yexte:version 1;
        yexte:release 0;
        yexte:correction 0;
        reference
            "RFC 7950: The YANG 1.1 Data Modeling Language";
    }

    revision 2021-01-11 {
        description
            "Initial version of the EUtranFreqRelation model.";
        yexte:version 0;
        yexte:release 1;
        yexte:correction 0;
        reference
            "RFC 7950: The YANG 1.1 Data Modeling Language";
    }

    deviation /me3gpp:ManagedElement/gnbcucp3gpp:GNBCUCPFunction/nrcellcu3gpp:NRCellCU/eutranfreqrel3gpp:EUtranFreqRelation/eutranfreqrel3gpp:ManagedNFService {
        description "Managed Network Function Service is not supported for EUtranFreqRelation.";
        deviate not-supported;
    }

    deviation /me3gpp:ManagedElement/gnbcucp3gpp:GNBCUCPFunction/nrcellcu3gpp:NRCellCU/eutranfreqrel3gpp:EUtranFreqRelation/eutranfreqrel3gpp:PerfMetricJob {
        description "Performance Metric Job is not supported for EUtranFreqRelation.";
        deviate not-supported;
    }

    deviation /me3gpp:ManagedElement/gnbcucp3gpp:GNBCUCPFunction/nrcellcu3gpp:NRCellCU/eutranfreqrel3gpp:EUtranFreqRelation/eutranfreqrel3gpp:ThresholdMonitor {
        description "Threshold Monitor is not supported for EUtranFreqRelation.";
        deviate not-supported;
    }

    deviation /me3gpp:ManagedElement/gnbcucp3gpp:GNBCUCPFunction/nrcellcu3gpp:NRCellCU/eutranfreqrel3gpp:EUtranFreqRelation/eutranfreqrel3gpp:TraceJob {
        description "Trace Job is not supported for EUtranFreqRelation.";
        deviate not-supported;
    }

    deviation /me3gpp:ManagedElement/gnbcucp3gpp:GNBCUCPFunction/nrcellcu3gpp:NRCellCU/eutranfreqrel3gpp:EUtranFreqRelation/eutranfreqrel3gpp:attributes/eutranfreqrel3gpp:SupportedPerfMetricGroup {
        description "Supported Performance Metrics is not supported for EUtranFreqRelation.";
        deviate not-supported;
    }

    deviation /me3gpp:ManagedElement/gnbcucp3gpp:GNBCUCPFunction/nrcellcu3gpp:NRCellCU/eutranfreqrel3gpp:EUtranFreqRelation/eutranfreqrel3gpp:attributes/eutranfreqrel3gpp:vnfParametersList {
        description "EUtranFreqRelation::vnfParametersList is not supported.";
        deviate not-supported;
    }

    deviation /me3gpp:ManagedElement/gnbcucp3gpp:GNBCUCPFunction/nrcellcu3gpp:NRCellCU/eutranfreqrel3gpp:EUtranFreqRelation/eutranfreqrel3gpp:attributes/eutranfreqrel3gpp:peeParametersList {
        description "EUtranFreqRelation::peeParametersList is not supported.";
        deviate not-supported;
    }

    deviation /me3gpp:ManagedElement/gnbcucp3gpp:GNBCUCPFunction/nrcellcu3gpp:NRCellCU/eutranfreqrel3gpp:EUtranFreqRelation/eutranfreqrel3gpp:attributes/eutranfreqrel3gpp:priorityLabel {
        description "EUtranFreqRelation::priorityLabel is not supported.";
        deviate not-supported;
    }

    deviation /me3gpp:ManagedElement/gnbcucp3gpp:GNBCUCPFunction/nrcellcu3gpp:NRCellCU/eutranfreqrel3gpp:EUtranFreqRelation/eutranfreqrel3gpp:attributes/eutranfreqrel3gpp:cellIndividualOffset {
        description "EUtranFreqRelation::cellIndividualOffset is not supported.";
        deviate not-supported;
    }

    deviation /me3gpp:ManagedElement/gnbcucp3gpp:GNBCUCPFunction/nrcellcu3gpp:NRCellCU/eutranfreqrel3gpp:EUtranFreqRelation/eutranfreqrel3gpp:attributes/eutranfreqrel3gpp:blackListEntry {
        description "EUtranFreqRelation::blackListEntry is not supported.";
        deviate not-supported;
    }

    deviation /me3gpp:ManagedElement/gnbcucp3gpp:GNBCUCPFunction/nrcellcu3gpp:NRCellCU/eutranfreqrel3gpp:EUtranFreqRelation/eutranfreqrel3gpp:attributes/eutranfreqrel3gpp:blackListEntryIdleMode {
        description "EUtranFreqRelation::blackListEntryIdleMode is not supported.";
        deviate not-supported;
    }

    deviation /me3gpp:ManagedElement/gnbcucp3gpp:GNBCUCPFunction/nrcellcu3gpp:NRCellCU/eutranfreqrel3gpp:EUtranFreqRelation/eutranfreqrel3gpp:attributes/eutranfreqrel3gpp:qOffsetFreq {
        description "EUtranFreqRelation::qOffsetFreq is not supported.";
        deviate not-supported;
    }

    deviation "/me3gpp:ManagedElement/gnbcucp3gpp:GNBCUCPFunction/nrcellcu3gpp:NRCellCU/eutranfreqrel3gpp:EUtranFreqRelation/eutranfreqrel3gpp:attributes" {
        deviate add {
            must "(./eutranfreqrel3gpp:threshXHighQ and ../../nrcellcu3gpp:attributes/nrcellcu3gppext:threshServingLowQ) or
                  (not(./eutranfreqrel3gpp:threshXHighQ) and not(../../nrcellcu3gpp:attributes/nrcellcu3gppext:threshServingLowQ))" {
                error-message
                    "threshXHighQ must be empty if NRCellCU::threshServingLowQ is empty or set if "+
                    "NRCellCU::threshServingLowQ is set.";
            }
            must "(./eutranfreqrel3gpp:threshXLowQ and ../../nrcellcu3gpp:attributes/nrcellcu3gppext:threshServingLowQ) or
                  (not(./eutranfreqrel3gpp:threshXLowQ) and not(../../nrcellcu3gpp:attributes/nrcellcu3gppext:threshServingLowQ))" {
                error-message
                    "threshXLowQ must be empty if NRCellCU::threshServingLowQ is empty or set if "+
                    "NRCellCU::threshServingLowQ is set.";
            }
        }
    }
}
