// Generated by eyang-preprocessor (1.22.0-48 2022-01-20 09:10:06 CET) on Jun 30, 2022, 8:31:35 AM
module ericsson-anrfunction-vcucp {
    yang-version 1.1;
    namespace "urn:rdns:com:ericsson:oammodel:ericsson-anrfunction-vcucp";
    prefix anrfunction;

    import tailf-common {
        prefix tailf;
    }
    import _3gpp-common-managed-element {
        prefix "me3gpp";
    }
    import _3gpp-nr-nrm-gnbcucpfunction {
        prefix "gnbcucp3gpp";
    }
    import _3gpp-common-top {
        prefix "top3gpp";
    }
    import ericsson-yang-extensions {
        prefix "yexte";
    }

    organization
        "Ericsson AB";
    contact
        "Ericsson first line support via email";
    description
        "The module defines the AnrFunction data model for the Ericsson vCU-CP.

        Copyright (c) 2021-2022 Ericsson AB. All rights reserved.";

    revision 2022-06-28 {
        description
            "Removed module-status preliminary.
             Removed preliminary status from removeEnbTime.";
        yexte:version 0;
        yexte:release 4;
        yexte:correction 0;
        reference
            "RFC 7950: The YANG 1.1 Data Modeling Language";
    }

    revision 2022-03-14 {
        description
            "Added attributes removeEnbTime and removeFreqRelTime.
             Updated description for removeGnbTime.
             Updated description and removed takes-effect for removeNrelTime.";
        yexte:version 0;
        yexte:release 3;
        yexte:correction 0;
        reference
            "RFC 7950: The YANG 1.1 Data Modeling Language";
    }

    revision 2021-11-05 {
        description
            "Added removeGnbTime attribute";
        yexte:version 0;
        yexte:release 2;
        yexte:correction 0;
        reference
            "RFC 7950: The YANG 1.1 Data Modeling Language";
    }

    revision 2021-06-08 {
        description
            "Changed error message for a must statement.";
        yexte:version 0;
        yexte:release 1;
        yexte:correction 1;
        reference
            "RFC 7950: The YANG 1.1 Data Modeling Language";
    }

    revision 2021-04-30 {
        description
            "Initial version of the AnrFunction model.";
        yexte:version 0;
        yexte:release 1;
        yexte:correction 0;
        reference
            "RFC 7950: The YANG 1.1 Data Modeling Language";
    }

    grouping AnrFunctionGrp {
        description "Represents the AnrFunction IOC.";

        leaf removeEnbTime {
            description
                "Time while neighbor eNodeB can be disconnected from gNodeB before " +
                "being considered for removal.

                Value 1000 means no automatic removal is performed.";
            type int32 {
                range "1..1000";
            }
            default 7;
            units day;
        }

        leaf removeFreqRelTime {
            description
                "Maximum time an NRFreqRelation can be unreferenced before being " +
                "considered for removal.

                Value 10000 means no automatic removal is performed.";
            type int32 {
                range "10..10000";
            }
            default 15;
            units minute;
            status current {
                yexte:preliminary;
            }
            tailf:info 'Preliminary, Maximum time an NRFreqRelation can be unreferenced before being considered for removal. Value 10000 means no automatic removal is performed.';
        }

        leaf removeGnbTime {
            description
              "Time a neighbor gNodeB can be without a relation to this gNodeB "+
              "before being considered for removal.

                1000 means no automatic removal is performed.";
            type int32 {
                range "1..1000";
            }
            default 7;
            units day;
        }

        leaf removeNrelTime {
            description
              "Maximum time while unused NR cell or E-UTRAN cell remains in the Managed Function.

              Value 1000 means no automatic removal is performed.";
            type int32 {
                range "1..1000";
            }
            default 7;
            units day;
        }
    }

    augment "/me3gpp:ManagedElement/gnbcucp3gpp:GNBCUCPFunction" {
        list AnrFunction {
            description
                "Parameters and constraints for ANR functions.
                The RDN of this MO must always be AnrFunction=1";
            key id;
            max-elements 1;
            uses top3gpp:Top_Grp {
                refine id {
                    must '. = "1"' {
                        error-message
                          "The RDN of this MO must always be AnrFunction=1";
                    }
                }
            }
            container attributes {
                uses AnrFunctionGrp;
            }
        }
    }
}
