// Generated by eyang-preprocessor (1.22.0-48 2022-01-20 09:10:06 CET) on Jun 30, 2022, 8:31:44 AM
module ericsson-uemcnrfreqrelprofile-vcucp {
    yang-version 1.1;
    namespace "urn:rdns:com:ericsson:oammodel:ericsson-uemcnrfreqrelprofile-vcucp";
    prefix "uemcnrfreqrelprofilevcucp";

    import tailf-common {
        prefix tailf;
    }
    import _3gpp-common-managed-element {
        prefix "me3gpp";
    }
    import _3gpp-nr-nrm-gnbcucpfunction {
        prefix "gnbcucp3gpp";
    }
    import _3gpp-common-top {
        prefix "top3gpp";
    }
    import ericsson-yang-extensions {
        prefix "yexte";
    }
    import ericsson-uemc-vcucp {
        prefix uemcvcucp;
    }
    import ericsson-common-types-vcucp {
        prefix commontypes;
    }

    organization
      "Ericsson AB";
    contact
      "Ericsson first line support via email";
    description
      "The module defines the UeMCNrFreqRelProfile data model for the Ericsson vCU-CP.

       Copyright (c) 2021-2022 Ericsson AB. All rights reserved.";

    revision 2022-06-28 {
        description
            "Removed module-status preliminary.
             Removed preliminary status from ueConfGroupType.";
        yexte:version 1;
        yexte:release 2;
        yexte:correction 0;
        reference
            "RFC 7950: The YANG 1.1 Data Modeling Language";
    }

    revision 2022-03-14 {
        description
          "Updated description for UeMCNrFreqRelProfile.
           Added attributes ueConfGroupType and userLabel.";
        yexte:version 1;
        yexte:release 1;
        yexte:correction 0;
        reference
          "RFC 7950: The YANG 1.1 Data Modeling Language";
    }

    revision 2021-11-05 {
        description
          "Removed default values for the attributes connModeAllowedPCell and connModePrioPCell.
           Updated precondition for UeMCNrFreqRelProfile.";
        yexte:version 1;
        yexte:release 0;
        yexte:correction 1;
        reference
          "RFC 7950: The YANG 1.1 Data Modeling Language";
    }

    revision 2021-10-04 {
        description
          "Marked the attributes connModeAllowedPCell and connModePrioPCell as obsolete.";
        yexte:version 1;
        yexte:release 0;
        yexte:correction 0;
        reference
          "RFC 7950: The YANG 1.1 Data Modeling Language";
    }

    revision 2021-09-13 {
        description
          "Updated description and precondition for the UeMCNrFreqRelProfile list.";
        yexte:version 0;
        yexte:release 1;
        yexte:correction 1;
        reference
          "RFC 7950: The YANG 1.1 Data Modeling Language";
    }

    revision 2021-04-16 {
        description
          "Initial version of the UeMCNrFreqRelProfile model.";
        yexte:version 0;
        yexte:release 1;
        yexte:correction 0;
        reference
          "RFC 7950: The YANG 1.1 Data Modeling Language";
    }

    grouping UeMCNrFreqRelProfileGrp {
        description
            "Represents the UeMCNrFreqRelProfile IOC.";

        leaf connModeAllowedPCell {
            description
                "Whether it is allowed to place PCell on NR frequency defined by NR"
                + " frequency relation.

                Applies to UEs which use cell as PCell.";
            type boolean;
            status obsolete {
                yexte:status-information
                    "Since 21.Q4. Replaced by "+
                    "UeMCNrFreqRelProfileUeCfg::connModeAllowedPCell. Planned to be "+
                    "removed.";
            }
            yexte:takes-effect
                "Next usage.";
            tailf:info 'Takes effect: Next usage, Status Info: Since 21.Q4. Replaced by UeMCNrFreqRelProfileUeCfg::connModeAllowedPCell. Planned to be removed, Obsolete, Whether it is allowed to place PCell on NR frequency defined by NR frequency relation. Applies to UEs which use cell as PCell.';
        }

        leaf connModePrioPCell {
            description
              "Connected mode PCell priority for NR frequency relation.

               Applies to UEs that use cell as PCell.

               Used to decide preference on which NR frequency to place PCell in "
            + "connected mode.

               0 means frequency relation with lowest priority.
               7 means frequency relation with highest priority.

               Applicable only when connModeAllowedPCell is set to true.";
            type int32 {
                range "0..7";
            }
            status obsolete {
                yexte:status-information
                    "Since 21.Q4. Replaced by "+
                    "UeMCNrFreqRelProfileUeCfg::connModePrioPCell. Planned to be "+
                    "removed.";
            }
            yexte:takes-effect
                "Next usage.";
            tailf:info 'Takes effect: Next usage, Status Info: Since 21.Q4. Replaced by UeMCNrFreqRelProfileUeCfg::connModePrioPCell. Planned to be removed, Obsolete, Connected mode PCell priority for NR frequency relation. Applies to UEs that use cell as PCell. Used to decide preference on which NR frequency to place PCell in connected mode. 0 means frequency relation with lowest priority. 7 means frequency relation with highest priority. Applicable only when connModeAllowedPCell is set to true.';
        }

        leaf ueConfGroupType {
            description
                "UE configuration Group Type.

                Defines which UE configuration group type that is applied in the "+
                "contained MO class UeMCNrFreqRelProfileUeCfg.";
            type commontypes:UeConfGroupType;
            default UE_MOBILITY_GROUP;
            yexte:disturbances
                "Changing this attribute can cause loss of traffic.";
            yexte:takes-effect
                "Next usage.";
            tailf:info 'Takes effect: Next usage, Traffic Disturbance: Changing this attribute can cause loss of traffic, UE configuration Group Type. Defines which UE configuration group type that is applied in the contained MO class UeMCNrFreqRelProfileUeCfg.';
        }
    }

    augment "/me3gpp:ManagedElement/gnbcucp3gpp:GNBCUCPFunction/uemcvcucp:UeMC" {
        list UeMCNrFreqRelProfile {
            description
                "UE mobility control attributes.

                Attributes are used on NR frequency relation level.

                MO instance UeMCNrFreqRelProfile=Default is created "+
                "automatically when parent MO is created, unless created manually "+
                "in the same transaction as parent MO.

                If NRFreqRelation::ueMCNrFreqRelProfileRef is non-empty, "+
                "attributes from referenced MO instance are used.
                If NRFreqRelation::ueMCNrFreqRelProfileRef is empty, attribute "+
                "default values according to UeMCNrFreqRelProfile and "+
                "UeMCNrFreqRelProfileUeCfg MO class definitions are used.";
            key id;
            uses top3gpp:Top_Grp;
            container attributes {
                uses UeMCNrFreqRelProfileGrp;
                uses commontypes:UserLabelGrp;
            }
            yexte:precondition
                "UeMCNrFreqRelProfile=Default MO instance must not be deleted unless "+
                "parent MO is deleted. Other instances can be created and deleted "+
                "manually.";
            tailf:info 'Precondition: UeMCNrFreqRelProfile=Default MO instance must not be deleted unless parent MO is deleted. Other instances can be created and deleted manually, UE mobility control attributes. Attributes are used on NR frequency relation level. MO instance UeMCNrFreqRelProfile=Default is created automatically when parent MO is created, unless created manually in the same transaction as parent MO. If NRFreqRelation::ueMCNrFreqRelProfileRef is non-empty, attributes from referenced MO instance are used. If NRFreqRelation::ueMCNrFreqRelProfileRef is empty, attribute default values according to UeMCNrFreqRelProfile and UeMCNrFreqRelProfileUeCfg MO class definitions are used.';
        }
    }
}
