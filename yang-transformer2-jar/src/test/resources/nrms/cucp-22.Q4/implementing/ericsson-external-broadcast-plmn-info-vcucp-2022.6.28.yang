// Generated by eyang-preprocessor (1.22.0-48 2022-01-20 09:10:06 CET) on Jun 30, 2022, 8:31:37 AM
module ericsson-external-broadcast-plmn-info-vcucp {
    yang-version 1.1;
    namespace "urn:rdns:com:ericsson:oammodel:ericsson-external-broadcast-plmn-info-vcucp";
    prefix "externalbroadcastplmninfo";

    import tailf-common {
        prefix tailf;
    }
    import _3gpp-common-managed-element {
        prefix "me3gpp";
    }
    import _3gpp-nr-nrm-gnbcucpfunction {
        prefix "gnbcucp3gpp";
    }
    import _3gpp-common-top {
        prefix "top3gpp";
    }
    import _3gpp-common-yang-types {
        prefix types3gpp;
    }
    import ericsson-nrnetwork-vcucp {
        prefix "nrnetwork";
    }
    import ericsson-externalgnbcucpfunction-vcucp {
        prefix "externalgnbcucpfunctionvcucp";
    }
    import ericsson-externalnrcellcu-vcucp {
        prefix "externalnrcellcu";
    }
    import ericsson-yang-extensions {
        prefix "yexte";
    }
    import ericsson-common-types-vcucp {
        prefix commontypes;
    }

    organization
      "Ericsson AB";
    contact
      "Ericsson first line support via email";
    description
      "The module defines the ExternalBroadcastPLMNInfo data model for the Ericsson vCU-CP.

       Copyright (c) 2021-2022 Ericsson AB. All rights reserved.";

    revision 2022-06-28 {
        description
            "Removed module-status preliminary.";
        yexte:version 1;
        yexte:release 1;
        yexte:correction 0;
        reference
            "RFC 7950: The YANG 1.1 Data Modeling Language";
    }

    revision 2021-11-05 {
        description
            "createdBy is marked obsolete.";
        yexte:version 1;
        yexte:release 0;
        yexte:correction 0;
        reference
            "RFC 7950: The YANG 1.1 Data Modeling Language";
    }

    revision 2021-05-06 {
        description
            "Remove is-system-created and restricted extensions from configurable attributes";
        yexte:version 0;
        yexte:release 2;
        yexte:correction 0;
        reference
            "RFC 7950: The YANG 1.1 Data Modeling Language";
    }

    revision 2021-03-31 {
        description
          "Initial version of the ExternalBroadcastPLMNInfo model.";
        yexte:version 0;
        yexte:release 1;
        yexte:correction 0;
        reference
          "RFC 7950: The YANG 1.1 Data Modeling Language";
    }

    grouping ExternalBroadcastPLMNInfoGrp {
        description
          "Represents the ExternalBroadcastPLMNInfo IOC.";

        leaf createdBy {
            description
              "Creator of MO.

               Can be one of following:
               - Xn.
               - Operator.";
            type commontypes:CreatedByNR;
            config false;
            status obsolete {
                yexte:status-information
                    "Since 21.Q2. Planned to be removed.";
            }
            tailf:info 'Status Info: Since 21.Q2. Planned to be removed, Obsolete, Creator of MO. Can be one of following: - Xn. - Operator.';
        }

        leaf nRTAC {
            description
              "NR Tracking Area Code (TAC).";
            type int32 {
                range "0..16777215";
            }
            mandatory true;
            yexte:takes-effect "Next MO unlock";
            yexte:precondition "Value can only be changed if TermPointToGNB has administrativeState LOCKED.";
            tailf:info 'Precondition: Value can only be changed if TermPointToGNB has administrativeState LOCKED, Takes effect: Next MO unlock, NR Tracking Area Code (TAC).';
        }

        list pLMNIdList {
            description
              "List of broadcast PLMNs.";
            key "mcc mnc";
            min-elements 1;
            max-elements 12;
            uses types3gpp:PLMNId;
            yexte:takes-effect
                "Next MO unlock";
            yexte:precondition
                "Value can only be changed if TermPointToGNB has administrativeState LOCKED.";
            tailf:info 'Precondition: Value can only be changed if TermPointToGNB has administrativeState LOCKED, Takes effect: Next MO unlock, List of broadcast PLMNs.';
        }
    }

    augment "/me3gpp:ManagedElement/gnbcucp3gpp:GNBCUCPFunction/nrnetwork:NRNetwork/externalgnbcucpfunctionvcucp:ExternalGNBCUCPFunction/externalnrcellcu:ExternalNRCellCU" {
        list ExternalBroadcastPLMNInfo {
            description
              "PLMN-related information that is served by external NR cell.

               This MO is created automatically. Can also be created and deleted manually.

               Created automatically when Xn message is received, unless it already exists.
               Deleted automatically.

               When created automatically, the RDNs of these MOs are ExternalBroadcastPLMNInfo=1 to ExternalBroadcastPLMNInfo=12.
               RDN value is assigned based on order received over Xn";
            key id;
            max-elements 12;
            uses top3gpp:Top_Grp;
            container attributes {
                uses ExternalBroadcastPLMNInfoGrp;
            }
            reference
              "3GPP TS 38.423";
            yexte:precondition
                "MO can be created and deleted manually, only if TermPointToGNB has administrativeState LOCKED";
            tailf:info 'Precondition: MO can be created and deleted manually, only if TermPointToGNB has administrativeState LOCKED, PLMN-related information that is served by external NR cell. This MO is created automatically. Can also be created and deleted manually. Created automatically when Xn message is received, unless it already exists. Deleted automatically. When created automatically, the RDNs of these MOs are ExternalBroadcastPLMNInfo=1 to ExternalBroadcastPLMNInfo=12. RDN value is assigned based on order received over Xn';
        }
    }
}
