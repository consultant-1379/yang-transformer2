// Generated by eyang-preprocessor (1.22.0-48 2022-01-20 09:10:06 CET) on Jun 30, 2022, 8:31:44 AM
module ericsson-termpointtoamf-vcucp {
    yang-version 1.1;
    namespace urn:rdns:com:ericsson:oammodel:ericsson-termpointtoamf-vcucp;
    prefix tptoamfvcucp;

    import tailf-common {
        prefix tailf;
    }
    import _3gpp-common-managed-element {
        prefix me3gpp;
    }
    import _3gpp-nr-nrm-gnbcucpfunction {
        prefix gnbcucp3gpp;
    }
    import _3gpp-common-top {
        prefix top3gpp;
    }
    import _3gpp-common-yang-types {
        prefix types3gpp;
    }
    import ericsson-yang-extensions {
        prefix yexte;
    }
    import ericsson-yang-types {
        prefix "typese";
    }
    import ietf-inet-types {
        prefix inet;
    }
    import ericsson-common-types-vcucp {
        prefix commontypes;
    }
    import ericsson-notifications {
        prefix notife;
    }

    organization
        "Ericsson AB";
    contact
        "Ericsson first line support via email";
    description
        "The module defines the TermPointToAmf data model for the Ericsson "+
        "vCU-CP.

         Copyright (c) 2021-2022 Ericsson AB. All rights reserved.";

    revision 2022-06-28 {
        description
            "Removed module-status preliminary.";
        yexte:version 1;
        yexte:release 2;
        yexte:correction 0;
        reference
            "RFC 7950: The YANG 1.1 Data Modeling Language";
    }

    revision 2021-07-27 {
        description
            "Bug Fix, leaf-list state notifiable compatibility issue. Adds extension notife:notifiable-state-data false to availabilityStatus.";
        yexte:version 1;
        yexte:release 1;
        yexte:correction 0;
        reference
            "RFC 7950: The YANG 1.1 Data Modeling Language";
    }

    revision 2021-06-16 {
        description
            "Initial version of the TermPointToAmf model.";
        yexte:version 0;
        yexte:release 1;
        yexte:correction 0;
        reference
            "RFC 7950: The YANG 1.1 Data Modeling Language";
    }

    typedef PWSRestartHandling {
        description
          "Whether PWS restart handling is supported.";
        type enumeration {
            enum DISABLED {
                value 0;
                description
                  "PWS restart and failure messages cannot be sent to AMF.";
            }
            enum ENABLED {
                value 1;
                description
                  "PWS restart and failure messages can be sent to AMF.";
            }
        }
    }

    grouping TermPointToAmfGrp {
        description
          "Models an NG link AMF termination point.

          Reference Ericsson documentation";
        leaf administrativeState {
            description
              "The administrative state.

              If set to SHUTTINGDOWN, the state is immediately brought to "+
              "LOCKED.";
            type types3gpp:AdministrativeState;
            default LOCKED;
            reference
              "ITU-T Rec. X.731";
        }

        leaf amfName {
            description
              "Used by ENM to identify an AMF.

              Set at successful NG-SETUP.";
            config false;
            type string;
            reference
              "3GPP TS 38.413";
        }

        leaf-list availabilityStatus {
            description
                "The availability status.

                It contains details about operationalState.";
            config false;
            notife:notifiable-state-data false;
            type typese:avail-status;
            reference
                "ITU-T Rec. X.731";
            tailf:meta-data notife:notifiable-state-data {
                tailf:meta-value false;
            }
        }

        leaf defaultAmf {
            description
              "Whether the TermPointToAmf instance is a default AMF or not.";
            type boolean;
            default true;
            yexte:takes-effect
              "Next MO unlock";
            yexte:precondition
              "Value can only be changed if administrativeState is LOCKED.";
            tailf:info 'Precondition: Value can only be changed if administrativeState is LOCKED, Takes effect: Next MO unlock, Whether the TermPointToAmf instance is a default AMF or not.';
        }

        leaf domainName {
            description
              "Fully qualified domain name of AMF.

              Consists of one or more labels, separated by dots (.).

              Valid characters for labels are limited to letters a - z, "+
              "A - Z, digits 0 - 9, and character - (dash). Character case "+
              "is preserved. Length of labels cannot exceed 255 characters.

              NOTE: First and last character in domain name cannot be the "+
              "character - (dash).

              For more information, see RFC 952, 1101 and 1123.";
            type string {
                length "1..255";
                pattern
                '(((([a-zA-Z0-9]([a-zA-Z0-9\-]){0,255})?[a-zA-Z0-9]\.)*' +
                '([a-zA-Z0-9]([a-zA-Z0-9\-]){0,255})?[a-zA-Z0-9]\.?)|\.)' {
                    description
                      "Fully qualified domain name of AMF.

                      Consists of one or more labels, separated by dots (.).

                      Valid characters for labels are limited to letters "+
                      "a - z, A - Z, digits 0 - 9, and character - "+
                      "(dash). Character case is preserved. "+
                      "Length of labels cannot exceed 255 characters.

                      NOTE: First and last character in domain name cannot "+
                      "be the character - (dash).

                      Example of valid value is ericsson.com";
                    error-message
                      "Incorrect format.";
                }
            }
            yexte:takes-effect
                "Next MO unlock";
            yexte:precondition
                "Value can only be changed if administrativeState is LOCKED.";
            tailf:info 'Precondition: Value can only be changed if administrativeState is LOCKED, Takes effect: Next MO unlock, Fully qualified domain name of AMF. Consists of one or more labels, separated by dots (.). Valid characters for labels are limited to letters a - z, A - Z, digits 0 - 9, and character - (dash). Character case is preserved. Length of labels cannot exceed 255 characters. NOTE: First and last character in domain name cannot be the character - (dash). For more information, see RFC 952, 1101 and 1123.';
        }

        leaf ipv4Address1 {
            description
                "Primary IPv4 address of AMF for NG-C interface.

                The input format is four fields of digits, separated by "+
                "dots. Each field consists of three digits. The value of "+
                "each field must be in the range 0-255.";
            type inet:ipv4-address-no-zone;
            default "0.0.0.0";
            yexte:takes-effect
                "Next MO unlock";
            yexte:precondition
                "Value can only be changed if administrativeState is LOCKED.";
            tailf:info 'Precondition: Value can only be changed if administrativeState is LOCKED, Takes effect: Next MO unlock, Primary IPv4 address of AMF for NG-C interface. The input format is four fields of digits, separated by dots. Each field consists of three digits. The value of each field must be in the range 0-255.';
        }

        leaf ipv4Address2 {
            description
              "Secondary IPv4 address of AMF for NG-C interface.

              The input format is four fields of digits, separated by dots. "+
              "Each field consists of three digits. The value of each "+
              "field must be in the range 0-255.";
            type inet:ipv4-address-no-zone;
            default "0.0.0.0";
            yexte:takes-effect
              "Next MO unlock";
            yexte:precondition
              "Value can only be changed if administrativeState is LOCKED.";
            tailf:info 'Precondition: Value can only be changed if administrativeState is LOCKED, Takes effect: Next MO unlock, Secondary IPv4 address of AMF for NG-C interface. The input format is four fields of digits, separated by dots. Each field consists of three digits. The value of each field must be in the range 0-255.';
        }

        leaf ipv6Address1 {
            description
              "Primary IPv6 address of AMF for NG-C interface.

              The input format is eight fields, separated by colons.
              Each field consists of four hexadecimal characters. The value "+
              "of each field must be in the range 0-FFFF.

              Leading zeroes can be omitted in a field, and multiple groups "+
              "of 16 bits of zeroes can be compressed to ::. The :: can be "+
              "used only once in an address.";
            type inet:ipv6-address-no-zone;
            default "::";
            yexte:takes-effect
              "Next MO unlock";
            yexte:precondition
              "Value can only be changed if administrativeState is LOCKED.";
            tailf:info 'Precondition: Value can only be changed if administrativeState is LOCKED, Takes effect: Next MO unlock, Primary IPv6 address of AMF for NG-C interface. The input format is eight fields, separated by colons. Each field consists of four hexadecimal characters. The value of each field must be in the range 0-FFFF. Leading zeroes can be omitted in a field, and multiple groups of 16 bits of zeroes can be compressed to ::. The :: can be used only once in an address.';
        }

        leaf ipv6Address2 {
            description
              "Secondary IPv6 address of AMF for NG-C interface.

              The input format is eight fields, separated by colons.
              Each field consists of four hexadecimal characters. The value "+
              "of each field must be in the range 0-FFFF.

              Leading zeroes can be omitted in a field, and multiple groups "+
              "of 16 bits of zeroes can be compressed to ::. The :: "+
              "can be used only once in an address.";
            type inet:ipv6-address-no-zone;
            default "::";
            yexte:takes-effect
              "Next MO unlock";
            yexte:precondition
              "Value can only be changed if administrativeState is LOCKED.";
            tailf:info 'Precondition: Value can only be changed if administrativeState is LOCKED, Takes effect: Next MO unlock, Secondary IPv6 address of AMF for NG-C interface. The input format is eight fields, separated by colons. Each field consists of four hexadecimal characters. The value of each field must be in the range 0-FFFF. Leading zeroes can be omitted in a field, and multiple groups of 16 bits of zeroes can be compressed to ::. The :: can be used only once in an address.';
        }

        leaf operationalState {
            description
              "The operational state.";
            config false;
            type types3gpp:OperationalState;
            reference
              "3GPP TS 28.625 and ITU-T Rec. X.731";
        }

        list operatorPLMNId {
            key "mcc mnc";
            max-elements 1;
            description
              "PLMN identifier used as a part of Global RAN Node ID.

              If empty, pLMNId on GNBCUCPFunction MO will be used.";
            uses types3gpp:PLMNId;
            yexte:takes-effect
              "Next MO unlock";
            yexte:precondition
              "Value can only be changed if TermPointToAmf has "+
              "administrativeState LOCKED.";
            tailf:info 'Precondition: Value can only be changed if TermPointToAmf has administrativeState LOCKED, Takes effect: Next MO unlock, PLMN identifier used as a part of Global RAN Node ID. If empty, pLMNId on GNBCUCPFunction MO will be used.';
        }

        list pLMNIdList {
            key "mcc mnc";
            max-elements 12;
            description
              "PLMNs that can be served by this AMF.";
            config false;
            uses types3gpp:PLMNId;
            reference
              "3GPP TS 38.413";
        }

        leaf pwsRestartHandling {
            description
              "Whether the NG-C link is used to send restart and failure "+
              "messages related to PWS.

              Note: If set to ENABLED but no connection exists between AMF "+
              "and CBC function, the PWS restart and failure messages are "+
              "lost.";
            type PWSRestartHandling;
            default DISABLED;
            yexte:disturbances
              "Changing this attribute can prevent sending PWS restart and "+
              "failure messages to an AMF.";
            yexte:takes-effect
              "Next PWS restart or failure message to be transmitted on the "+
              "NG-C interface. Does not affect ongoing PWS broadcast.";
            tailf:info 'Takes effect: Next PWS restart or failure message to be transmitted on the NG-C interface. Does not affect ongoing PWS broadcast, Traffic Disturbance: Changing this attribute can prevent sending PWS restart and failure messages to an AMF, Whether the NG-C link is used to send restart and failure messages related to PWS. Note: If set to ENABLED but no connection exists between AMF and CBC function, the PWS restart and failure messages are lost.';
        }

        leaf relativeCapacity {
            description
              "Relative processing capacity of an AMF to other AMFs in pool.

              Capacity is used to balance the load between AMFs in a pool.";
            config false;
            type int32 {
                range "0..255";
            }
            reference
              "3GPP TS 38.413";
        }

        list servedGuamiList {
            key "amfPointer amfRegionId amfSetId mcc mnc";
            max-elements 256;
            description
              "List of Globally Unique AMF IDs (GUAMIs) served by this AMF.";
            config false;
            uses types3gpp:AmfIdentifier;
            uses types3gpp:PLMNId;
            reference
              "3GPP TS 38.413";
        }

        list sNSSAIList {
            key "sd sst";
            max-elements 1024;
            description
              "List of supported network slices.";
            config false;
            uses commontypes:SliceSelectionAssistInfo;
            reference
              "3GPP TS 38.413";
            yexte:takes-effect
              "Next cell unlock";
            tailf:info 'Takes effect: Next cell unlock, List of supported network slices.';
        }

        leaf usedIpAddress {
            description
              "The destination address used for initialization of the "+
              "underlying SCTP association.

              Contains the address of the latest successful NGAP Setup.

              The IP address can be an IPv4 or an IPv6 address.";
            config false;
            type inet:ip-address-no-zone;
        }
    }

    augment "/me3gpp:ManagedElement/gnbcucp3gpp:GNBCUCPFunction" {
        list TermPointToAmf {
            description "Represents an NG link AMF termination point.";
            key id;
            max-elements 64;
            uses top3gpp:Top_Grp;
            container attributes {
                uses TermPointToAmfGrp;
            }
        }
    }
}
