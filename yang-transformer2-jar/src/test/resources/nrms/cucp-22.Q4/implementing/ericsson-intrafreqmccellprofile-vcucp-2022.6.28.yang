// Generated by eyang-preprocessor (1.22.0-48 2022-01-20 09:10:06 CET) on Jun 30, 2022, 8:31:38 AM
module ericsson-intrafreqmccellprofile-vcucp {
    yang-version 1.1;
    namespace "urn:rdns:com:ericsson:oammodel:ericsson-intrafreqmccellprofile-vcucp";
    prefix "intrafreqmccellprofile";

    import tailf-common {
        prefix tailf;
    }
    import _3gpp-common-managed-element {
        prefix "me3gpp";
    }
    import _3gpp-nr-nrm-gnbcucpfunction {
        prefix "gnbcucp3gpp";
    }
    import _3gpp-common-top {
        prefix "top3gpp";
    }
    import ericsson-intrafreqmc-vcucp {
        prefix "intrafreqmc";
    }
    import ericsson-yang-extensions {
        prefix "yexte";
    }
    import ericsson-common-types-vcucp {
        prefix "commontypes";
    }

    organization
      "Ericsson AB";
    contact
      "Ericsson first line support via email";
    description
      "The module defines the IntraFreqMCCellProfile data model for the Ericsson vCU-CP.

       Copyright (c) 2021-2022 Ericsson AB. All rights reserved.";

    revision 2022-06-28 {
        description
            "Removed module-status preliminary.
             Removed preliminary status from ueConfGroupType.";
        yexte:version 1;
        yexte:release 1;
        yexte:correction 0;
        reference
            "RFC 7950: The YANG 1.1 Data Modeling Language";
    }

    revision 2022-03-14 {
        description
            "Updated description for the IntraFreqMCCellProfile MO list.
             Marked betterSpCellTriggerQuantity, endcActionEvalFail, rsrpBetterSpCell and rsrqBetterSpCell as obsolete.
             Added the attributes ueConfGroupType and userLabel.";
        yexte:version 1;
        yexte:release 0;
        yexte:correction 0;
        reference
            "RFC 7950: The YANG 1.1 Data Modeling Language";
    }

    revision 2021-11-05 {
        description
            "Updated description and precondition for the IntraFreqMCCellProfile MO list.";
        yexte:version 0;
        yexte:release 1;
        yexte:correction 1;
        reference
            "RFC 7950: The YANG 1.1 Data Modeling Language";
    }

    revision 2021-04-12 {
        description
          "Initial version of the IntraFreqMCCellProfile model.";
        yexte:version 0;
        yexte:release 1;
        yexte:correction 0;
        reference
          "RFC 7950: The YANG 1.1 Data Modeling Language";
    }

    grouping ReportConfigA3RsrpObsolete {
        description
            "Report configuration settings for A3 measurement events when trigger quantity is RSRP.";

        leaf hysteresis {
            description
                "Hysteresis value for eventA3.";
            type int32{
                range "0..150";
            }
            units "0.1 dB";
            reference
                "3GPP TS 38.331";
            status obsolete {
                yexte:status-information
                    "Since 22.Q1. Replaced by "+
                    "IntraFreqMCCellProfileUeCfg::rsrpBetterSpCell::hysteresis. Planned to be "+
                    "removed.";
            }
            tailf:info 'Status Info: Since 22.Q1. Replaced by IntraFreqMCCellProfileUeCfg::rsrpBetterSpCell::hysteresis. Planned to be removed, Obsolete, Hysteresis value for eventA3.';
        }

        leaf offset {
            description
                "Offset value for eventA3.";
            type int32{
                range "-150..150";
            }
            units "0.1 dB";
            reference
                "3GPP TS 38.331";
            status obsolete {
                yexte:status-information
                    "Since 22.Q1. Replaced by "+
                    "IntraFreqMCCellProfileUeCfg::rsrpBetterSpCell::offset. Planned to be "+
                    "removed.";
            }
            tailf:info 'Status Info: Since 22.Q1. Replaced by IntraFreqMCCellProfileUeCfg::rsrpBetterSpCell::offset. Planned to be removed, Obsolete, Offset value for eventA3.';
        }

        leaf timeToTrigger {
            description
                "Time-to-trigger value for eventA3.";
            type int32 {
                range "0 | 40 | 64 | 80 | 100 | 128 | 160 | 256 | 320 | 480 | 512 | 640 | 1024 | 1280 | 2560 | 5120";
            }
            units ms;
            reference
                "3GPP TS 38.331";
            status obsolete {
                yexte:status-information
                    "Since 22.Q1. Replaced by "+
                    "IntraFreqMCCellProfileUeCfg::rsrpBetterSpCell::timeToTrigger. Planned to be "+
                    "removed.";
            }
            tailf:info 'Status Info: Since 22.Q1. Replaced by IntraFreqMCCellProfileUeCfg::rsrpBetterSpCell::timeToTrigger. Planned to be removed, Obsolete, Time-to-trigger value for eventA3.';
        }
    }

    grouping ReportConfigA3RsrqObsolete {
        description
            "Report configuration settings for A3 measurement events when trigger quantity is RSRQ.";

        leaf hysteresis {
            description
                "Hysteresis value for eventA3.";
            type int32 {
                range "0..150";
            }
            units "0.1 dB";
            reference
                "3GPP TS 38.331";
            status obsolete {
                yexte:status-information
                    "Since 22.Q1. Replaced by "+
                    "IntraFreqMCCellProfileUeCfg::rsrqBetterSpCell::hysteresis. Planned to be "+
                    "removed.";
            }
            tailf:info 'Status Info: Since 22.Q1. Replaced by IntraFreqMCCellProfileUeCfg::rsrqBetterSpCell::hysteresis. Planned to be removed, Obsolete, Hysteresis value for eventA3.';
        }

        leaf offset {
            description
                "Offset value for eventA3.";
            type int32{
                range "-150..150";
            }
            units "0.1 dB";
            reference
                "3GPP TS 38.331";
            status obsolete {
                yexte:status-information
                    "Since 22.Q1. Replaced by "+
                    "IntraFreqMCCellProfileUeCfg::rsrqBetterSpCell::offset. Planned to be "+
                    "removed.";
            }
            tailf:info 'Status Info: Since 22.Q1. Replaced by IntraFreqMCCellProfileUeCfg::rsrqBetterSpCell::offset. Planned to be removed, Obsolete, Offset value for eventA3.';
        }

        leaf timeToTrigger {
            description
                "Time-to-trigger value for eventA3.";
            type int32 {
                range "0 | 40 | 64 | 80 | 100 | 128 | 160 | 256 | 320 | 480 | 512 | 640 | 1024 | 1280 | 2560 | 5120";
            }
            units ms;
            reference
                "3GPP TS 38.331";
            status obsolete {
                yexte:status-information
                    "Since 22.Q1. Replaced by "+
                    "IntraFreqMCCellProfileUeCfg::rsrqBetterSpCell::timeToTrigger. Planned to be "+
                    "removed.";
            }
            tailf:info 'Status Info: Since 22.Q1. Replaced by IntraFreqMCCellProfileUeCfg::rsrqBetterSpCell::timeToTrigger. Planned to be removed, Obsolete, Time-to-trigger value for eventA3.';
        }
    }

    grouping IntraFreqMCCellProfileGrp {
        description
          "Represents the IntraFreqMCCellProfile IOC.";

        leaf betterSpCellTriggerQuantity {
            description
              "Measurement trigger quantity used when searching for better Special Cell.

               Special Cell is either PCell or PSCell.";
            type commontypes:TriggerQuantity;
            status obsolete {
                yexte:status-information
                "Since 22.Q1. Replaced by "+
                "IntraFreqMCCellProfileUeCfg::betterSpCellTriggerQuantity. Planned "+
                "to be removed.";
            }
            reference
              "3GPP TS 38.331";
            yexte:takes-effect
              "Next usage";
            tailf:info 'Takes effect: Next usage, Status Info: Since 22.Q1. Replaced by IntraFreqMCCellProfileUeCfg::betterSpCellTriggerQuantity. Planned to be removed, Obsolete, Measurement trigger quantity used when searching for better Special Cell. Special Cell is either PCell or PSCell.';
        }

        leaf endcActionEvalFail {
            description
              "Action taken when intra-frequency handover evaluation or Secondary Node change procedure fails.

               Applies to UE which use cell as PSCell in EN-DC configuration.";
            type commontypes:EndcMobilityAction;
            status obsolete {
                yexte:status-information
                "Since 22.Q1. Replaced by "+
                "IntraFreqMCCellProfileUeCfg::endcActionEvalFail. Planned to be "+
                "removed.";
            }
            yexte:takes-effect
              "Next usage";
            tailf:info 'Takes effect: Next usage, Status Info: Since 22.Q1. Replaced by IntraFreqMCCellProfileUeCfg::endcActionEvalFail. Planned to be removed, Obsolete, Action taken when intra-frequency handover evaluation or Secondary Node change procedure fails. Applies to UE which use cell as PSCell in EN-DC configuration.';
        }

        container rsrpBetterSCell {
            description
              "Configures UE measurement to detect neighboring SCells with better coverage.

               The cell referring to this profile is used as a PCell or PSCell for UE.
               Measurement trigger quantity for SCell neighbor with better coverage is always RSRP.";
            uses commontypes:ReportConfigA6Rsrp;
            reference
              "3GPP TS 38.331";
            yexte:takes-effect
              "New connection";
            tailf:info 'Takes effect: New connection, Configures UE measurement to detect neighboring SCells with better coverage. The cell referring to this profile is used as a PCell or PSCell for UE. Measurement trigger quantity for SCell neighbor with better coverage is always RSRP.';
        }

        container rsrpBetterSpCell {
            description
              "Downlink RSRP measurement report criteria when searching for better Special Cell.

               Special Cell is either PCell or PSCell.
               Used only when triggerQuantity is set to RSRP.";
            uses ReportConfigA3RsrpObsolete {
                status obsolete;
            }
            status obsolete {
                yexte:status-information
                "Since 22.Q1. Replaced by "+
                "IntraFreqMCCellProfileUeCfg::rsrpBetterSpCell. Planned to be "+
                "removed.";
            }
            reference
              "3GPP TS 38.331";
            yexte:takes-effect
              "Next usage";
            tailf:info 'Takes effect: Next usage, Status Info: Since 22.Q1. Replaced by IntraFreqMCCellProfileUeCfg::rsrpBetterSpCell. Planned to be removed, Obsolete, Downlink RSRP measurement report criteria when searching for better Special Cell. Special Cell is either PCell or PSCell. Used only when triggerQuantity is set to RSRP.';
        }

        container rsrpSCellCoverage {
            description
              "Configures UE measurements to detect poor or good coverage in SCell.

               The cell referring to this profile is used as a PCell or PSCell for UE.
               Used only when triggerQuantity is set to RSRP.";
            uses commontypes:ReportConfigA1A2Rsrp;
            reference
              "3GPP TS 38.331";
            yexte:takes-effect
              "New connection";
            tailf:info 'Takes effect: New connection, Configures UE measurements to detect poor or good coverage in SCell. The cell referring to this profile is used as a PCell or PSCell for UE. Used only when triggerQuantity is set to RSRP.';
        }

        container rsrqBetterSpCell {
            description
              "Downlink RSRQ measurement report criteria when searching for better Special Cell.

               Special Cell is either PCell or PSCell.
               Used only when triggerQuantity is set to RSRQ.";
            uses ReportConfigA3RsrqObsolete {
                status obsolete;
            }
            status obsolete {
                yexte:status-information
                "Since 22.Q1. Replaced by "+
                "IntraFreqMCCellProfileUeCfg::rsrqBetterSpCell. Planned to be "+
                "removed.";
            }
            reference
              "3GPP TS 38.331";
            yexte:takes-effect
              "Next usage";
            tailf:info 'Takes effect: Next usage, Status Info: Since 22.Q1. Replaced by IntraFreqMCCellProfileUeCfg::rsrqBetterSpCell. Planned to be removed, Obsolete, Downlink RSRQ measurement report criteria when searching for better Special Cell. Special Cell is either PCell or PSCell. Used only when triggerQuantity is set to RSRQ.';
        }

        container rsrqSCellCoverage {
            description
              "Configures UE measurements to detect poor or good coverage in SCell.

               The cell referring to this profile is used as a PCell or PSCell for UE.
               Used only when triggerQuantity is set to RSRQ.";
            uses commontypes:ReportConfigA1A2Rsrq;
            reference
              "3GPP TS 38.331";
            yexte:takes-effect
              "New connection";
            tailf:info 'Takes effect: New connection, Configures UE measurements to detect poor or good coverage in SCell. The cell referring to this profile is used as a PCell or PSCell for UE. Used only when triggerQuantity is set to RSRQ.';
        }

        leaf sCellCoverageTriggerQuantity {
            description
              "Quantity that triggers SCell poor or good coverage measurements.";
            type commontypes:TriggerQuantity;
            default RSRP;
            reference
              "Specification: 3GPP TS 38.331";
            yexte:takes-effect
              "New connection";
            tailf:info 'Takes effect: New connection, Quantity that triggers SCell poor or good coverage measurements.';
        }

        leaf ueConfGroupType {
            description
              "UE configuration group Type.

               Defines which UE configuration group type that is applied in "+
              "contained MO class IntraFreqMCCellProfileUeCfg.";
            type commontypes:UeConfGroupType;
            default UE_MOBILITY_GROUP;
            yexte:disturbances
              "Changing this attribute can cause loss of traffic.";
            yexte:takes-effect
              "Next usage.";
            tailf:info 'Takes effect: Next usage, Traffic Disturbance: Changing this attribute can cause loss of traffic, UE configuration group Type. Defines which UE configuration group type that is applied in contained MO class IntraFreqMCCellProfileUeCfg.';
        }
    }

    augment "/me3gpp:ManagedElement/gnbcucp3gpp:GNBCUCPFunction/intrafreqmc:IntraFreqMC" {
        list IntraFreqMCCellProfile {
            description
                "Intra-frequency mobility control, cell configuration profile.

                Applies to UEs that use cell as SpCell. Attributes are used on "+
                "cell level.

                MO instance IntraFreqMCCellProfile=Default is created "+
                "automatically when parent MO is created, unless created manually "+
                "in the same transaction as parent MO.

                If NRCellCU::intraFreqMCCellProfileRef is non-empty, attributes "+
                "from referred MO instance are used.
                If NRCellCU::intraFreqMCCellProfileRef is empty, attribute "+
                "default values according to IntraFreqMCCellProfile and "+
                "IntraFreqMCCellProfileUeCfg MO class definitions are used.";
            key id;
            uses top3gpp:Top_Grp;
            container attributes {
                uses IntraFreqMCCellProfileGrp;
                uses commontypes:UserLabelGrp;
            }
            yexte:precondition
                "IntraFreqMCCellProfile=Default MO instance must not be deleted unless "+
                "parent MO is deleted. Other instances can be created and deleted "+
                "manually.";
            tailf:info 'Precondition: IntraFreqMCCellProfile=Default MO instance must not be deleted unless parent MO is deleted. Other instances can be created and deleted manually, Intra-frequency mobility control, cell configuration profile. Applies to UEs that use cell as SpCell. Attributes are used on cell level. MO instance IntraFreqMCCellProfile=Default is created automatically when parent MO is created, unless created manually in the same transaction as parent MO. If NRCellCU::intraFreqMCCellProfileRef is non-empty, attributes from referred MO instance are used. If NRCellCU::intraFreqMCCellProfileRef is empty, attribute default values according to IntraFreqMCCellProfile and IntraFreqMCCellProfileUeCfg MO class definitions are used.';
        }
    }
}
