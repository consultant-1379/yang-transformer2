// Generated by eyang-preprocessor (1.22.0-48 2022-01-20 09:10:06 CET) on Jun 30, 2022, 8:31:38 AM
module ericsson-inactivityprofile-vcucp {
    yang-version 1.1;
    namespace urn:rdns:com:ericsson:oammodel:ericsson-inactivityprofile-vcucp;
    prefix inactivityprofilevcucp;

    import tailf-common {
        prefix tailf;
    }
    import _3gpp-common-managed-element {
        prefix "me3gpp";
    }
    import _3gpp-nr-nrm-gnbcucpfunction {
        prefix "gnbcucp3gpp";
    }
    import _3gpp-common-top {
        prefix "top3gpp";
    }
    import ericsson-uecc-vcucp {
        prefix "ueccvcucp";
    }
    import ericsson-yang-extensions {
        prefix "yexte";
    }

    organization
      "Ericsson AB";
    contact
      "Ericsson first line support via email";
    description
      "The module defines the InactivityProfile data model for the Ericsson vCU-CP.

       Copyright (c) 2021-2022 Ericsson AB. All rights reserved.";

    revision 2022-06-28 {
        description
            "Removed module-status preliminary.";
        yexte:version 0;
        yexte:release 2;
        yexte:correction 0;
        reference
            "RFC 7950: The YANG 1.1 Data Modeling Language";
    }

    revision 2022-03-14 {
        description
          "Correct description and precondition for InactivityProfile.";
        yexte:version 0;
        yexte:release 1;
        yexte:correction 1;
        reference
          "RFC 7950: The YANG 1.1 Data Modeling Language";
    }

    revision 2021-10-24 {
        description
          "Initial version of the InactivityProfile model.";
        yexte:version 0;
        yexte:release 1;
        yexte:correction 0;
        reference
          "RFC 7950: The YANG 1.1 Data Modeling Language";
    }

    augment "/me3gpp:ManagedElement/gnbcucp3gpp:GNBCUCPFunction/ueccvcucp:UeCC" {
        list InactivityProfile {
            description
                "Inactivity profile used for current UE.

                MO instance InactivityProfile=Default is created automatically "+
                "when parent MO is created, unless created manually in the same "+
                "transaction as parent MO.";
            key id;
            max-elements 1;
            uses top3gpp:Top_Grp;
            yexte:precondition
                "InactivityProfile=Default instance can only be created in the same "+
                "transaction as parent MO is created and must not be deleted unless "+
                "parent MO is deleted.";
            must "count(../inactivityprofilevcucp:InactivityProfile) &lt; 1 or
              count(../inactivityprofilevcucp:InactivityProfile/id[. = 'Default']) = 1" {
                error-message
                  "One InactivityProfile must be configured as the Default Configuration Instance under UeCC.";
            }
            tailf:info 'Precondition: InactivityProfile=Default instance can only be created in the same transaction as parent MO is created and must not be deleted unless parent MO is deleted, Inactivity profile used for current UE. MO instance InactivityProfile=Default is created automatically when parent MO is created, unless created manually in the same transaction as parent MO.';
        }
    }
}
