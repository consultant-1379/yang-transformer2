// Generated by eyang-preprocessor (1.22.0-48 2022-01-20 09:10:06 CET) on Sep 4, 2022, 12:23:52 PM
module ericsson-gnbcucpfunction-ext-vcucp {
    yang-version 1.1;
    namespace urn:rdns:com:ericsson:oammodel:ericsson-gnbcucpfunction-ext-vcucp;
    prefix gnbcucp3gppext;

    import tailf-common {
        prefix tailf;
    }
    import _3gpp-common-yang-types {
        prefix types3gpp;
    }
    import _3gpp-common-managed-element {
        prefix me3gpp;
    }
    import _3gpp-nr-nrm-gnbcucpfunction {
        prefix gnbcucp3gpp;
    }
    import ericsson-endpoint-resource-vcucp {
        prefix epresource;
    }
    import ericsson-transport-types-vcu {
        prefix transtypes;
    }
    import ericsson-yang-extensions {
        prefix yexte;
    }
    import ericsson-notifications {
        prefix notife;
    }

    organization
      "Ericsson AB";
    contact
      "Ericsson first line support via email";
    description
      "The module defines the GNBCUCPFunction data model extensions for the Ericsson vCU-CP.

       Copyright (c) 2021-2022 Ericsson AB. All rights reserved.";

    revision 2022-08-23 {
        description
            "Mark redundancyState deprecated.";
        yexte:version 3;
        yexte:release 3;
        yexte:correction 0;
        reference
            "RFC 7950: The YANG 1.1 Data Modeling Language";
    }

    revision 2022-06-28 {
        description
            "Removed module-status preliminary.
             Removed preliminary status from maxCommonProcTime, rrcReestSupportType,
              tXnDcOverall and tXnDcPrep.";
        yexte:version 3;
        yexte:release 2;
        yexte:correction 0;
        reference
            "RFC 7950: The YANG 1.1 Data Modeling Language";
    }

    revision 2022-03-14 {
        description
            "Updated description of gNBCUName and xnIpAddrViaNgActive.
            Added type RreSupportType and attribute rrcReestSupportType.
            Added attribute tXnDcOverall and tXnDcPrep.";
        yexte:version 3;
        yexte:release 1;
        yexte:correction 0;
        reference
            "RFC 7950: The YANG 1.1 Data Modeling Language";
    }

    revision 2021-11-05 {
        description
            "Remove mandatory and add default for gNBIdLength.
             Mark tInactivityTimer obsolete.";
        yexte:version 3;
        yexte:release 0;
        yexte:correction 0;
        reference
            "RFC 7950: The YANG 1.1 Data Modeling Language";
    }

    revision 2021-10-19 {
        description
            "Make transportServiceId mandatory and unique.";
        yexte:version 2;
        yexte:release 0;
        yexte:correction 0;
        reference
            "RFC 7950: The YANG 1.1 Data Modeling Language";
    }

    revision 2021-10-06 {
        description
            "Update description of gNBCUName";
        yexte:version 1;
        yexte:release 2;
        yexte:correction 1;
        reference
            "RFC 7950: The YANG 1.1 Data Modeling Language";
    }

    revision 2021-08-23 {
        description
            "Change GNBCUCPFunction cardinality from 1 to 4.";
        yexte:version 1;
        yexte:release 2;
        yexte:correction 0;
        reference
            "RFC 7950: The YANG 1.1 Data Modeling Language";
    }

    revision 2021-06-15 {
        description
            "Add redundancyEnabled and redundancyState.";
        yexte:version 1;
        yexte:release 1;
        yexte:correction 0;
        reference
            "RFC 7950: The YANG 1.1 Data Modeling Language";
    }

    revision 2021-06-08 {
        description
            "Changed error message for a must statement.";
        yexte:version 1;
        yexte:release 0;
        yexte:correction 2;
        reference
            "RFC 7950: The YANG 1.1 Data Modeling Language";
    }

    revision 2021-06-03 {
        description
            "Disable notifications for noOfSupportedNRCellCU.";
        yexte:version 1;
        yexte:release 0;
        yexte:correction 1;
        reference
            "RFC 7950: The YANG 1.1 Data Modeling Language";
    }

    revision 2021-03-30 {
        description
            "Add Ericsson descriptions and tags to attributes.";
        yexte:version 1;
        yexte:release 0;
        yexte:correction 0;
        reference
            "RFC 7950: The YANG 1.1 Data Modeling Language";
    }

    revision 2021-03-24 {
        description
            "Correct must statement for MO reference.";
        yexte:version 0;
        yexte:release 3;
        yexte:correction 1;
        reference
            "RFC 7950: The YANG 1.1 Data Modeling Language";
    }

    revision 2021-03-18 {
        description
          "Parity with ECIM R1A79.";
        yexte:version 0;
        yexte:release 3;
        yexte:correction 0;
        reference
          "RFC 7950: The YANG 1.1 Data Modeling Language";
    }

    revision 2021-01-14 {
        description
          "Add attribute transportServiceId";
        yexte:version 0;
        yexte:release 2;
        yexte:correction 0;
        reference
          "RFC 7950: The YANG 1.1 Data Modeling Language";
    }

    revision 2021-01-11 {
        description
          "Add attributes on _3gpp-nr-nrm-gnbcucpfunction.";
        yexte:version 0;
        yexte:release 1;
        yexte:correction 0;
        reference
          "RFC 7950: The YANG 1.1 Data Modeling Language";
    }

    typedef redundancy-state {
        type enumeration {
            enum passive {
                value 1;
                description "The entity is in passive state standing by for later
            service.";
            }
            enum active {
                value 2;
                description "The entity is in active state providing services.";
            }
        }
        description "Redundancy state of an entity.";
    }

    typedef RreSupportType {
        description
            "Support type of RRC Re-establishment.";

        type enumeration {
            enum NO_RRE_SUPPORT {
                value 0;
                description
                    "No RRE support.";
            }

            enum INTRA_GNB_RRE {
                value 1;
                description
                    "Support is only for intra-gNodeB RRE.";
            }

            enum INTRA_INTER_GNB_RRE {
                value 2;
                description
                    "Support is for intra- and inter-gNodeB RREs.";
            }
        }
    }

    deviation /me3gpp:ManagedElement/gnbcucp3gpp:GNBCUCPFunction {
        deviate add {
            max-elements 4;
            yexte:updated-description
                "Represents the logical node gNodeB-CU-CP.";
        }
    }

    deviation /me3gpp:ManagedElement/gnbcucp3gpp:GNBCUCPFunction/gnbcucp3gpp:attributes {
        deviate add {
            must '(current()/gnbcucp3gpp:gNBIdLength = 22 and current()/gnbcucp3gpp:gNBId <= 4194303) or (current()/gnbcucp3gpp:gNBIdLength = 23 and current()/gnbcucp3gpp:gNBId <= 8388607) or (current()/gnbcucp3gpp:gNBIdLength = 24 and current()/gnbcucp3gpp:gNBId <= 16777215) or (current()/gnbcucp3gpp:gNBIdLength = 25 and current()/gnbcucp3gpp:gNBId <= 33554431) or (current()/gnbcucp3gpp:gNBIdLength = 26 and current()/gnbcucp3gpp:gNBId <= 67108863) or (current()/gnbcucp3gpp:gNBIdLength = 27 and current()/gnbcucp3gpp:gNBId <= 134217727) or (current()/gnbcucp3gpp:gNBIdLength = 28 and current()/gnbcucp3gpp:gNBId <= 268435455) or (current()/gnbcucp3gpp:gNBIdLength = 29 and current()/gnbcucp3gpp:gNBId <= 536870911) or (current()/gnbcucp3gpp:gNBIdLength = 30 and current()/gnbcucp3gpp:gNBId <= 1073741823) or (current()/gnbcucp3gpp:gNBIdLength = 31 and current()/gnbcucp3gpp:gNBId <= 2147483647) or current()/gnbcucp3gpp:gNBIdLength = 32' {
                error-message
                  "The gNBId must be equal or less than 2^gNBIdLength - 1.";
            }
        }
    }

    deviation /me3gpp:ManagedElement/gnbcucp3gpp:GNBCUCPFunction/gnbcucp3gpp:attributes/gnbcucp3gpp:gNBCUName {
        deviate add {
            yexte:updated-description
                "Name of the gNodeB-CU.

                Allowed characters for the value, are as follows:
                - a-z
                - A-Z
                - 0-9
                - Space
                - Apostrophe (')
                - Left and right parenthesis ((,))
                - Plus and minus sign (+,-)
                - Comma (,)
                - Full stop (.)
                - Forward slash (/)
                - Colon (:)
                - Equal sign (=)
                - Question mark (?)
                Character case is preserved. Length of name cannot exceed 150 "+
                "characters.

                For more information, see PrintableString of ITU-T Rec X.680.
                If the attribute contains invalid characters, each invalid one is "+
                "replaced by a space before the string is sent to gNodeB-DU.
                If empty, gNBCU-Name is not sent to gNodeB-DU.";
            yexte:takes-effect
                "New connection";
        }
    }

    deviation /me3gpp:ManagedElement/gnbcucp3gpp:GNBCUCPFunction/gnbcucp3gpp:attributes/gnbcucp3gpp:gNBId {
        deviate add {
            yexte:updated-description
                "Identity of gNodeB within a PLMN.

                Part of the NR Cell Global Identity. Identifies node over NG-C and X2.";
            yexte:dependencies
                "gNBId =< (2^gNBIdLength)-1";
            yexte:takes-effect
                "Node restart";
        }
    }

    deviation /me3gpp:ManagedElement/gnbcucp3gpp:GNBCUCPFunction/gnbcucp3gpp:attributes/gnbcucp3gpp:gNBIdLength {
        deviate replace {
            mandatory false;
        }
        deviate add {
            default 22;
            yexte:updated-description
                "Length of gNBId bit string representation.

                If gNBId bit representation exceeds 22 bits, gNBIdLength value must "+
                "be at least minimum bit length that can accommodate gNBId.

                gNBId =< (2^gNBIdLength)-1";
            yexte:takes-effect
                "Node restart";
        }
    }

    deviation /me3gpp:ManagedElement/gnbcucp3gpp:GNBCUCPFunction/gnbcucp3gpp:attributes/gnbcucp3gpp:pLMNId {
        deviate add {
            yexte:updated-description
                "PLMN identifier to be used as part of global RAN node identity.

                Value (MCC=001, MNC=01) indicates that PLMN is not initiated and "+
                "cannot be used as a valid PLMN Identity.";
            yexte:takes-effect
                "Next cell unlock";
        }
    }

    grouping GNBCUCPFunctionVCUCPGrp {
        description
          "Ericsson extensions to the 3gpp GNBCUCPFunction.";
        reference
          "Ericsson documentation";

        leaf endpointResourceRef {
            description
              "Reference to EndpointResource MO instance.";
            type types3gpp:DistinguishedName;
            yexte:takes-effect "Node restart";
            must "re-match(current(), 'ManagedElement=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,GNBCUCPFunction=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,EndpointResource=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?') and
                re-match(current(), concat('ManagedElement=', ../../../me3gpp:id, ',.*')) and
                re-match(current(), concat('.*GNBCUCPFunction=', ../../gnbcucp3gpp:id, ',.*')) and
                count(../../epresource:EndpointResource[re-match(current(), concat('.*EndpointResource=', epresource:id))]) > 0" {
                error-message
                  "endpointResourceRef must refer to an EndpointResource under the same GNBCUCPFunction.";
            }
            tailf:info 'Takes effect: Node restart, Reference to EndpointResource MO instance.';
        }

        leaf maxCommonProcTime {
            description
              "Maximum time until an expected response message to a common "
            + "procedure is considered lost.";
            type int32 {
                range "1..60";
            }
            default 30;
            units s;
            yexte:takes-effect
                "New connection";
            tailf:info 'Takes effect: New connection, Maximum time until an expected response message to a common procedure is considered lost.';
        }

        leaf maxNgRetryTime {
            description
              "Maximum time between consecutive NG setup attempts.

               Time between retry attempts is increasing for every retry. This value "
            + "sets un upperbound to it.";
            type int32 {
                range "1..3600";
            }
            default 30;
            units s;
            yexte:takes-effect
                "New connection";
            tailf:info 'Takes effect: New connection, Maximum time between consecutive NG setup attempts. Time between retry attempts is increasing for every retry. This value sets un upperbound to it.';
        }

        leaf nasInactivityTime {
            description
              "NAS inactivity time to pass before NGAP UE Context Release Request "
            + "procedure initiated.";
            type int32 {
                range "1..60";
            }
            default 5;
            units s;
            yexte:takes-effect
                "New connection";
            tailf:info 'Takes effect: New connection, NAS inactivity time to pass before NGAP UE Context Release Request procedure initiated.';
        }

        leaf ngcDedProcTime {
            description
              "Time until response to UE-dedicated NGAP message considered lost.";
            type int32 {
                range "1..60";
            }
            default 5;
            units s;
            yexte:takes-effect
                "New connection";
            tailf:info 'Takes effect: New connection, Time until response to UE-dedicated NGAP message considered lost.';
        }

        leaf noOfSupportedNRCellCU {
            description
              "Supported number of NRCellCU instances in current deployment.";
            config false;
            type int32;
            notife:notifiable-state-data false;
            tailf:meta-data notife:notifiable-state-data {
                tailf:meta-value false;
            }
        }

        leaf pwsBroadcastStarted {
            description
              "Whether PWS service is started.";
            config false;
            type boolean;
        }

        leaf redundancyEnabled {
            description
              "Whether redundancy feature is enabled.";
            config false;
            type boolean;
        }

        leaf redundancyState {
            description
              "Current state of redundancy.";
            config false;
            type redundancy-state;
            status deprecated {
                yexte:status-information
                    "Deprecated: Since 22.Q4. Replaced by CUCPRedundancy::redundancyState. Planned to be removed";
            }
            tailf:info 'Status Info: Deprecated: Since 22.Q4. Replaced by CUCPRedundancy::redundancyState. Planned to be removed, Deprecated, Current state of redundancy.';
        }

        leaf release {
            description
              "The product release of the ManagedFunction.";
            config false;
            type string;
        }

        leaf rrcReestSupportType {
            description
                "Support type for RRC reestablishment.";
            type RreSupportType;
            default NO_RRE_SUPPORT;
            yexte:takes-effect
                "New connection";
            tailf:info 'Takes effect: New connection, Support type for RRC reestablishment.';
        }

        leaf tDcOverall {
            description
              "Waiting time in EN-DC setup procedure.

               Waiting time for SN STATUS TRANSFER and SGNB RECONFIGURATION COMPLETE "
            + "during SgNB Addition on X2AP.";
            type int32 {
                range "1..20";
            }
            default 7;
            units s;
            reference
              "3GPP TS 36.423";
            yexte:takes-effect
                "New connection";
            tailf:info 'Takes effect: New connection, Waiting time in EN-DC setup procedure. Waiting time for SN STATUS TRANSFER and SGNB RECONFIGURATION COMPLETE during SgNB Addition on X2AP.';
        }

        leaf tInactivityTimer {
            description
              "Time NR SA UE can be inactive before released.";
            type int32 {
                range "1..7200";
            }
            units s;
            yexte:takes-effect
                "New connection";
            status obsolete {
                yexte:status-information
                    "Since 21.Q2. Replaced by InactivityProfileUeCfg::tInactivityTimer.";
            }
            tailf:info 'Status Info: Since 21.Q2. Replaced by InactivityProfileUeCfg::tInactivityTimer, Obsolete, Takes effect: New connection, Time NR SA UE can be inactive before released.';
        }

        leaf xnIpAddrViaNgActive {
            description
              "Whether automatic lookup of Xn IP addresses over NG is active.

               NGAP Configuration Transfer Procedures are used for retrieving Xn IP "+
               "addresses for neighbor gNodeB.";
            type boolean;
            default true;
            reference
              "3GPP TS 38.413";
        }

        leaf transportServiceId {
            description
              "Reference to a TransportService MO. Must match the value of the corresponding attribute in a TransportService MO instance";
            type transtypes:ReferenceId;
            mandatory true;
            must 'count(../../../gnbcucp3gpp:GNBCUCPFunction/gnbcucp3gpp:attributes/gnbcucp3gppext:transportServiceId[current() = .]) = 1' {
                error-message
                  "All GNBCUCPFunctions must have a unique transportServiceId.";
            }
        }

        leaf tXnDcOverall {
            description
                "Maximum time used in the Secondary Node for protection of XnAP "+
                "procedures.

                Used for either Secondary Node-initiated Secondary Node Modification "+
                "procedure or the protection of the NG-RAN actions necessary to "+
                "configure UE resources at Secondary Node Addition or Master "+
                "Node-initiated Secondary Node Modification procedures.";
            type int32 {
                range "1..20";
            }
            default 5;
            units s;
            reference
                "3GPP TS 38.423";
            yexte:takes-effect
                "New connection";
            tailf:info 'Takes effect: New connection, Maximum time used in the Secondary Node for protection of XnAP procedures. Used for either Secondary Node-initiated Secondary Node Modification procedure or the protection of the NG-RAN actions necessary to configure UE resources at Secondary Node Addition or Master Node-initiated Secondary Node Modification procedures.';
        }

        leaf tXnDcPrep {
            description
                "Maximum time used in the Master Node for protection of XnAP "+
                "procedures.

                Used for Secondary Node Addition Preparation or Master "+
                "Node-initiated Secondary Node Modification Preparation.";
            type int32 {
                range "1..20";
            }
            default 5;
            units s;
            reference
                "3GPP TS 38.423";
            yexte:takes-effect
                "New connection";
            tailf:info 'Takes effect: New connection, Maximum time used in the Master Node for protection of XnAP procedures. Used for Secondary Node Addition Preparation or Master Node-initiated Secondary Node Modification Preparation.';
        }
    }

    augment "/me3gpp:ManagedElement/gnbcucp3gpp:GNBCUCPFunction/gnbcucp3gpp:attributes" {
        when 'true()'; // temp fix to force augment statement to allow adding mandatory attributes.
        description
          "Adds Ericsson attributes to 3gpp GNBCUCPFunction.";
        uses GNBCUCPFunctionVCUCPGrp;
    }
}
