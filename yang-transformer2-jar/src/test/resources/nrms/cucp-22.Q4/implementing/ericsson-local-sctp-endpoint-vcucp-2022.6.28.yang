// Generated by eyang-preprocessor (1.22.0-48 2022-01-20 09:10:06 CET) on Jun 30, 2022, 8:31:38 AM
module ericsson-local-sctp-endpoint-vcucp {
    yang-version 1.1;
    namespace urn:rdns:com:ericsson:oammodel:ericsson-local-sctp-endpoint-vcucp;
    prefix localsctpepvcucp;

    import tailf-common {
        prefix tailf;
    }
    import _3gpp-common-managed-element {
        prefix me3gpp;
    }
    import _3gpp-nr-nrm-gnbcucpfunction {
        prefix gnbcucp3gpp;
    }
    import _3gpp-common-top {
        prefix top3gpp;
    }
    import ericsson-endpoint-resource-vcucp {
        prefix epresource;
    }
    import ericsson-local-sctp-endpoint-vcu {
        prefix localsctpep;
    }
    import ericsson-yang-extensions {
        prefix yexte;
    }

    organization
        "Ericsson AB";
    contact
        "Ericsson first line support via email";
    description
        "The module defines the LocalSctpEndpoint data model for the Ericsson vCU-CP.

    Copyright (c) 2021-2022 Ericsson AB. All rights reserved.";

    revision 2022-06-28 {
        description
            "Removed module-status preliminary.";
        yexte:version 0;
        yexte:release 3;
        yexte:correction 0;
        reference
            "RFC 7950: The YANG 1.1 Data Modeling Language";
    }

    revision 2022-06-16 {
        description
            "Add takes-effect information to sctpEndpointId.";
        yexte:version 0;
        yexte:release 2;
        yexte:correction 4;
        reference
            "RFC 7950: The YANG 1.1 Data Modeling Language";
    }

    revision 2021-11-05 {
        description
            "Add must rule for sctpEndpointId";
        yexte:version 0;
        yexte:release 2;
        yexte:correction 3;
        reference
            "RFC 7950: The YANG 1.1 Data Modeling Language";
    }

    revision 2021-05-24 {
        description
            "Add rule about sctpEndpointId uniqueness";
        yexte:version 0;
        yexte:release 2;
        yexte:correction 2;
        reference
            "RFC 7950: The YANG 1.1 Data Modeling Language";
    }

    revision 2021-04-06 {
        description
            "Updated Ericsson MO description.";
        yexte:version 0;
        yexte:release 2;
        yexte:correction 1;
        reference
            "RFC 7950: The YANG 1.1 Data Modeling Language";
    }

    revision 2021-01-13 {
        description
            "Changed prefix and import to ericsson-local-sctp-endpoint-vcu.";
        yexte:version 0;
        yexte:release 2;
        yexte:correction 0;
        reference
            "RFC 7950: The YANG 1.1 Data Modeling Language";
    }

    revision 2021-01-11 {
        description
            "Initial version of the LocalSctpEndpoint model.";
        yexte:version 0;
        yexte:release 1;
        yexte:correction 0;
        reference
            "RFC 7950: The YANG 1.1 Data Modeling Language";
    }

    augment "/me3gpp:ManagedElement/gnbcucp3gpp:GNBCUCPFunction/epresource:EndpointResource" {

        list LocalSctpEndpoint {
            description
                "Local transport network endpoint for control plane interface.

                E1 control plane uses TCP, hence this interface is configured in "+
                "MO class LocalIpEndpoint.";
            key id;
            uses top3gpp:Top_Grp;
            unique attributes/sctpEndpointId;
            container attributes {
                must 'count(../../../epresource:EndpointResource/localsctpepvcucp:LocalSctpEndpoint/attributes[sctpEndpointId = current()/sctpEndpointId and interfaceList != current()/interfaceList ]) &lt; 1' {
                    error-message "If sctpEndpointId is the same for LocalSctpEndpoint MO instances, interfaceList must be the same.";
                }

                uses localsctpep:LocalSctpEndpointGrp {
                    refine interfaceList {
                        min-elements 1;
                        max-elements 1;
                        must '(. = "NG") or (. = "F1") or (. = "X2") or (. = "XN")' {
                            error-message "Allowed values: NG, F1, X2, XN";
                        }
                        must 'count(../../../localsctpepvcucp:LocalSctpEndpoint/attributes/interfaceList[. = "NG"]) &lt; 2 and
                              count(../../../localsctpepvcucp:LocalSctpEndpoint/attributes/interfaceList[. = "F1"]) &lt; 2 and
                              count(../../../localsctpepvcucp:LocalSctpEndpoint/attributes/interfaceList[. = "X2"]) &lt; 2 and
                              count(../../../localsctpepvcucp:LocalSctpEndpoint/attributes/interfaceList[. = "XN"]) &lt; 2' {
                            error-message "An interface must be unique across LocalSctpEndpoints under EndpointResource.";
                        }
                        yexte:takes-effect
                            "Node restart";
                        yexte:dependencies
                            "An interface must be unique across LocalSctpEndpoints under EndpointResource.";
                        tailf:info 'Dependencies: An interface must be unique across LocalSctpEndpoints under EndpointResource, Takes effect: Node restart.';
                    }
                    refine sctpEndpointId {
                        yexte:takes-effect
                            "Node restart";
                        tailf:info 'Takes effect: Node restart.';
                    }
                }
            }
        }
    }
}
