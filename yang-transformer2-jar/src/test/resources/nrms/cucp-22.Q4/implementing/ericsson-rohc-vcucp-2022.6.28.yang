// Generated by eyang-preprocessor (1.22.0-48 2022-01-20 09:10:06 CET) on Jun 30, 2022, 8:31:43 AM
module ericsson-rohc-vcucp {
    yang-version 1.1;
    namespace urn:rdns:com:ericsson:oammodel:ericsson-rohc-vcucp;
    prefix rohcvcucp;

    import tailf-common {
        prefix tailf;
    }
    import _3gpp-common-managed-element {
        prefix "me3gpp";
    }
    import _3gpp-nr-nrm-gnbcucpfunction {
        prefix "gnbcucp3gpp";
    }
    import ericsson-uecc-vcucp {
        prefix "ueccvcucp";
    }
    import _3gpp-common-top {
        prefix "top3gpp";
    }
    import ericsson-yang-extensions {
        prefix "yexte";
    }
    import ericsson-common-types-vcucp {
        prefix commontypes;
    }

    organization
      "Ericsson AB";
    contact
      "Ericsson first line support via email";
    description
      "The module defines the Rohc data model for the Ericsson vCU-CP.

       Copyright (c) 2022 Ericsson AB. All rights reserved.";

    revision 2022-06-28 {
        description
            "Removed module-status preliminary.
             Removed preliminary status from Rohc.";
        yexte:version 0;
        yexte:release 2;
        yexte:correction 0;
        reference
            "RFC 7950: The YANG 1.1 Data Modeling Language";
    }

    revision 2022-03-14 {
        description
          "Initial version of the Rohc model.";
        yexte:version 0;
        yexte:release 1;
        yexte:correction 0;
        reference
          "RFC 7950: The YANG 1.1 Data Modeling Language";
    }

    grouping RohcGrp {
        description
            "Represents the Rohc IOC.";

        leaf ueConfGroupType {
            description
                "UE configuration Group Type.

                Defines which configuration group type that is applied in the "+
                "contained MO class RohcUeCfg.";
            type commontypes:UeConfGroupType;
            default UE_SERVICE_GROUP;
            yexte:disturbances
                "Changing this attribute can cause loss of traffic.";
            yexte:takes-effect
                "New connection";
            tailf:info 'Takes effect: New connection, Traffic Disturbance: Changing this attribute can cause loss of traffic, UE configuration Group Type. Defines which configuration group type that is applied in the contained MO class RohcUeCfg.';
        }
    }

    augment "/me3gpp:ManagedElement/gnbcucp3gpp:GNBCUCPFunction/ueccvcucp:UeCC" {
        list Rohc {
            key id;
            max-elements 1;
            description
                "Container class for Robust Header Compression configuration classes.

                The RDN of this MO must always be Rohc=1.

                MO instance Rohc=1 is created automatically when parent MO is "+
                "created, unless created manually in the same transaction as "+
                "parent MO and cannot be deleted unless parent MO is deleted.";
            yexte:precondition
                "Rohc=1 instance can only be created in the same transaction as "+
                "parent MO and must not be deleted unless parent MO is deleted.";
            uses top3gpp:Top_Grp {
                refine id {
                    must '. = "1"' {
                        error-message
                            "RDN must be 1 (e.g.. Rohc=1)";
                    }
                }
            }
            container attributes {
                uses RohcGrp;
            }
            tailf:info 'Precondition: Rohc=1 instance can only be created in the same transaction as parent MO and must not be deleted unless parent MO is deleted, Container class for Robust Header Compression configuration classes. The RDN of this MO must always be Rohc=1. MO instance Rohc=1 is created automatically when parent MO is created, unless created manually in the same transaction as parent MO and cannot be deleted unless parent MO is deleted.';
        }
    }
}
