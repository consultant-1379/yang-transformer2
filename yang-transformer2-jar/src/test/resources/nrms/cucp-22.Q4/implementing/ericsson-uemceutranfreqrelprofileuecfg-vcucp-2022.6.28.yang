// Generated by eyang-preprocessor (1.22.0-48 2022-01-20 09:10:06 CET) on Jun 30, 2022, 8:31:44 AM
module ericsson-uemceutranfreqrelprofileuecfg-vcucp {
    yang-version 1.1;
    namespace "urn:rdns:com:ericsson:oammodel:ericsson-uemceutranfreqrelprofileuecfg-vcucp";
    prefix "uemceutranfreqrelprofileuecfg";

    import tailf-common {
        prefix tailf;
    }
    import _3gpp-common-managed-element {
        prefix "me3gpp";
    }
    import _3gpp-nr-nrm-gnbcucpfunction {
        prefix "gnbcucp3gpp";
    }
    import _3gpp-common-top {
        prefix "top3gpp";
    }
    import ericsson-yang-extensions {
        prefix "yexte";
    }
    import ericsson-uemc-vcucp {
        prefix "uemc";
    }
    import ericsson-uemceutranfreqrelprofile-vcucp {
        prefix "uemceutranfreqrelprofile";
    }
    import ericsson-common-types-vcucp {
        prefix "commontypes";
    }

    organization
        "Ericsson AB";
    contact
        "Ericsson first line support via email";
    description
        "The module defines the UeMCEUtranFreqRelProfileUeCfg data model for the Ericsson vCU-CP.

        Copyright (c) 2022 Ericsson AB. All rights reserved.";

    revision 2022-06-28 {
        description
            "Removed module-status preliminary.
             Removed preliminary status from UeMCEUtranFreqRelProfileUeCfg.";
        yexte:version 0;
        yexte:release 2;
        yexte:correction 0;
        reference
            "RFC 7950: The YANG 1.1 Data Modeling Language";
    }

    revision 2022-03-14 {
        description
            "Initial version of the UeMCEUtranFreqRelProfileUeCfg model";
        yexte:version 0;
        yexte:release 1;
        yexte:correction 0;
        reference
            "RFC 7950: The YANG 1.1 Data Modeling Language";
    }

    grouping UeMCEUtranFreqRelProfileUeCfgGrp {
        description
            "Represents the UeMCEUtranFreqRelProfileUeCfg IOC.";

        leaf blindRwrAllowed {
            description
                "Whether this frequency relation is used as blind release with "+
                "redirect candidate.

                Applied at blind release with redirect triggered by poor coverage or "+
                "when UE fails capability check.

                If true for more than one E-UTRAN frequency relation, frequency "+
                "relation with lowest ARFCN is used.
                If false for all E-UTRAN frequency relations, UE will be released to "+
                "idle without redirection.";
            type boolean;
            default false;
            must "(../connModeAllowedPCell = 'true') or (. = 'false')" {
                error-message "blindRwrAllowed cannot be true if connModeAllowedPCell is false";
            }
            yexte:dependencies
                "Value true is only allowed if connModeAllowedPCell is true.";
            yexte:takes-effect
                "Next usage.";
            tailf:info 'Takes effect: Next usage, Dependencies: Value true is only allowed if connModeAllowedPCell is true, Whether this frequency relation is used as blind release with redirect candidate. Applied at blind release with redirect triggered by poor coverage or when UE fails capability check. If true for more than one E-UTRAN frequency relation, frequency relation with lowest ARFCN is used. If false for all E-UTRAN frequency relations, UE will be released to idle without redirection.';
        }

        leaf connModeAllowedPCell {
            description
                "Whether placing PCell on E-UTRAN frequency defined by E-UTRAN "+
                "frequency relation is allowed.

                Applies to UEs that use cell as PCell for poor coverage triggered "+
                "handover or blind release with redirect to this cell. Blind release "+
                "with redirect can be triggered by poor coverage or when UE fails "+
                "capability check.";
            type boolean;
            default false;
            must "(../blindRwrAllowed = 'false') or (. = 'true')" {
                error-message "connModeAllowedPCell cannot be false if blindRwrAllowed is true";
            }
            yexte:dependencies
                "Value false is not allowed if blindRwrAllowed is true.";
            yexte:takes-effect
                "Next usage.";
            tailf:info 'Takes effect: Next usage, Dependencies: Value false is not allowed if blindRwrAllowed is true, Whether placing PCell on E-UTRAN frequency defined by E-UTRAN frequency relation is allowed. Applies to UEs that use cell as PCell for poor coverage triggered handover or blind release with redirect to this cell. Blind release with redirect can be triggered by poor coverage or when UE fails capability check.';
        }

        leaf connModePrioPCell {
            description
                "Connected mode PCell priority for E-UTRAN frequency relation.

                Applies to UEs that use cell as PCell.

                Used to decide preference on which E-UTRAN frequency to place PCell "+
                "in connected mode.

                0 means frequency relation with lowest priority.
                7 means frequency relation with highest priority.

                Applicable only when connModeAllowedPCell attribute is true.";
            type int32 {
                range "0..7";
            }
            default 7;
            yexte:takes-effect
                "Next usage.";
            tailf:info 'Takes effect: Next usage, Connected mode PCell priority for E-UTRAN frequency relation. Applies to UEs that use cell as PCell. Used to decide preference on which E-UTRAN frequency to place PCell in connected mode. 0 means frequency relation with lowest priority. 7 means frequency relation with highest priority. Applicable only when connModeAllowedPCell attribute is true.';
        }

        leaf-list prefUeGroupList {
            description
                "Preference UE group list.

                List of preference UE group identifiers.

                If empty, the MO instance matches preference UE group identifiers "+
                "not defined in prefUeGroupList of any other MO instances under "+
                "parent MO instance.";
            max-elements 8;
            ordered-by user;
            type int32 {
                range "1..255";
            }
            yexte:dependencies
                "Combinations of pair of preference UE group Identifier in "+
                "prefUeGroupList and UE group identifier in ueGroupList must be "+
                "unique among UeMCEUtranFreqRelProfileUeCfg instances under same "+
                "parent UeMCEUtranFreqRelProfile instance.

                Combination of a UE group identifier in UeGroupList and empty "+
                "prefUeGroupList must be unique among UeMCEUtranFreqRelProfileUeCfg "+
                "instances under same parent UeMCEUtranFreqRelProfile instance.";
            yexte:disturbances
                "Changing this attribute can cause loss of traffic.";
            yexte:takes-effect
                "Next usage.";
            must "count(../../../UeMCEUtranFreqRelProfileUeCfg/attributes[prefUeGroupList = current()
                  and count(ueGroupList) = 0] ) = 1" {
                error-message
                    "Exactly one UeMCEUtranFreqRelProfileUeCfg instance under an "+
                    "UeMCEUtranFreqRelProfile must combine a specific preference UE "+
                    "group identifier in attribute prefUeGroupList with an empty ueGroupList.";
            }
            tailf:info 'Takes effect: Next usage, Traffic Disturbance: Changing this attribute can cause loss of traffic, Dependencies: Combinations of pair of preference UE group Identifier in prefUeGroupList and UE group identifier in ueGroupList must be unique among UeMCEUtranFreqRelProfileUeCfg instances under same parent UeMCEUtranFreqRelProfile instance.

                Combination of a UE group identifier in UeGroupList and empty prefUeGroupList must be unique among UeMCEUtranFreqRelProfileUeCfg instances under same parent UeMCEUtranFreqRelProfile instance, Preference UE group list. List of preference UE group identifiers. If empty, the MO instance matches preference UE group identifiers not defined in prefUeGroupList of any other MO instances under parent MO instance.';
        }

        leaf-list ueConfGroupList {
            description
                "UE configuration group list.

                List of UE configuration group identifiers.

                If empty, the MO instance matches all UE configuration group "+
                "identifiers.

                Which UE configuration group type that is applied is defined by "+
                "attribute ueConfGroupType in parent MO class instance.";
            max-elements 32;
            ordered-by user;

            type int32 {
                range "1..255";
            }
            yexte:dependencies
                "UE configuration group identifier must be defined in only one "+
                "ueConfGroupList among UeMCEUtranFreqRelProfileUeCfg instances under "+
                "same parent UeMCEUtranFreqRelProfile instance.

                A given UE configuration group identifier can be defined in only one "+
                "ueConfGroupList among UeMCEUtranFreqRelProfileUeCfg instances under "+
                "same parent UeMCEUtranFreqRelProfile instance.";
            yexte:disturbances
                "Changing this attribute can cause loss of traffic.";
            yexte:takes-effect
                "Next usage.";
            must "count(../../../UeMCEUtranFreqRelProfileUeCfg/attributes[ueConfGroupList = current() ]) &lt;= 1" {
                error-message
                    "Only one UeMCEUtranFreqRelProfileUeCfg instance under an "+
                    "UeMCEUtranFreqRelProfile can include a specific UE configuration "+
                    "group identifier in attribute ueConfGroupList.";
            }
            tailf:info 'Takes effect: Next usage, Traffic Disturbance: Changing this attribute can cause loss of traffic, Dependencies: UE configuration group identifier must be defined in only one ueConfGroupList among UeMCEUtranFreqRelProfileUeCfg instances under same parent UeMCEUtranFreqRelProfile instance.

                A given UE configuration group identifier can be defined in only one ueConfGroupList among UeMCEUtranFreqRelProfileUeCfg instances under same parent UeMCEUtranFreqRelProfile instance, UE configuration group list. List of UE configuration group identifiers. If empty, the MO instance matches all UE configuration group identifiers. Which UE configuration group type that is applied is defined by attribute ueConfGroupType in parent MO class instance.';
        }

        leaf-list ueGroupList {
            description
                "UE group list.

                List of UE group identifiers.

                If empty, the MO instance matches all UE group identifiers.";
            max-elements 16;
            ordered-by user;

            type int32 {
                range "1..255";
            }
            yexte:dependencies
                "Combinations of pair of preference UE group Identifier in "+
                "prefUeGroupList and UE group identifier in ueGroupList must be "+
                "unique among UeMCEUtranFreqRelProfileUeCfg instances under same "+
                "parent UeMCEUtranFreqRelProfile instance.

                Combination of a UE group identifier in UeGroupList and empty "+
                "prefUeGroupList must be unique among UeMCEUtranFreqRelProfileUeCfg "+
                "instances under same parent UeMCEUtranFreqRelProfile instance.";
            yexte:disturbances
                "Changing this attribute can cause loss of traffic.";
            yexte:takes-effect
                "Next usage.";
            must "count(../prefUeGroupList) &gt; 0 or
                  count(../../../UeMCEUtranFreqRelProfileUeCfg/attributes[ueGroupList = current()
                  and count(prefUeGroupList) = 0] ) &lt;= 1" {
                error-message
                    "Only one UeMCEUtranFreqRelProfileUeCfg instance under an "+
                    "UeMCEUtranFreqRelProfile can combine a specific UE group "+
                    "identifier in attribute ueGroupList with an empty prefUeGroupList.";
            }
            tailf:info 'Takes effect: Next usage, Traffic Disturbance: Changing this attribute can cause loss of traffic, Dependencies: Combinations of pair of preference UE group Identifier in prefUeGroupList and UE group identifier in ueGroupList must be unique among UeMCEUtranFreqRelProfileUeCfg instances under same parent UeMCEUtranFreqRelProfile instance.

                Combination of a UE group identifier in UeGroupList and empty prefUeGroupList must be unique among UeMCEUtranFreqRelProfileUeCfg instances under same parent UeMCEUtranFreqRelProfile instance, UE group list. List of UE group identifiers. If empty, the MO instance matches all UE group identifiers.';
        }
    }

    augment "/me3gpp:ManagedElement/gnbcucp3gpp:GNBCUCPFunction/uemc:UeMC/uemceutranfreqrelprofile:UeMCEUtranFreqRelProfile" {
        list UeMCEUtranFreqRelProfileUeCfg {
            description
                "UE mobility control attributes, UE configuration group.

                The attributes are used on E-UTRAN frequency relation level.

                MO instance UeMCEutranFreqRelProfileUeCfg=Base is created "+
                "automatically when parent MO is created, unless created "+
                "manually in the same transaction as parent MO.

                Attributes prefUeGroupList, ueGroupList and ueConfGroupList "+
                "must be empty in instance UeMCEutranFreqRelProfileUeCfg=Base "+
                "but cannot all be empty in other instances of "+
                "UeMCEutranFreqRelProfileUeCfg under same parent "+
                "UeMCEutranFreqRelProfile.";
            key id;
            max-elements 32;
            uses top3gpp:Top_Grp;
            container attributes {
                uses UeMCEUtranFreqRelProfileUeCfgGrp;
                uses commontypes:UserLabelGrp;
            }
            yexte:precondition
                "UeMCEutranFreqRelProfileUeCfg=Base MO instance can only be "+
                "created in the same transaction as parent MO and must not be "+
                "deleted unless parent MO is deleted. Other instances can be "+
                "created and deleted manually.

                Maximum 31 UeMCEutranFreqRelProfileUeCfg instances, with RDN "+
                "different from Base, can be created.";

            must "count(../UeMCEUtranFreqRelProfileUeCfg) &lt; 32 or
                  count(../UeMCEUtranFreqRelProfileUeCfg/id[. = 'Base'] ) = 1" {
                error-message
                    "Maximum 31 UeMCEUtranFreqRelProfileUeCfg instances under an "+
                    "UeMCEUtranFreqRelProfile can be created with RDN different from Base.";
            }
            must "count(../UeMCEUtranFreqRelProfileUeCfg/attributes[prefUeGroupList = current()/attributes/prefUeGroupList
                  and ueGroupList = current()/attributes/ueGroupList] ) &lt;= 1" {
                error-message
                    "The combinations of a pair of UE group identifier in ueGroupList "+
                    "and preference UE group identifier in prefUeGroupList must be "+
                    "unique among UeMCEUtranFreqRelProfileUeCfg under an "+
                    "UeMCEUtranFreqRelProfile.";
            }
            must "./id != 'Base'
                    or ( count(./attributes/ueConfGroupList) = 0
                         and count(./attributes/ueGroupList) = 0
                         and count(./attributes/prefUeGroupList) = 0 )" {
                error-message
                    "UeMCEutranFreqRelProfileUeCfg::prefUeGroupList, ueGroupList and "+
                    "ueConfGroupList must be empty in the UeMCEUtranFreqRelProfileUeCfg=Base "+
                    "instance.";
            }
            must "./id = 'Base'
                    or not ( count(./attributes/ueConfGroupList) = 0
                             and count(./attributes/ueGroupList) = 0
                             and count(./attributes/prefUeGroupList) = 0 )" {
                error-message
                    "UeMCEutranFreqRelProfileUeCfg::prefUeGroupList, ueGroupList and "+
                    "ueConfGroupList can only be empty in the UeMCEUtranFreqRelProfileUeCfg=Base "+
                    "instance.";
            }
            tailf:info 'Precondition: UeMCEutranFreqRelProfileUeCfg=Base MO instance can only be created in the same transaction as parent MO and must not be deleted unless parent MO is deleted. Other instances can be created and deleted manually.

                Maximum 31 UeMCEutranFreqRelProfileUeCfg instances, with RDN different from Base, can be created, UE mobility control attributes, UE configuration group. The attributes are used on E-UTRAN frequency relation level. MO instance UeMCEutranFreqRelProfileUeCfg=Base is created automatically when parent MO is created, unless created manually in the same transaction as parent MO. Attributes prefUeGroupList, ueGroupList and ueConfGroupList must be empty in instance UeMCEutranFreqRelProfileUeCfg=Base but cannot all be empty in other instances of UeMCEutranFreqRelProfileUeCfg under same parent UeMCEutranFreqRelProfile.';
        }
    }
}
