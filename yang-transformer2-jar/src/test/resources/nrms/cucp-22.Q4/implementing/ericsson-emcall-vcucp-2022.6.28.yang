// Generated by eyang-preprocessor (1.22.0-48 2022-01-20 09:10:06 CET) on Jun 30, 2022, 8:31:35 AM
module ericsson-emcall-vcucp {
    yang-version 1.1;
    namespace urn:rdns:com:ericsson:oammodel:ericsson-emcall-vcucp;
    prefix emcallvcucp;

    import tailf-common {
        prefix tailf;
    }
    import _3gpp-common-managed-element {
        prefix me3gpp;
    }
    import _3gpp-nr-nrm-gnbcucpfunction {
        prefix gnbcucp3gpp;
    }
    import _3gpp-common-top {
        prefix top3gpp;
    }
    import _3gpp-common-yang-types {
        prefix types3gpp;
    }
    import ericsson-yang-extensions {
        prefix yexte;
    }
    import ericsson-common-types-vcucp {
        prefix commontypes;
    }

    organization
        "Ericsson AB";
    contact
        "Ericsson first line support via email";
    description
        "The module defines the EmCall data model for the Ericsson vCU-CP.

        Copyright (c) 2021-2022 Ericsson AB. All rights reserved.";

    revision 2022-06-28 {
        description
            "Removed module-status preliminary.";
        yexte:version 0;
        yexte:release 3;
        yexte:correction 0;
        reference
            "RFC 7950: The YANG 1.1 Data Modeling Language";
    }

    revision 2022-03-14 {
        description
            "Added the userLabel attribute.";
        yexte:version 0;
        yexte:release 2;
        yexte:correction 0;
        reference
            "RFC 7950: The YANG 1.1 Data Modeling Language";
    }

    revision 2021-11-04 {
        description
            "Initial version of the EmCall model.";
        yexte:version 0;
        yexte:release 1;
        yexte:correction 0;
        reference
            "RFC 7950: The YANG 1.1 Data Modeling Language";
    }

    grouping EmCallGrp {
        description
            "Represents the EmCall IOC.";

        leaf-list arpPrioEm5qi1List {
            max-elements 15;
            description
                "ARP level values used for emergency calls in QoS flow with 5qi = 1.

                If empty, no Allocation and Retention Priority (ARP) level is " +
                "interpreted as emergency call.";
            type int32 {
                range "1..15";
            }
            reference
                "3GPP TS 38.413";
            yexte:takes-effect
                "New connection";
            tailf:info 'Takes effect: New connection, ARP level values used for emergency calls in QoS flow with 5qi = 1. If empty, no Allocation and Retention Priority (ARP) level is interpreted as emergency call.';
        }

        leaf-list arpPrioEm5qi5List {
            max-elements 15;
            description
                "ARP level values used for emergency calls in QoS flow with 5qi = 5.

                If empty, no Allocation and Retention Priority (ARP) level is " +
                "interpreted as emergency call.";
            type int32 {
                range "1..15";
            }
            reference
                "3GPP TS 38.413";
            yexte:takes-effect
                "New connection";
            tailf:info 'Takes effect: New connection, ARP level values used for emergency calls in QoS flow with 5qi = 5. If empty, no Allocation and Retention Priority (ARP) level is interpreted as emergency call.';
        }

        list pLMNIdList {
            key "mcc mnc";
            max-elements 12;
            description
                "List of PLMNs for which the parameters of EmCall MO instance are " +
                "valid.

                If empty, parameters are valid for all PLMNs and are only used if " +
                "the PLMN does not match any EmCall::pLMNIdList.";
            uses types3gpp:PLMNId;
            must "count(../../../EmCall/attributes/pLMNIdList[mcc = current()/mcc and mnc = current()/mnc]) &lt;= 1" {
                error-message "pLMNIds in all pLMNIdLists must be unique among all EmCall MOs under the same GNBCUCPFunction.";
            }
            yexte:dependencies
                "Only one instance of EmCall can have empty pLMNIdList.

                A pLMNId must only exist in one EmCall instance under a " +
                "GNBCUCPFunction.";
            reference
                "3GPP TS 28.541";
            tailf:info 'Dependencies: Only one instance of EmCall can have empty pLMNIdList.

                A pLMNId must only exist in one EmCall instance under a GNBCUCPFunction, List of PLMNs for which the parameters of EmCall MO instance are valid. If empty, parameters are valid for all PLMNs and are only used if the PLMN does not match any EmCall::pLMNIdList.';
        }
    }

    augment "/me3gpp:ManagedElement/gnbcucp3gpp:GNBCUCPFunction" {
        list EmCall {
            description
                "Emergency call configuration for NRCellCU MOs.";
            key id;
            max-elements 12;
            uses top3gpp:Top_Grp;
            container attributes {
                uses EmCallGrp;
                uses commontypes:UserLabelGrp;
            }
            must "count(../EmCall[count(attributes/pLMNIdList) = 0]) &lt;= 1" {
                error-message "Only one EmCall can be configure with an empty pLMNIdList under the same GNBCUCPFunction.";
            }
        }
    }
}
