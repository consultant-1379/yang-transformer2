// Generated by eyang-preprocessor (1.22.0-48 2022-01-20 09:10:06 CET) on Jun 30, 2022, 8:31:44 AM
module ericsson-securityhandling-vcucp {
    yang-version 1.1;
    namespace urn:rdns:com:ericsson:oammodel:ericsson-securityhandling-vcucp;
    prefix sechandling;

    import tailf-common {
        prefix tailf;
    }
    import _3gpp-common-managed-element {
        prefix me3gpp;
    }
    import _3gpp-nr-nrm-gnbcucpfunction {
        prefix gnbcucp3gpp;
    }
    import _3gpp-common-top {
        prefix top3gpp;
    }
    import ericsson-yang-extensions {
        prefix yexte;
    }

    organization
        "Ericsson AB";
    contact
        "Ericsson first line support via email";
    description
        "The module defines the SecurityHandling data model for the Ericsson vCU-CP.

        Copyright (c) 2021-2022 Ericsson AB. All rights reserved.";

    revision 2022-06-28 {
        description
            "Removed module-status preliminary.";
        yexte:version 1;
        yexte:release 1;
        yexte:correction 0;
        reference
            "RFC 7950: The YANG 1.1 Data Modeling Language";
    }

    revision 2022-03-14 {
        description
            "Changed order of initial-value tags for cipheringAlgoPrio.";
        yexte:version 1;
        yexte:release 0;
        yexte:correction 0;
        reference
            "RFC 7950: The YANG 1.1 Data Modeling Language";
    }

    revision 2022-03-09 {
        description
            "Made cipheringAlgoPrio ordered by user.";
        yexte:version 0;
        yexte:release 1;
        yexte:correction 2;
        reference
            "RFC 7950: The YANG 1.1 Data Modeling Language";
    }

    revision 2021-06-08 {
        description
            "Changed error message for a must statement.";
        yexte:version 0;
        yexte:release 1;
        yexte:correction 1;
        reference
            "RFC 7950: The YANG 1.1 Data Modeling Language";
    }

    revision 2021-05-17 {
        description
            "Initial version of the SecurityHandling model";
        yexte:version 0;
        yexte:release 1;
        yexte:correction 0;
        reference
            "RFC 7950: The YANG 1.1 Data Modeling Language";
    }

    typedef CipheringAlgorithmID {
        description
            "Ciphering algorithms enum.";

        type enumeration {
            enum NEA0 {
                value 0;
                description
                    "No ciphering is applied.";
                reference
                    "3GPP TS 33.501";
            }

            enum NEA1 {
                value 1;
                description
                    "128-NEA1 (based on SNOW 3G).";
                reference
                    "3GPP TS 33.501";
            }

            enum NEA2 {
                value 2;
                description
                    "128-NEA2 (based on AES).";
                reference
                    "3GPP TS 33.501";
            }

            enum NEA3 {
                value 3;
                description
                    "128-NEA3 (based on ZUC).";
                reference
                    "3GPP TS 33.501";
            }
        }
    }

    grouping SecurityHandlingGrp {
        description
            "Represents the SecurityHandling IOC.";

        leaf-list cipheringAlgoPrio {
            description
                "Array of allowed ciphering algorithms with priority order.

                Minimum length of 1, maximum length of 4. Algorithm in index zero has "+
                "highest priority. Each algorithm written only once in array.";
            type CipheringAlgorithmID;
            min-elements 1;
            max-elements 4;
            ordered-by user;
            yexte:initial-value NEA2;
            yexte:initial-value NEA1;
            yexte:initial-value NEA0;
            yexte:takes-effect
                "New connection";
            tailf:info 'Takes effect: New connection, Array of allowed ciphering algorithms with priority order. Minimum length of 1, maximum length of 4. Algorithm in index zero has highest priority. Each algorithm written only once in array.';
        }

        leaf personalDataProtectionEnabled {
            description
                "Whether personal data protection is enabled.

                When personal data protection is enabled, subscriber personal data is "+
                "not logged.
                If protection is disabled, there are rare traffic occasions when "+
                "subscriber personal data is revealed and can be logged in PM events "+
                "and other short-lived on-demand troubleshooting logs.
                Alert is raised when personal data protection is set to be disabled.";
            type boolean;
            default true;
            yexte:takes-effect
                "Node restart";
            tailf:info 'Takes effect: Node restart, Whether personal data protection is enabled. When personal data protection is enabled, subscriber personal data is not logged. If protection is disabled, there are rare traffic occasions when subscriber personal data is revealed and can be logged in PM events and other short-lived on-demand troubleshooting logs. Alert is raised when personal data protection is set to be disabled.';
        }
    }

    augment "/me3gpp:ManagedElement/gnbcucp3gpp:GNBCUCPFunction" {
        list SecurityHandling {
            description
                "Manageable characteristics of security handling except during X2 "+
                "handover and S1 handover.

                The RDN of this MO is SecurityHandling=1.";
            max-elements 1;
            key id;
            uses top3gpp:Top_Grp {
                refine id {
                    must '. = "1"' {
                        error-message
                          "The RDN of this MO must always be SecurityHandling=1";
                    }
                }
            }
            container attributes {
                uses SecurityHandlingGrp;
            }
            yexte:system-supplied-entries "id=1 cipheringAlgoPrio=[NEA1, NEA2, NEA0] personalDataProtectionEnabled=true";
        }
    }
}
