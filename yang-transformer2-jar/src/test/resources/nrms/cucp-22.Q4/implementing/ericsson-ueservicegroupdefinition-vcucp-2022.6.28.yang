// Generated by eyang-preprocessor (1.22.0-48 2022-01-20 09:10:06 CET) on Jun 30, 2022, 8:31:44 AM
module ericsson-ueservicegroupdefinition-vcucp {
    yang-version 1.1;
    namespace "urn:rdns:com:ericsson:oammodel:ericsson-ueservicegroupdefinition-vcucp";
    prefix ueservicegroupdefinition;

    import tailf-common {
        prefix tailf;
    }
    import _3gpp-common-managed-element {
        prefix "me3gpp";
    }
    import _3gpp-nr-nrm-gnbcucpfunction {
        prefix "gnbcucp3gpp";
    }
    import _3gpp-common-top {
        prefix "top3gpp";
    }
    import ericsson-uegroupselection-vcucp {
        prefix "uegroupselectionvcucp";
    }
    import ericsson-yang-extensions {
        prefix "yexte";
    }
    import ericsson-common-types-vcucp {
        prefix "commontypes";
    }

    organization
      "Ericsson AB";
    contact
      "Ericsson first line support via email";
    description
      "The module defines the UeServiceGroupDefinition data model for the Ericsson vCU-CP.

       Copyright (c) 2022 Ericsson AB. All rights reserved.";

    revision 2022-06-28 {
        description
            "Removed module-status preliminary.
             Removed preliminary status from UeServiceGroupDefinition.";
        yexte:version 0;
        yexte:release 2;
        yexte:correction 0;
        reference
            "RFC 7950: The YANG 1.1 Data Modeling Language";
    }

    revision 2022-03-14 {
        description
            "Initial version of the UeServiceGroupDefinition model.";
        yexte:version 0;
        yexte:release 1;
        yexte:correction 0;
        reference
            "RFC 7950: The YANG 1.1 Data Modeling Language";
    }

    grouping UeServiceGroupDefinitionGrp {
        description
            "Represents the UeServiceGroupDefinition IOC.";

        leaf selectionCriteria {
            description
                "UE service group selection criteria.

                Backus-Naur form defines criteria to decide if a UE belongs to the "+
                "UE service group.

                If empty, UE service group selection criteria matches all UEs.

                Syntax:
                &lt;Statement&gt; ::= &lt;ExpressionList&gt; | \"\"
                &lt;ExpressionList&gt; ::= &lt;ExpressionList&gt; &lt;AndOr&gt; &lt;ExpressionList&gt; | "+
                "\"!\"? \"(\" &lt;ExpressionList&gt; \")\" | \"!\"? &lt;VariableExpression&gt;
                &lt;VariableExpression&gt; ::= &lt;Variable&gt; &lt;RelationalOperator&gt; &lt;Value&gt; | "+
                "&lt;Variable&gt; \"==\" \"{\" &lt;ValueList&gt; \"}\"
                &lt;ValueList&gt; ::= &lt;Value&gt; \",\" &lt;ValueList&gt; | &lt;Value&gt;

                &lt;Variable&gt; ::= \"5qi\" | \"arp\" | \"cgrole\" | \"imeisv\" | "+
                "\"imeisvn \" | \"imeitac\" | \"plmn\" | \"qci\" | \"rfsp\" | "+
                "\"snssai\" | \"spid\"

                &lt;AndOr&gt; ::= \"&amp;&amp;\" | \"||\"
                &lt;RelationalOperator&gt; ::= \"==\" | \"!=\" | \"&lt;\" | \"&lt;=\" | \"&gt;=\" | "+
                "\"&gt;\"

                A list of possible values can be specified in the form &lt;Variable&gt; == "+
                "{&lt;value1&gt;, &lt;value2&gt;, ... , &lt;valueN&gt;}. This statement is equivalent "+
                "to writing (&lt;Variable&gt; == &lt;value1&gt; || &lt;Variable&gt; == &lt;value2&gt; || ... "+
                "|| &lt;Variable&gt; == &lt;valueN&gt;).

                A &lt;Statement&gt; set to the empty string (\"\") always evaluates to true.

                Whitespaces are allowed between every token in the syntax above.

                Question mark (?) means zero or one occurrence. For example, \"!\"? "+
                "makes ! optional.

                Allowed &lt;Value&gt; and &lt;RelationalOperator&gt; depend on &lt;Variable&gt; with "+
                "limitations given below.

                Variable Definitions

                5qi:
                Operator: one of ==, !=, &lt;=, &gt;=, &lt;, &gt;
                Value: Integer in range 0..255 given in decimal.

                arp:
                Operator: one of ==, !=, &lt;=, &gt;=, &lt;, &gt;
                Value: Integer in range 1..16 given in decimal.

                cgrole:
                Operator: one of ==, !=
                Value: One of mcg or scg.

                imeisv:
                Operator: one of ==, !=
                Value: A string matched by regular expression "+
                "[0-9]{10}[0-9fF]{4}[0-9]{2} (10 digit decimal number + 4 digit "+
                "hexa-decimal number + 2 digit decimal number).
                Description: IMEISV composed of three distinct elements:
                - 8-digit Type Allocation Code (TAC): 8 digit decimal number
                - 6-digit Serial Number (SNR): 6 digit decimal number
                - 2-digit Software Version Number (SVN): 2 digit decimal number

                - last four digits of SNR are automatically masked with 0xFFFF to "+
                "match with masked IMEISV.

                ExampleValues: 1234567890123456, 1234567890FFFF12, 1234567890ffff12

                imeitac:
                Type Allocation Code (TAC) part of imeisv
                Operator: one of ==, !=
                Value: 8 digit decimal number

                imeisvn:
                Software Version Number (SVN) part of imeisv
                Operator: one of ==, !=, &lt;=, &gt;=, &lt;, &gt;
                Value: 2 digit decimal number

                plmn:
                Operator: one of ==, !=
                Value: A string matched by the regular expression "+
                "[02-79][0-9][0-9]-[0-9][0-9][0-9]?.

                ExampleValues: 070-007, 070-07, 234-56

                qci:
                Operator: one of ==, !=, &lt;=, &gt;=, &lt;, &gt;
                Value: Integer in range 0..255 given in decimal.

                rfsp:
                Operator: one of ==, !=, &lt;=, &gt;=, &lt;, &gt;
                Value: Integer in range 1..256 given in decimal.

                snssai:
                Operator: one of ==, !=, &lt;=, &gt;=, &lt;, &gt;
                Value: Integer in range 0x0..0xffffffff given in hexadecimal.

                spid:
                Operator: one of ==, !=, &lt;=, &gt;=, &lt;, &gt;
                Value: Integer in range 1..256 given in decimal.

                Operators

                Precedence Operator Description
                ---------------------------------------------
                1 &lt; Less than
                &lt;= Less than or equal
                &gt; Greater than
                &gt;= Greater than or equal
                == Equal
                != Not equal
                ---------------------------------------------
                2 ! Not
                ---------------------------------------------
                3 &amp;&amp; And
                ---------------------------------------------
                4 || Or
                ---------------------------------------------

                The not operator ! negates either the following &lt;VariableExpression&gt; "+
                "or an &lt;ExpressionList&gt; encapsulated in parenthesis.
                Therefore, the expression !a==b &amp;&amp; c==d is equivalent to ((!(a==b)) "+
                "&amp;&amp; (c==d)) and different from !(a==b &amp;&amp; c==d).
                Expression !a==b and !(a==b) are equivalent.

                Since operator &amp;&amp; operator has higher precedence than ||, a&lt;b || a&lt;c "+
                "&amp;&amp; c&lt;d is equivalent to (a&lt;b || (a&lt;c &amp;&amp; c&lt;d)). To change the order "+
                "of operations, surround the expression with parentheses (...) as "+
                "(a&lt;b || a&lt;c) &amp;&amp; c&lt;d to force || to be evaluated first.

                Examples

                Simple one valued expressions:
                plmn == 234-56
                spid == 1
                cgrole == mcg
                arp &gt; 3
                snssai == 0xfedcba98

                Value list expressions:
                spid == {8,9,10,1,155}
                !plmn == {234-56, 434-567}

                Equivalent expressions using ||:
                (spid == 8 || spid == 9 || spid == 10 || spid == 1 || spid == 155)
                !(plmn == 234-56 || plmn == 434-567)

                Mixed examples:
                spid == 1 &amp;&amp; cgrole == mcg
                !(spid != 1 || cgrole != mcg)
                (spid == 8 || spid == 9 || spid == 10 || spid == 1 || spid == 155) "+
                "&amp;&amp; (plmn == 234-56 || plmn == 434-567)";
            type string {
                length "1..1000";
            }
            yexte:disturbances
                "Changing this attribute can cause loss of traffic.";
            yexte:takes-effect
                "New connection";
            tailf:info 'Takes effect: New connection, Traffic Disturbance: Changing this attribute can cause loss of traffic, UE service group selection criteria. Backus-Naur form defines criteria to decide if a UE belongs to the UE service group. If empty, UE service group selection criteria matches all UEs. Syntax: &lt;Statement&gt; ::= &lt;ExpressionList&gt; | \"\" &lt;ExpressionList&gt; ::= &lt;ExpressionList&gt; &lt;AndOr&gt; &lt;ExpressionList&gt; | \"!\"? \"(\" &lt;ExpressionList&gt; \")\" | \"!\"? &lt;VariableExpression&gt; &lt;VariableExpression&gt; ::= &lt;Variable&gt; &lt;RelationalOperator&gt; &lt;Value&gt; | &lt;Variable&gt; \"==\" \"{\" &lt;ValueList&gt; \"}\" &lt;ValueList&gt; ::= &lt;Value&gt; \",\" &lt;ValueList&gt; | &lt;Value&gt; &lt;Variable&gt; ::= \"5qi\" | \"arp\" | \"cgrole\" | \"imeisv\" | \"imeisvn \" | \"imeitac\" | \"plmn\" | \"qci\" | \"rfsp\" | \"snssai\" | \"spid\" &lt;AndOr&gt; ::= \"&amp;&amp;\" | \"||\" &lt;RelationalOperator&gt; ::= \"==\" | \"!=\" | \"&lt;\" | \"&lt;=\" | \"&gt;=\" | \"&gt;\" A list of possible values can be specified in the form &lt;Variable&gt; == {&lt;value1&gt;, &lt;value2&gt;, ... , &lt;valueN&gt;}. This statement is equivalent to writing (&lt;Variable&gt; == &lt;value1&gt; || &lt;Variable&gt; == &lt;value2&gt; || ... || &lt;Variable&gt; == &lt;valueN&gt;). A &lt;Statement&gt; set to the empty string (\"\") always evaluates to true. Whitespaces are allowed between every token in the syntax above. Question mark (?) means zero or one occurrence. For example, \"!\"? makes ! optional. Allowed &lt;Value&gt; and &lt;RelationalOperator&gt; depend on &lt;Variable&gt; with limitations given below. Variable Definitions 5qi: Operator: one of ==, !=, &lt;=, &gt;=, &lt;, &gt; Value: Integer in range 0..255 given in decimal. arp: Operator: one of ==, !=, &lt;=, &gt;=, &lt;, &gt; Value: Integer in range 1..16 given in decimal. cgrole: Operator: one of ==, != Value: One of mcg or scg. imeisv: Operator: one of ==, != Value: A string matched by regular expression [0-9]{10}[0-9fF]{4}[0-9]{2} (10 digit decimal number + 4 digit hexa-decimal number + 2 digit decimal number). Description: IMEISV composed of three distinct elements: - 8-digit Type Allocation Code (TAC): 8 digit decimal number - 6-digit Serial Number (SNR): 6 digit decimal number - 2-digit Software Version Number (SVN): 2 digit decimal number - last four digits of SNR are automatically masked with 0xFFFF to match with masked IMEISV. ExampleValues: 1234567890123456, 1234567890FFFF12, 1234567890ffff12 imeitac: Type Allocation Code (TAC) part of imeisv Operator: one of ==, != Value: 8 digit decimal number imeisvn: Software Version Number (SVN) part of imeisv Operator: one of ==, !=, &lt;=, &gt;=, &lt;, &gt; Value: 2 digit decimal number plmn: Operator: one of ==, != Value: A string matched by the regular expression [02-79][0-9][0-9]-[0-9][0-9][0-9]?. ExampleValues: 070-007, 070-07, 234-56 qci: Operator: one of ==, !=, &lt;=, &gt;=, &lt;, &gt; Value: Integer in range 0..255 given in decimal. rfsp: Operator: one of ==, !=, &lt;=, &gt;=, &lt;, &gt; Value: Integer in range 1..256 given in decimal. snssai: Operator: one of ==, !=, &lt;=, &gt;=, &lt;, &gt; Value: Integer in range 0x0..0xffffffff given in hexadecimal. spid: Operator: one of ==, !=, &lt;=, &gt;=, &lt;, &gt; Value: Integer in range 1..256 given in decimal. Operators Precedence Operator Description --------------------------------------------- 1 &lt; Less than &lt;= Less than or equal &gt; Greater than &gt;= Greater than or equal == Equal != Not equal --------------------------------------------- 2 ! Not --------------------------------------------- 3 &amp;&amp; And --------------------------------------------- 4 || Or --------------------------------------------- The not operator ! negates either the following &lt;VariableExpression&gt; or an &lt;ExpressionList&gt; encapsulated in parenthesis. Therefore, the expression !a==b &amp;&amp; c==d is equivalent to ((!(a==b)) &amp;&amp; (c==d)) and different from !(a==b &amp;&amp; c==d). Expression !a==b and !(a==b) are equivalent. Since operator &amp;&amp; operator has higher precedence than ||, a&lt;b || a&lt;c &amp;&amp; c&lt;d is equivalent to (a&lt;b || (a&lt;c &amp;&amp; c&lt;d)). To change the order of operations, surround the expression with parentheses (...) as (a&lt;b || a&lt;c) &amp;&amp; c&lt;d to force || to be evaluated first. Examples Simple one valued expressions: plmn == 234-56 spid == 1 cgrole == mcg arp &gt; 3 snssai == 0xfedcba98 Value list expressions: spid == {8,9,10,1,155} !plmn == {234-56, 434-567} Equivalent expressions using ||: (spid == 8 || spid == 9 || spid == 10 || spid == 1 || spid == 155) !(plmn == 234-56 || plmn == 434-567) Mixed examples: spid == 1 &amp;&amp; cgrole == mcg !(spid != 1 || cgrole != mcg) (spid == 8 || spid == 9 || spid == 10 || spid == 1 || spid == 155) &amp;&amp; (plmn == 234-56 || plmn == 434-567)';
        }

        leaf ueServiceGroupId {
            description
                "UE service group Identifier.";
            mandatory true;
            type int32 {
                range "1..255";
            }
            yexte:dependencies
                "The ueServiceGroupId must be unique among UeServiceGroupDefinition "+
                "MO instances.";
            yexte:disturbances
                "Changing this attribute can cause loss of traffic.";
            yexte:takes-effect
                "New connection";
            tailf:info 'Takes effect: New connection, Traffic Disturbance: Changing this attribute can cause loss of traffic, Dependencies: The ueServiceGroupId must be unique among UeServiceGroupDefinition MO instances, UE service group Identifier.';
        }

        leaf ueServiceGroupPriority {
            description
                "Relative priority among UE service groups.

                If UE fulfills the selection criteria for more than one UE service "+
                "group, UE service group with the highest priority is selected.
                Higher value of ueServiceGroupPriority gives higher priority.";
            mandatory true;
            type int32 {
                range "1..65535";
            }
            yexte:dependencies
                "The ueServiceGroupPriority must be unique among "+
                "UeServiceGroupDefinition MO instances.";
            yexte:disturbances
                "Changing this attribute can cause loss of traffic.";
            yexte:takes-effect
                "New connection";
            tailf:info 'Takes effect: New connection, Traffic Disturbance: Changing this attribute can cause loss of traffic, Dependencies: The ueServiceGroupPriority must be unique among UeServiceGroupDefinition MO instances, Relative priority among UE service groups. If UE fulfills the selection criteria for more than one UE service group, UE service group with the highest priority is selected. Higher value of ueServiceGroupPriority gives higher priority.';
        }
    }

    augment "/me3gpp:ManagedElement/gnbcucp3gpp:GNBCUCPFunction/uegroupselectionvcucp:UeGroupSelection" {
        list UeServiceGroupDefinition {
            description
                "UE service group definition.";
            key id;
            unique "attributes/ueServiceGroupId";
            unique "attributes/ueServiceGroupPriority";
            max-elements 15;
            uses top3gpp:Top_Grp;

            container attributes {
                uses UeServiceGroupDefinitionGrp;
                uses commontypes:UserLabelGrp;
            }
        }
    }
}
