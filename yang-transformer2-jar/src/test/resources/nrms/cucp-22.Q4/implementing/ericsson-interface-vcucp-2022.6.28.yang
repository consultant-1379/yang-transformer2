// Generated by eyang-preprocessor (1.22.0-48 2022-01-20 09:10:06 CET) on Jun 30, 2022, 8:31:38 AM
module ericsson-interface-vcucp {
    yang-version 1.1;
    namespace urn:rdns:com:ericsson:oammodel:ericsson-interface-vcucp;
    prefix interfacevcucp;

    import tailf-common {
        prefix tailf;
    }
    import _3gpp-common-managed-element {
        prefix me3gpp;
    }
    import _3gpp-common-top {
        prefix top3gpp;
    }
    import ericsson-interface-vcu {
        prefix interface;
    }
    import ericsson-ipaddress-vcu {
        prefix ipaddress;
    }
    import ericsson-transport-service-vcucp {
        prefix transservice;
    }
    import ericsson-yang-extensions {
        prefix yexte;
    }

    organization
        "Ericsson AB";
    contact
        "Ericsson first line support via email";
    description
        "The module defines the Interface data model for the Ericsson vCU-CP.

    Copyright (c) 2021-2022 Ericsson AB. All rights reserved.";

    revision 2022-06-28 {
        description
            "Removed module-status preliminary.";
        yexte:version 0;
        yexte:release 2;
        yexte:correction 0;
        reference
            "RFC 7950: The YANG 1.1 Data Modeling Language";
    }

    revision 2021-03-16 {
        description
            "Moved IpAddressV4 and IpAddressV6 from module ericsson-ipaddress-vcucp.";
        yexte:version 0;
        yexte:release 1;
        yexte:correction 1;
        reference
            "RFC 7950: The YANG 1.1 Data Modeling Language";
    }

    revision 2021-01-13 {
        description
            "Initial version of the Interface model.";
        yexte:version 0;
        yexte:release 1;
        yexte:correction 0;
        reference
            "RFC 7950: The YANG 1.1 Data Modeling Language";
    }

    augment "/me3gpp:ManagedElement/transservice:TransportService" {
        list Interface {
            description
                "Represents IP-addressed termination points.";
            key id;
            uses top3gpp:Top_Grp;
            container attributes {
                uses interface:InterfaceGrp;
            }
            uses ipaddress:IpAddressV4Wrapper;
            uses ipaddress:IpAddressV6Wrapper;

            must '(count(current()/IpAddressV4) + count(current()/IpAddressV6)) &gt; 0' {
                error-message
                    "At least one IpAddressV4 or IpAddressV6 must exist.";
            }

            yexte:is-system-created;
            tailf:meta-data yexte:is-system-created;
        }
    }
}
