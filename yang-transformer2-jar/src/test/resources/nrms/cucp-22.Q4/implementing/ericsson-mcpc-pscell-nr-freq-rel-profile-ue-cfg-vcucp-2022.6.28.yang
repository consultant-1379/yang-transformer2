// Generated by eyang-preprocessor (1.22.0-48 2022-01-20 09:10:06 CET) on Jun 30, 2022, 8:31:39 AM
module ericsson-mcpc-pscell-nr-freq-rel-profile-ue-cfg-vcucp {
    yang-version 1.1;
    namespace urn:rdns:com:ericsson:oammodel:ericsson-mcpc-pscell-nr-freq-rel-profile-ue-cfg-vcucp;
    prefix mcpcpscellnrfreqrelprofuecfg;

    import tailf-common {
        prefix tailf;
    }
    import _3gpp-common-managed-element {
        prefix me3gpp;
    }
    import _3gpp-nr-nrm-gnbcucpfunction {
        prefix gnbcucp3gpp;
    }
    import _3gpp-common-top {
        prefix top3gpp;
    }
    import ericsson-yang-extensions {
        prefix yexte;
    }
    import ericsson-common-types-vcucp {
        prefix commontypes;
    }
    import ericsson-mcpc-vcucp {
        prefix mcpc;
    }
    import ericsson-mcpc-pscell-nr-freq-rel-profile-vcucp {
        prefix mcpcpscellnrfreqrelprofile;
    }

    organization
        "Ericsson AB";
    contact
        "Ericsson first line support via email";
    description
        "The module defines the McpcPSCellNrFreqRelProfileUeCfg data model for the Ericsson vCU-CP.

        Copyright (c) 2021-2022 Ericsson AB. All rights reserved.";

    revision 2022-06-28 {
        description
            "Removed module-status preliminary.";
        yexte:version 0;
        yexte:release 2;
        yexte:correction 0;
        reference
            "RFC 7950: The YANG 1.1 Data Modeling Language";
    }

    revision 2022-03-14 {
        description
            "Update description of McpcPSCellNrFreqRelProfileUeCfg.";
        yexte:version 0;
        yexte:release 1;
        yexte:correction 2;
        reference
            "RFC 7950: The YANG 1.1 Data Modeling Language";
    }

    revision 2021-11-05 {
        description
            "Update precondition for McpcPSCellNrFreqRelProfileUeCfg.";
        yexte:version 0;
        yexte:release 1;
        yexte:correction 1;
        reference
            "RFC 7950: The YANG 1.1 Data Modeling Language";
    }

    revision 2021-09-20 {
        description
            "Initial version of the McpcPSCellNrFreqRelProfileUeCfg model";
        yexte:version 0;
        yexte:release 1;
        yexte:correction 0;
        reference
            "RFC 7950: The YANG 1.1 Data Modeling Language";
    }

    grouping McpcPSCellNrFreqRelProfileUeCfgGrp {
        description
            "Represents the McpcPSCellNrFreqRelProfileUeCfg IOC.";

        leaf inhibitMeasForCellCandidate {
            description
                "Whether UE measurement to detect PSCell candidate on this frequency "+
                "is inhibited.";
            type boolean;
            default false;
            yexte:takes-effect
                "Next usage.";
            tailf:info 'Takes effect: Next usage, Whether UE measurement to detect PSCell candidate on this frequency is inhibited.';
        }

        container rsrpCandidateA5Offsets {
            description
              "Downlink RSRP A5 measurement offsets when searching for PSCell "+
              "candidate.";
            uses commontypes:ReportConfigA5RsrpOffsets;
            yexte:takes-effect
                "Next usage.";
            tailf:info 'Takes effect: Next usage, Downlink RSRP A5 measurement offsets when searching for PSCell candidate.';
        }
    }

    augment "/me3gpp:ManagedElement/gnbcucp3gpp:GNBCUCPFunction/mcpc:Mcpc/mcpcpscellnrfreqrelprofile:McpcPSCellNrFreqRelProfile" {

        list McpcPSCellNrFreqRelProfileUeCfg {
            description
                "Mobility control at poor coverage function for PSCell in "+
                "EN-DC, UE configuration group.

                Applies to UEs that use this cell as PSCell in EN-DC. "+
                "Attributes are used on NR frequency relation level.

                MO instance McpcPSCellNrFreqRelProfileUeCfg=Base is created "+
                "automatically when parent MO is created, unless created "+
                "manually in the same transaction as parent MO.

                The RDN of this MO must always be "+
                "McpcPSCellNrFreqRelProfileUeCfg=Base.";
            key id;
            max-elements 1;
            uses top3gpp:Top_Grp {
                refine id {
                    must '. = "Base"' {
                        error-message
                          "The RDN of this MO must always be McpcPSCellNrFreqRelProfileUeCfg=Base";
                    }
                }
            }
            container attributes {
                uses McpcPSCellNrFreqRelProfileUeCfgGrp;
                uses commontypes:UserLabelGrp;
            }
            yexte:precondition
                "McpcPSCellNrFreqRelProfileUeCfg=Base MO instance must not be deleted "+
                "unless parent MO is deleted.";
            tailf:info 'Precondition: McpcPSCellNrFreqRelProfileUeCfg=Base MO instance must not be deleted unless parent MO is deleted, Mobility control at poor coverage function for PSCell in EN-DC, UE configuration group. Applies to UEs that use this cell as PSCell in EN-DC. Attributes are used on NR frequency relation level. MO instance McpcPSCellNrFreqRelProfileUeCfg=Base is created automatically when parent MO is created, unless created manually in the same transaction as parent MO. The RDN of this MO must always be McpcPSCellNrFreqRelProfileUeCfg=Base.';
        }
    }
}
