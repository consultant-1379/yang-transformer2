// Generated by eyang-preprocessor (1.22.0-48 2022-01-20 09:10:06 CET) on Jun 30, 2022, 8:31:38 AM
module ericsson-intrafreqmcfreqrelprofileuecfg-vcucp {
    yang-version 1.1;
    namespace urn:rdns:com:ericsson:oammodel:ericsson-intrafreqmcfreqrelprofileuecfg-vcucp;
    prefix intrafreqmcfreqrelprofileuecfg;

    import tailf-common {
        prefix tailf;
    }
    import _3gpp-common-managed-element {
        prefix "me3gpp";
    }
    import _3gpp-nr-nrm-gnbcucpfunction {
        prefix "gnbcucp3gpp";
    }
    import _3gpp-common-top {
        prefix "top3gpp";
    }
    import ericsson-yang-extensions {
        prefix "yexte";
    }
    import ericsson-intrafreqmc-vcucp {
        prefix "intrafreqmc";
    }
    import ericsson-intrafreqmcfreqrelprofile-vcucp {
        prefix "intrafreqmcfreqrelprofile";
    }
    import ericsson-common-types-vcucp {
        prefix "commontypes";
    }

    organization
      "Ericsson AB";
    contact
      "Ericsson first line support via email";
    description
      "The module defines the IntraFreqMCFreqRelProfileUeCfg data model for the Ericsson vCU-CP.

       Copyright (c) 2021-2022 Ericsson AB. All rights reserved.";

    revision 2022-06-28 {
        description
            "Removed module-status preliminary.";
        yexte:version 0;
        yexte:release 3;
        yexte:correction 0;
        reference
            "RFC 7950: The YANG 1.1 Data Modeling Language";
    }

    revision 2022-03-14 {
        description
          "Update the description for the IntraFreqMCFreqRelProfileUeCfg model.
           Added the userLabel attribute.";
        yexte:version 0;
        yexte:release 2;
        yexte:correction 0;
        reference
          "RFC 7950: The YANG 1.1 Data Modeling Language";
    }

    revision 2021-11-05 {
        description
          "Initial version of the IntraFreqMCFreqRelProfileUeCfg model.";
        yexte:version 0;
        yexte:release 1;
        yexte:correction 0;
        reference
          "RFC 7950: The YANG 1.1 Data Modeling Language";
    }

    grouping IntraFreqMCFreqRelProfileUeCfgGrp {
        description
            "Represents the IntraFreqMCFreqRelProfileUeCfg IOC.";

        leaf rsrpSCellCoverageThrOffset {
            description
                "NR frequency relation-specific RSRP threshold offset value for Event "+
                "A1 and Event A2.

                Threshold offset used for detecting poor or good coverage in SCell.";
            type int32 {
                range "-30..30";
            }
            default 0;
            units dB;
            reference
                "3GPP TS 38.331";
            yexte:takes-effect
                "Next usage.";
            tailf:info 'Takes effect: Next usage, NR frequency relation-specific RSRP threshold offset value for Event A1 and Event A2. Threshold offset used for detecting poor or good coverage in SCell.';
        }

        leaf rsrqSCellCoverageThrOffset {
            description
                "NR frequency relation-specific RSRQ threshold offset value for Event "+
                "A1 and Event A2.

                Threshold offset used for detecting poor or good coverage in SCell.";
            type int32 {
                range "-300..300";
            }
            default 0;
            units "0.1 dB";
            must ". mod 5 = 0" {
                error-message
                "The value must set with resolution/step of 5";
            }
            reference
                "3GPP TS 38.331";
            yexte:takes-effect
                "Next usage.";
            tailf:info 'Takes effect: Next usage, NR frequency relation-specific RSRQ threshold offset value for Event A1 and Event A2. Threshold offset used for detecting poor or good coverage in SCell.';
        }
    }

    augment "/me3gpp:ManagedElement/gnbcucp3gpp:GNBCUCPFunction/intrafreqmc:IntraFreqMC/intrafreqmcfreqrelprofile:IntraFreqMCFreqRelProfile" {
        list IntraFreqMCFreqRelProfileUeCfg {
            description
                "Intra-frequency mobility control cell configuration profile "+
                "for UE configuration group.

                Applies to UEs that use cell as SpCell. Attributes are used on "+
                "NR frequency relation level.

                MO instance IntraFreqMCFreqRelProfileUeCfg=Base is created "+
                "automatically when parent MO is created, unless created "+
                "manually in the same transaction as parent MO.

                The RDN of this MO must always be "+
                "IntraFreqMCFreqRelProfileUeCfg=Base.";
            key id;
            max-elements 1;
            uses top3gpp:Top_Grp {
                refine id {
                    must '. = "Base"' {
                        error-message
                          "The RDN of this MO must always be IntraFreqMCFreqRelProfileUeCfg=Base";
                    }
                }
            }
            container attributes {
                uses IntraFreqMCFreqRelProfileUeCfgGrp;
                uses commontypes:UserLabelGrp;
            }
            yexte:precondition
                "IntraFreqMCFreqRelProfileUeCfg=Base MO instance must not be deleted "+
                "unless parent MO is deleted.";
            tailf:info 'Precondition: IntraFreqMCFreqRelProfileUeCfg=Base MO instance must not be deleted unless parent MO is deleted, Intra-frequency mobility control cell configuration profile for UE configuration group. Applies to UEs that use cell as SpCell. Attributes are used on NR frequency relation level. MO instance IntraFreqMCFreqRelProfileUeCfg=Base is created automatically when parent MO is created, unless created manually in the same transaction as parent MO. The RDN of this MO must always be IntraFreqMCFreqRelProfileUeCfg=Base.';
        }
    }
}
