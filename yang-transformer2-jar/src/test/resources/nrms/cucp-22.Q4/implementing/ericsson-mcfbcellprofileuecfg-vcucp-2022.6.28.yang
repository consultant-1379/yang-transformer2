// Generated by eyang-preprocessor (1.22.0-48 2022-01-20 09:10:06 CET) on Jun 30, 2022, 8:31:38 AM
module ericsson-mcfbcellprofileuecfg-vcucp {
    yang-version 1.1;
    namespace urn:rdns:com:ericsson:oammodel:ericsson-mcfbcellprofileuecfg-vcucp;
    prefix mcfbcellprofileuecfg;

    import tailf-common {
        prefix tailf;
    }
    import _3gpp-common-managed-element {
        prefix me3gpp;
    }
    import _3gpp-nr-nrm-gnbcucpfunction {
        prefix gnbcucp3gpp;
    }
    import _3gpp-common-top {
        prefix top3gpp;
    }
    import ericsson-mcfb-vcucp {
        prefix mcfb;
    }
    import ericsson-mcfbcellprofile-vcucp {
        prefix mcfbcellprofile;
    }
    import ericsson-yang-extensions {
        prefix yexte;
    }
    import ericsson-common-types-vcucp {
        prefix commontypes;
    }

    organization
      "Ericsson AB";
    contact
      "Ericsson first line support via email";
    description
      "The module defines the McfbCellProfileUeCfg data model for the Ericsson vCU-CP.

        Copyright (c) 2022 Ericsson AB. All rights reserved.";

    revision 2022-06-28 {
        description
            "Removed module-status preliminary.
             Removed preliminary status from McfbCellProfileUeCfg.";
        yexte:version 0;
        yexte:release 2;
        yexte:correction 0;
        reference
            "RFC 7950: The YANG 1.1 Data Modeling Language";
    }

    revision 2022-03-14 {
        description
          "Initial version of the McfbCellProfileUeCfg model.";
        yexte:version 0;
        yexte:release 1;
        yexte:correction 0;
        reference
          "RFC 7950: The YANG 1.1 Data Modeling Language";
    }

    grouping McfbCellProfileUeCfgGrp {
        description
            "Represents the McfbCellProfileUeCfg IOC.";

        leaf epsFallbackOperation {
            description
                "Policy for EPS fallback or Voice over NR (VoNR) for voice calls.";
            type commontypes:EpsFallbackOperationType;
            default FORCED;
            yexte:disturbances
                "Changing this attribute can cause loss of traffic.";
            yexte:takes-effect
                "Next usage.";
            tailf:info 'Takes effect: Next usage, Traffic Disturbance: Changing this attribute can cause loss of traffic, Policy for EPS fallback or Voice over NR (VoNR) for voice calls.';
        }

        leaf epsFallbackOperationEm {
            description
                "Policy for EPS fallback or Voice over NR (VoNR) for emergency calls.";
            type commontypes:EpsFbOperationTypeEm;
            default FORCED;
            yexte:disturbances
                "Changing this attribute can cause loss of traffic.";
            yexte:takes-effect
                "Next usage.";
            tailf:info 'Takes effect: Next usage, Traffic Disturbance: Changing this attribute can cause loss of traffic, Policy for EPS fallback or Voice over NR (VoNR) for emergency calls.';
        }

        leaf epsFbTargetSearchTimer {
            description
                "Length of time the gNodeB waits for reports from B1 measurement for "+
                "EPS fallback reasons.";
            type int32 {
                range "1..12000";
            }
            default 500;
            units ms;
            yexte:disturbances
                "Changing this attribute can cause loss of traffic.";
            yexte:takes-effect
                "Next usage.";
            tailf:info 'Takes effect: Next usage, Traffic Disturbance: Changing this attribute can cause loss of traffic, Length of time the gNodeB waits for reports from B1 measurement for EPS fallback reasons.';
        }

        leaf-list prefUeGroupList {
            description
                "Preference UE group list.

                 List of preference UE group identifiers.

                 If empty, the MO instance matches preference UE group identifiers not "+
                "defined in prefUeGroupList of any other MO instances under parent MO "+
                "instance.";
            type int32 {
                range "1..255";
            }
            max-elements 8;
            ordered-by user;
            yexte:dependencies
                "Combinations of pair of UE group identifier in ueGroupList and "+
                "preference UE group identifier in prefUeGroupList must be unique "+
                "among McfbCellProfileUeCfg instances under same parent "+
                "McfbCellProfile instance.

                 For all preference UE group identifiers in prefUeGroupList "+
                "attributes under same parent McfbCellProfile MO instance, exactly "+
                "one McfbCellProfileUeCfg MO instance must exist that combines the "+
                "given preference UE group identifier with an empty ueGroupList.";
            yexte:disturbances
                "Changing this attribute can cause loss of traffic.";
            yexte:takes-effect
                "Next usage.";
            must "count(../../../McfbCellProfileUeCfg/attributes[prefUeGroupList = current() and count(ueGroupList) = 0]) = 1" {
                error-message
                   "Exactly one McfbCellProfileUeCfg instance under an McfbCellProfile must combine a specific preference UE group identifier in attribute prefUeGroupList with an empty ueGroupList.";
            }
            tailf:info 'Takes effect: Next usage, Traffic Disturbance: Changing this attribute can cause loss of traffic, Dependencies: Combinations of pair of UE group identifier in ueGroupList and preference UE group identifier in prefUeGroupList must be unique among McfbCellProfileUeCfg instances under same parent McfbCellProfile instance.

                 For all preference UE group identifiers in prefUeGroupList attributes under same parent McfbCellProfile MO instance, exactly one McfbCellProfileUeCfg MO instance must exist that combines the given preference UE group identifier with an empty ueGroupList, Preference UE group list. List of preference UE group identifiers. If empty, the MO instance matches preference UE group identifiers not defined in prefUeGroupList of any other MO instances under parent MO instance.';
        }

        leaf rejectVoiceIncHoAtEpsFb {
            description
                "Whether policy for EPS fallback is considered for rejecting incoming "+
                "handover with voice service.

                 If true, handover fails if voice service is not allowed when "+
                "epsFallbackOperation is set to one of below values:
                 - FORCED
                 - FORCED_MEAS_RWR
                 - FORCED_MEAS_IRAT_HO

                 For emergency service EPS fallback emergency is considered.

                 If true, handover fails if emergency service is not allowed when "+
                "epsFallbackOperationEm set to FORCED.

                 If false, voice and emergency services are always allowed at incoming "+
                "handover procedure.

                 For initial call setup procedure, EPS fallback operation or EPS "+
                "fallback emergency operation policy is applied, "+
                "rejectVoiceIncHoAtEpsFb has no impact.";
            type boolean;
            default false;
            yexte:disturbances
                "Changing this attribute can cause loss of traffic.";
            yexte:takes-effect
                "New connection";
            tailf:info 'Takes effect: New connection, Traffic Disturbance: Changing this attribute can cause loss of traffic, Whether policy for EPS fallback is considered for rejecting incoming handover with voice service. If true, handover fails if voice service is not allowed when epsFallbackOperation is set to one of below values: - FORCED - FORCED_MEAS_RWR - FORCED_MEAS_IRAT_HO For emergency service EPS fallback emergency is considered. If true, handover fails if emergency service is not allowed when epsFallbackOperationEm set to FORCED. If false, voice and emergency services are always allowed at incoming handover procedure. For initial call setup procedure, EPS fallback operation or EPS fallback emergency operation policy is applied, rejectVoiceIncHoAtEpsFb has no impact.';
        }

        container rsrpCellCandidate {
            description
                "RSRP B1 measurement report criteria when searching for E-UTRAN cell " +
                "candidate.";
            uses commontypes:ReportConfigB1Rsrp;
            yexte:disturbances
                "Changing this attribute can cause loss of traffic.";
            yexte:takes-effect
                "Next usage.";
            tailf:info 'Takes effect: Next usage, Traffic Disturbance: Changing this attribute can cause loss of traffic, RSRP B1 measurement report criteria when searching for E-UTRAN cell candidate.';
        }

        container rsrpCriticalCoverage {
            description
                "RSRP A2 measurement report criteria for detecting critical coverage.";
            uses commontypes:ReportConfigA1A2Rsrp;
            yexte:disturbances
                "Changing this attribute can cause loss of traffic.";
            yexte:takes-effect
                "Next usage.";
            tailf:info 'Takes effect: Next usage, Traffic Disturbance: Changing this attribute can cause loss of traffic, RSRP A2 measurement report criteria for detecting critical coverage.';
        }

        container rsrqCellCandidate {
            description
                "RSRQ B1 measurement report criteria when searching for E-UTRAN cell " +
                "candidate.";
            uses commontypes:ReportConfigB1Rsrq;
            yexte:disturbances
                "Changing this attribute can cause loss of traffic.";
            yexte:takes-effect
                "Next usage.";
            tailf:info 'Takes effect: Next usage, Traffic Disturbance: Changing this attribute can cause loss of traffic, RSRQ B1 measurement report criteria when searching for E-UTRAN cell candidate.';
        }

        container rsrqCriticalCoverage {
            description
                "RSRQ A2 measurement report criteria for detecting critical coverage.";
            uses commontypes:ReportConfigA1A2Rsrq;
            yexte:disturbances
                "Changing this attribute can cause loss of traffic.";
            yexte:takes-effect
                "Next usage.";
            tailf:info 'Takes effect: Next usage, Traffic Disturbance: Changing this attribute can cause loss of traffic, RSRQ A2 measurement report criteria for detecting critical coverage.';
        }

        leaf triggerQuantity {
            description
                "Quantity that triggers the event B1 and A2.";
            type commontypes:TriggerQuantity;
            default RSRP;
            yexte:disturbances
                "Changing this attribute can cause loss of traffic.";
            yexte:takes-effect
                "Next usage.";
            tailf:info 'Takes effect: Next usage, Traffic Disturbance: Changing this attribute can cause loss of traffic, Quantity that triggers the event B1 and A2.';
        }

        leaf-list ueConfGroupList {
            description
                "UE configuration group list.

                 List of UE configuration group identifiers.

                 If empty, the MO instance matches all UE configuration group "+
                "identifiers.

                 Which UE configuration group type that is applied is defined by "+
                "attribute ueConfGroupType in parent MO class instance.";
            type int32 {
                range "1..255";
            }
            max-elements 16;
            ordered-by user;
            yexte:dependencies
                "A given UE configuration group identifier can be defined in only one "+
                "ueConfGroupList among McfbCellProfileUeCfg instances under same "+
                "parent McfbCellProfile instance.";
            yexte:disturbances
                "Changing this attribute can cause loss of traffic.";
            yexte:takes-effect
                "Next usage.";
            must "count(../../../McfbCellProfileUeCfg/attributes[ueConfGroupList = current()]) &lt;= 1" {
                error-message
                    "Only one McfbCellProfileUeCfg instance under an McfbCellProfile can include a specific ueConfGroupId in attribute ueConfGroupList.";
            }
            tailf:info 'Takes effect: Next usage, Traffic Disturbance: Changing this attribute can cause loss of traffic, Dependencies: A given UE configuration group identifier can be defined in only one ueConfGroupList among McfbCellProfileUeCfg instances under same parent McfbCellProfile instance, UE configuration group list. List of UE configuration group identifiers. If empty, the MO instance matches all UE configuration group identifiers. Which UE configuration group type that is applied is defined by attribute ueConfGroupType in parent MO class instance.';
        }

        leaf-list ueGroupList {
            description
                "UE group list.

                 List of UE group identifiers.

                 If empty, the MO instance matches all UE group identifiers.";
            type int32 {
                range "1..255";
            }
            max-elements 16;
            ordered-by user;
            yexte:dependencies
                "Combinations of pair of UE group identifier in ueGroupList and "+
                "preference UE group identifier in prefUeGroupList must be unique "+
                "among McfbCellProfileUeCfg instances under same parent "+
                "McfbCellProfile instance.

                 Combination of a UE group identifier in UeGroupList and empty "+
                "prefUeGroupList must be unique among McfbCellProfileUeCfg instances "+
                "under same parent McfbCellProfile instance.";
            yexte:disturbances
                "Changing this attribute can cause loss of traffic.";
            yexte:takes-effect
                "Next usage.";
            must "count(../prefUeGroupList) &gt; 0 or
                  count(../../../McfbCellProfileUeCfg/attributes[ueGroupList = current() and count(prefUeGroupList) = 0]) &lt;= 1" {
                error-message
                    "Only one McfbCellProfileUeCfg instance under an McfbCellProfile can combine a specific UE group identifier in attribute ueGroupList with an empty prefUeGroupList.";
            }
            tailf:info 'Takes effect: Next usage, Traffic Disturbance: Changing this attribute can cause loss of traffic, Dependencies: Combinations of pair of UE group identifier in ueGroupList and preference UE group identifier in prefUeGroupList must be unique among McfbCellProfileUeCfg instances under same parent McfbCellProfile instance.

                 Combination of a UE group identifier in UeGroupList and empty prefUeGroupList must be unique among McfbCellProfileUeCfg instances under same parent McfbCellProfile instance, UE group list. List of UE group identifiers. If empty, the MO instance matches all UE group identifiers.';
        }
    }

    augment "/me3gpp:ManagedElement/gnbcucp3gpp:GNBCUCPFunction/mcfb:Mcfb/mcfbcellprofile:McfbCellProfile" {

        list McfbCellProfileUeCfg {
            description
              "Mobility Control Fallback Cell Profile, UE configuration group.

               Applies to UEs that use cell as PCell. Attributes are used on "+
              "cell level.

               MO instance McfbCellProfileUeCfg=Base is created automatically "+
              "when parent MO is created, unless created manually in the same "+
              "transaction as parent MO.

               Attributes prefUeGroupList, ueGroupList and ueConfGroupList "+
              "must be empty in instance McfbCellProfileUeCfg=Base but cannot "+
              "all be empty in other instances of McfbCellProfileUeCfg under "+
              "same parent McfbCellProfile.";
            yexte:precondition
              "McfbCellProfileUeCfg=Base MO instance can only be created in "+
              "the same transaction as parent MO and must not be deleted unless "+
              "parent MO is deleted.

               Maximum 31 McfbCellProfileUeCfg instances, with RDN different "+
              "from Base, can be created.";
            key id;
            max-elements 32;
            uses top3gpp:Top_Grp;
            container attributes {
                uses McfbCellProfileUeCfgGrp;
                uses commontypes:UserLabelGrp;
            }

            must "count(../McfbCellProfileUeCfg) &lt; 32 or
                  count(../McfbCellProfileUeCfg/id[. = 'Base']) = 1" {
                error-message
                    "Maximum 31 McfbCellProfileUeCfg instances under an McfbCellProfile can be created with RDN different from Base.";
            }

            must "id != 'Base' or
                  (count(attributes/prefUeGroupList) = 0 and count(attributes/ueGroupList) = 0 and count(attributes/ueConfGroupList) = 0)" {
                error-message
                    "prefUeGroupList, ueGroupList and ueConfGroupList must be empty in the McfbCellProfileUeCfg=Base instance.";
            }

            must "id = 'Base' or
                  not(count(attributes/prefUeGroupList) = 0 and count(attributes/ueGroupList) = 0 and count(attributes/ueConfGroupList) = 0)" {
                error-message
                    "prefUeGroupList, ueGroupList and ueConfGroupList can only be empty in the McfbCellProfileUeCfg=Base instance.";
            }

            must "count(../McfbCellProfileUeCfg/attributes[prefUeGroupList = current()/attributes/prefUeGroupList and ueGroupList = current()/attributes/ueGroupList] ) &lt;= 1" {
                error-message
                    "The combinations of a pair of UE group identifier in ueGroupList and preference UE group identifier in prefUeGroupList must be unique among McfbCellProfileUeCfg under an McfbCellProfile.";
            }
            tailf:info 'Precondition: McfbCellProfileUeCfg=Base MO instance can only be created in the same transaction as parent MO and must not be deleted unless parent MO is deleted.

               Maximum 31 McfbCellProfileUeCfg instances, with RDN different from Base, can be created, Mobility Control Fallback Cell Profile, UE configuration group. Applies to UEs that use cell as PCell. Attributes are used on cell level. MO instance McfbCellProfileUeCfg=Base is created automatically when parent MO is created, unless created manually in the same transaction as parent MO. Attributes prefUeGroupList, ueGroupList and ueConfGroupList must be empty in instance McfbCellProfileUeCfg=Base but cannot all be empty in other instances of McfbCellProfileUeCfg under same parent McfbCellProfile.';
        }
    }
}
