// Generated by eyang-preprocessor (1.22.0-48 2022-01-20 09:10:06 CET) on Jun 30, 2022, 8:31:41 AM
module ericsson-nrdc-mn-cell-profile-vcucp {
    yang-version 1.1;
    namespace "urn:rdns:com:ericsson:oammodel:ericsson-nrdc-mn-cell-profile-vcucp";
    prefix nrdcmncellprofile;

    import tailf-common {
        prefix tailf;
    }
    import _3gpp-common-managed-element {
        prefix "me3gpp";
    }
    import _3gpp-nr-nrm-gnbcucpfunction {
        prefix "gnbcucp3gpp";
    }
    import _3gpp-common-top {
        prefix "top3gpp";
    }
    import ericsson-yang-extensions {
        prefix "yexte";
    }
    import ericsson-nrdc-control-vcucp {
        prefix "nrdccontrol";
    }

    organization
        "Ericsson AB";
    contact
        "Ericsson first line support via email";
    description
        "The module defines the NrdcMnCellProfile data model for the Ericsson vCU-CP.

        Copyright (c) 2022 Ericsson AB. All rights reserved.";

    revision 2022-06-28 {
        description
            "Removed module-status preliminary.
             Removed preliminary status from NrdcMnCellProfile.";
        yexte:version 0;
        yexte:release 2;
        yexte:correction 0;
        reference
            "RFC 7950: The YANG 1.1 Data Modeling Language";
    }

    revision 2022-03-14 {
        description
            "Initial version of the NrdcMnCellProfile model.";
        yexte:version 0;
        yexte:release 1;
        yexte:correction 0;
        reference
            "RFC 7950: The YANG 1.1 Data Modeling Language";
    }

    augment "/me3gpp:ManagedElement/gnbcucp3gpp:GNBCUCPFunction/nrdccontrol:NrdcControl" {
        list NrdcMnCellProfile {
            description
              "NR-NR Dual Connectivity control for PCell in Master Node.

              Applies to UEs which use the cell as PCell in Master Node. "+
              "Attributes are used on cell level.

              NrdcMnCellProfile=Default MO instance is created automatically "+
              "when parent MO is created, unless created manually in the same "+
              "transaction as parent MO.

              If NRCellCU::nrdcMnCellProfileRef is non-empty, attributes from "+
              "referred MO instance are used.
              If NRCellCU::nrdcMnCellProfileRef is empty, attribute default "+
              "values according to MO class definition are used.";
            yexte:precondition
              "NrdcMnCellProfile=Default MO instance can only be created in "+
              "the same transaction as parent MO and must not be deleted unless "+
              "parent MO is deleted. Other instances can be created and deleted "+
              "manually.";
            key id;
            max-elements 8;
            uses top3gpp:Top_Grp;
            tailf:info 'Precondition: NrdcMnCellProfile=Default MO instance can only be created in the same transaction as parent MO and must not be deleted unless parent MO is deleted. Other instances can be created and deleted manually, NR-NR Dual Connectivity control for PCell in Master Node. Applies to UEs which use the cell as PCell in Master Node. Attributes are used on cell level. NrdcMnCellProfile=Default MO instance is created automatically when parent MO is created, unless created manually in the same transaction as parent MO. If NRCellCU::nrdcMnCellProfileRef is non-empty, attributes from referred MO instance are used. If NRCellCU::nrdcMnCellProfileRef is empty, attribute default values according to MO class definition are used.';
        }
    }
}
