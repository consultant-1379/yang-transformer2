// Generated by eyang-preprocessor (1.22.0-48 2022-01-20 09:10:06 CET) on Jun 30, 2022, 8:31:36 AM
module ericsson-eutrancellrelation-ext-vcucp {
    yang-version 1.1;
    namespace urn:rdns:com:ericsson:oammodel:ericsson-eutrancellrelation-ext-vcucp;
    prefix eutrancellrel3gppext;

    import tailf-common {
        prefix tailf;
    }
    import _3gpp-common-managed-element {
        prefix me3gpp;
    }
    import _3gpp-nr-nrm-gnbcucpfunction {
        prefix gnbcucp3gpp;
    }
    import _3gpp-nr-nrm-nrcellcu {
        prefix nrcellcu3gpp;
    }
    import _3gpp-nr-nrm-eutrancellrelation {
        prefix eutrancellrel3gpp;
    }
    import ericsson-common-types-vcucp {
        prefix commontypes;
    }
    import ericsson-externalenbfunction-vcucp {
        prefix extenb;
    }
    import ericsson-externaleutrancell-vcucp {
        prefix exteutrancell;
    }
    import ericsson-eutranetwork-vcucp {
        prefix "eutranet";
    }
    import ericsson-yang-extensions {
        prefix yexte;
    }

    organization
        "Ericsson AB";
    contact
        "Ericsson first line support via email";
    description
        "The module defines the EUtranCellRelation data model extensions for the Ericsson vCU-CP.

        Copyright (c) 2021-2022 Ericsson AB. All rights reserved.";

    revision 2022-06-28 {
        description
            "Removed module-status preliminary.";
        yexte:version 2;
        yexte:release 1;
        yexte:correction 0;
        reference
            "RFC 7950: The YANG 1.1 Data Modeling Language";
    }

    revision 2022-03-14 {
        description
            "Updated description for isRemoveAllowed to reflect that the attribute is an enum.";
        yexte:version 2;
        yexte:release 0;
        yexte:correction 1;
        reference
            "RFC 7950: The YANG 1.1 Data Modeling Language";
    }

    revision 2021-11-05 {
        description
            "Mark createdBy as obsolete.
            Updated description on adjacentCell must rule";
        yexte:version 2;
        yexte:release 0;
        yexte:correction 0;
        reference
            "RFC 7950: The YANG 1.1 Data Modeling Language";
    }

    revision 2021-05-24 {
        description
            "Add must statements related to essEnabled and adjacentCell.";
        yexte:version 1;
        yexte:release 3;
        yexte:correction 1;
        reference
            "RFC 7950: The YANG 1.1 Data Modeling Language";
    }

    revision 2021-05-06 {
        description
            "Remove is-system-created and restricted extensions from configurable attributes.";
        yexte:version 1;
        yexte:release 3;
        yexte:correction 0;
        reference
            "RFC 7950: The YANG 1.1 Data Modeling Language";
    }

    revision 2021-03-30 {
        description
            "Add Ericsson descriptions and tags to attributes.
             The attribute adjacentCell should now refer to an ExternalEUtranCell MO instead of
              an ExternalEUtranCellFDD/TDD.";
        yexte:version 1;
        yexte:release 2;
        yexte:correction 0;
        reference
            "RFC 7950: The YANG 1.1 Data Modeling Language";
    }

    revision 2021-03-24 {
        description
            "Correct must statement for MO reference.";
        yexte:version 1;
        yexte:release 1;
        yexte:correction 1;
        reference
            "RFC 7950: The YANG 1.1 Data Modeling Language";
    }

    revision 2021-03-19 {
        description
            "Parity with ECIM R1A79.";
        yexte:version 1;
        yexte:release 1;
        yexte:correction 0;
        reference
            "RFC 7950: The YANG 1.1 Data Modeling Language";
    }

    revision 2021-01-20 {
        description
            "Add extensions is-system-created and restricted.";
        yexte:version 1;
        yexte:release 0;
        yexte:correction 0;
        reference
            "RFC 7950: The YANG 1.1 Data Modeling Language";
    }

    revision 2021-01-11 {
        description
            "Deviations on _3gpp-nr-nrm-eutrancellrelation.";
        yexte:version 0;
        yexte:release 1;
        yexte:correction 0;
        reference
            "RFC 7950: The YANG 1.1 Data Modeling Language";
    }

    deviation /me3gpp:ManagedElement/gnbcucp3gpp:GNBCUCPFunction/nrcellcu3gpp:NRCellCU/eutrancellrel3gpp:EUtranCellRelation/eutrancellrel3gpp:attributes/eutrancellrel3gpp:cellIndividualOffset {
        deviate add {
            default 0;
            yexte:updated-description
                "Offset value for neighbor E-UTRAN cell.

                Used when UE is in connected mode.";
            yexte:takes-effect
                "Next usage.";
        }
    }

    deviation /me3gpp:ManagedElement/gnbcucp3gpp:GNBCUCPFunction/nrcellcu3gpp:NRCellCU/eutrancellrel3gpp:EUtranCellRelation/eutrancellrel3gpp:attributes/eutrancellrel3gpp:isHOAllowed {
        // Replace deviate for removing the Mandatory statement is deliberately added here instead of the -ext file since the YANG validator gives an error if this is separated from the default value statement.
        deviate replace {
            mandatory false;
        }
        deviate add {
            default "YES";
            yexte:updated-description
                "Whether handover between cells in this relation is allowed.";
            yexte:takes-effect
                "Next usage.";
        }
    }

    deviation /me3gpp:ManagedElement/gnbcucp3gpp:GNBCUCPFunction/nrcellcu3gpp:NRCellCU/eutrancellrel3gpp:EUtranCellRelation/eutrancellrel3gpp:attributes/eutrancellrel3gpp:adjacentCell {
        deviate add {
            must "re-match(current(), 'ManagedElement=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,GNBCUCPFunction=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,EUtraNetwork=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,ExternalENBFunction=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,ExternalEUtranCell=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?') and
                  re-match(current(), concat('ManagedElement=', ../../../../../me3gpp:id, ',.*')) and
                  re-match(current(), concat('.*GNBCUCPFunction=', ../../../../gnbcucp3gpp:id, ',.*')) and
                  count(../../../../eutranet:EUtraNetwork[re-match(current(), concat('.*EUtraNetwork=', eutranet:id, ',.*'))]/extenb:ExternalENBFunction[re-match(current(), concat('.*ExternalENBFunction=', extenb:id, ',.*'))]/exteutrancell:ExternalEUtranCell[re-match(current(), concat('.*ExternalEUtranCell=', exteutrancell:id))]) &gt; 0" {
                description
                    "The reference must point at a ExternalEUtranCell entry.

                    An example of a valid value is
                    ManagedElement=1,GNBCUCPFunction=1,EUtraNetwork=1,ExternalENBFunction=1,ExternalEUtranCell=1";
                error-message
                    "adjacentCell must refer to an ExternalEUtranCell under the same GNBCUCPFunction.";
            }

            must "count(../../../eutrancellrel3gpp:EUtranCellRelation/eutrancellrel3gpp:attributes/eutrancellrel3gpp:adjacentCell[current() = .]) = 1" {
                error-message
                    "Must be unique for all EUtranCellRelation under the same NRCellCU.";
            }

            yexte:updated-description
                "Reference to an instance of ExternalEUtranCell MO.";
            yexte:dependencies
                "Must be unique for EUtranCellRelation MO instances under an NRCellCU.
                Must be unique for all EUtranCellRelation MO instances with "+
                "attribute essEnabled value true, under all NRCellCU instances.";
        }
    }

    deviation /me3gpp:ManagedElement/gnbcucp3gpp:GNBCUCPFunction/nrcellcu3gpp:NRCellCU/eutrancellrel3gpp:EUtranCellRelation/eutrancellrel3gpp:attributes/eutrancellrel3gpp:isRemoveAllowed {
        // Replace deviate for removing the Mandatory statement is deliberately added here instead of the -ext file since the YANG validator gives an error if this is separated from the default value statement (not present for this attribute).
        deviate replace {
            mandatory false;
        }
        deviate add {
            yexte:updated-description
                "If ANR function is allowed to remove this object.

                The setting does not restrict operator removal of object. Objects "+
                "created by ANR have this parameter set to YES initially.

                If empty, this attribute is handled as if it is NO.";
            yexte:initial-value "NO";
        }
    }

    deviation /me3gpp:ManagedElement/gnbcucp3gpp:GNBCUCPFunction/nrcellcu3gpp:NRCellCU/eutrancellrel3gpp:EUtranCellRelation {
        deviate add {
            max-elements 128;
            yexte:updated-description
                "Handover relationship between NR cell and a neighboring E-UTRAN "+
                "cell.";
        }
    }

    grouping EssCellScPair {
        description
            "The eNodeB-gNodeB Sector Carrier pair used for ESS operation.";

        leaf eNBessLocalScId {
            description
                "The eNodeB Local SectorCarrier ID.";
            type int32 {
                range "0..99999";
            }
        }

        leaf essScPairId {
            description
                "ESS SectorCarrier Pair ID.";
            type int64 {
                range "0..9223372036854775807";
            }
        }

        leaf gNBessLocalScId {
            description
                "The gNodeB Local SectorCarrier ID.";
            type int32 {
                range "0..99999";
            }
        }
    }

    grouping EUtranCellRelationVCUCPGrp {
        description "Ericsson extensions to the 3gpp EUtranCellRelation.";
        reference "Ericsson documentation";

        leaf createdBy {
            description
                "Creator of MO.

                Can be one of following:
                - ANR function.
                - Operator.
                - X2.";
            config false;
            type commontypes:CreatedByGutran;
            status obsolete {
                yexte:status-information
                "Since 21.Q2. Planned to be removed.";
            }
            tailf:info 'Status Info: Since 21.Q2. Planned to be removed, Obsolete, Creator of MO. Can be one of following: - ANR function. - Operator. - X2.';
        }

        list essCellScPairs {
            key "eNBessLocalScId essScPairId gNBessLocalScId";
            max-elements 14;
            description
                "The eNodeB-gNodeB Sector Carrier pairs used in cell for ESS "+
                "operation.";
            config false;
            uses EssCellScPair;
        }

        leaf essEnabled {
            description
              "ESS service enabled between cells in this relation.

               Only one EUtranCellRelation under an NRCellCU can be essEnabled.";

            must "count(../../../eutrancellrel3gpp:EUtranCellRelation/eutrancellrel3gpp:attributes/eutrancellrel3gppext:essEnabled[. = 'true']) &lt; 2" {
                error-message
                  "Only one EUtranCellRelation under an NRCellCU can be essEnabled.";
            }
            must "(current() = 'true' and
                    count(../../../../nrcellcu3gpp:NRCellCU/eutrancellrel3gpp:EUtranCellRelation/eutrancellrel3gpp:attributes[eutrancellrel3gppext:essEnabled = 'true' and eutrancellrel3gpp:adjacentCell = current()/../eutrancellrel3gpp:adjacentCell]) &lt; 2)
                  or current() = 'false'" {
                error-message
                  "adjacentCell must be unique for all EUtranCellRelation with "
                + "essEnabled=true under the same GNBCUCPFunction.";
            }
            type boolean;
            default false;
            yexte:takes-effect
                "Next cell unlock";
            tailf:info 'Takes effect: Next cell unlock, ESS service enabled between cells in this relation. Only one EUtranCellRelation under an NRCellCU can be essEnabled.';
        }
    }

    augment "/me3gpp:ManagedElement/gnbcucp3gpp:GNBCUCPFunction/nrcellcu3gpp:NRCellCU/eutrancellrel3gpp:EUtranCellRelation/eutrancellrel3gpp:attributes" {
        description "Adds Ericsson attributes to 3gpp EUtranCellRelation.";
        uses EUtranCellRelationVCUCPGrp;
    }
}
