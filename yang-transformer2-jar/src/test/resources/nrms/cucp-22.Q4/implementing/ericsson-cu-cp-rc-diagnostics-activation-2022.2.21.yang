module ericsson-cu-cp-rc-diagnostics-activation {
    yang-version 1.1;
    namespace urn:rdns:com:ericsson:oammodel:ericsson-cu-cp-rc-diagnostics-activation;
    prefix rcdiagact;
    import ericsson-yang-extensions {
        prefix yexte;
    }
    import ericsson-common-types-diagnostics {
        prefix commontypesdiag;
    }
    import ericsson-cu-cp-rc-diagnostics {
        prefix rcdiag;
    }
    organization
      'Ericsson AB';
    contact
      'Ericsson first line support via email';
    description
      'Diagnostics action:activate for RC Service

       Copyright (c) 2022 Ericsson AB. All rights reserved';
    revision 2022-02-21 {
        description
        'Initial revision';
        yexte:version 1;
        yexte:release 0;
        yexte:correction 0;
    }

    yexte:module-status preliminary;

    augment "/rcdiag:rc-diagnostics" {
        uses commontypesdiag:activation-action;
    }
}
