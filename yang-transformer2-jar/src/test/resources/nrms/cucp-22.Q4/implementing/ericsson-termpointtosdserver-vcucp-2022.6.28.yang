// Generated by eyang-preprocessor (1.22.0-48 2022-01-20 09:10:06 CET) on Jun 30, 2022, 8:31:44 AM
module ericsson-termpointtosdserver-vcucp {
    yang-version 1.1;
    namespace urn:rdns:com:ericsson:oammodel:ericsson-termpointtosdserver-vcucp;
    prefix tptosdservervcucp;

    import tailf-common {
        prefix tailf;
    }
    import _3gpp-common-managed-element {
        prefix me3gpp;
    }
    import _3gpp-common-top {
        prefix top3gpp;
    }
    import ericsson-yang-extensions {
        prefix yexte;
    }
    import ietf-inet-types {
        prefix inet;
    }
    import _3gpp-common-yang-types {
        prefix types3gpp;
    }
    import ericsson-yang-types {
        prefix "typese";
    }
    import _3gpp-nr-nrm-gnbcucpfunction {
        prefix gnbcucp3gpp;
    }
    import ericsson-notifications {
        prefix notife;
    }

    organization
        "Ericsson AB";
    contact
        "Ericsson first line support via email";
    description
        "The module defines the TermPointToSdServer Instance data model for the Ericsson vCU-CP.

         Copyright (c) 2022 Ericsson AB. All rights reserved.";

    revision 2022-06-28 {
        description
            "Removed module-status preliminary.";
        yexte:version 1;
        yexte:release 1;
        yexte:correction 0;
        reference
            "RFC 7950: The YANG 1.1 Data Modeling Language";
    }

    revision 2022-03-30 {
        description
            "Change availabilityStatus from leaf to leaf-list. Add config false in TermPointToSdServer.";
        yexte:version 1;
        yexte:release 0;
        yexte:correction 0;
        reference
            "RFC 7950: The YANG 1.1 Data Modeling Language";
    }

    revision 2022-03-08 {
        description
            "Initial version of the TermPointToSdServer Instance model.";
        yexte:version 0;
        yexte:release 1;
        yexte:correction 0;
        reference
            "RFC 7950: The YANG 1.1 Data Modeling Language";
    }

    grouping TermPointToSdServerGrp {
        leaf host {
            type inet:host;
            description "IP address or FQDN of the service discovery server.";
            config false;
        }

        leaf port {
            type inet:port-number;
            description "Port number used for the service discovery server.";
            config false;
        }

        leaf operationalState {
            description
                "The operational state";
            type types3gpp:OperationalState;
            config false;
            reference "ITU-T Rec. X.731";
        }

        leaf-list availabilityStatus {
            description
               "The availability status.";
            type typese:avail-status;
            config false;
            notife:notifiable-state-data true;
            reference
               "ITU-T Rec. X.731";
            tailf:meta-data notife:notifiable-state-data {
                tailf:meta-value true;
            }
        }

        description "Represents a TermPointToSdServer instance.";
    }

    augment "/me3gpp:ManagedElement/gnbcucp3gpp:GNBCUCPFunction" {
        list TermPointToSdServer {
            description
                "Represents a TermPointToSdServer instance.";
            key id;
            uses top3gpp:Top_Grp;
            config false;
            container attributes {
                uses TermPointToSdServerGrp;
            }
        }
    }
}
