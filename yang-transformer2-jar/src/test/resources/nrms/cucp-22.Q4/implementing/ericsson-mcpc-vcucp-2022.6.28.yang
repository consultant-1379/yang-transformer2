// Generated by eyang-preprocessor (1.22.0-48 2022-01-20 09:10:06 CET) on Jun 30, 2022, 8:31:39 AM
module ericsson-mcpc-vcucp {
    yang-version 1.1;
    namespace urn:rdns:com:ericsson:oammodel:ericsson-mcpc-vcucp;
    prefix mcpc;

    import tailf-common {
        prefix tailf;
    }
    import _3gpp-common-managed-element {
        prefix me3gpp;
    }
    import _3gpp-nr-nrm-gnbcucpfunction {
        prefix gnbcucp3gpp;
    }
    import _3gpp-common-top {
        prefix top3gpp;
    }
    import ericsson-yang-extensions {
        prefix yexte;
    }

    organization
        "Ericsson AB";
    contact
        "Ericsson first line support via email";
    description
        "The module defines the Mcpc data model for the Ericsson vCU-CP.

        Copyright (c) 2021-2022 Ericsson AB. All rights reserved.";

    revision 2022-06-28 {
        description
            "Removed module-status preliminary.";
        yexte:version 0;
        yexte:release 2;
        yexte:correction 0;
        reference
            "RFC 7950: The YANG 1.1 Data Modeling Language";
    }

    revision 2022-03-14 {
        description
            "Update description of Mcpc list.";
        yexte:version 0;
        yexte:release 1;
        yexte:correction 4;
        reference
            "RFC 7950: The YANG 1.1 Data Modeling Language";
    }

    revision 2021-11-05 {
        description
            "Update precondition for the Mcpc list.";
        yexte:version 0;
        yexte:release 1;
        yexte:correction 3;
        reference
            "RFC 7950: The YANG 1.1 Data Modeling Language";
    }

    revision 2021-09-20 {
        description
            "Changed description and added precondition for the Mcpc list.";
        yexte:version 0;
        yexte:release 1;
        yexte:correction 2;
        reference
            "RFC 7950: The YANG 1.1 Data Modeling Language";
    }

    revision 2021-06-08 {
        description
            "Changed error message for a must statement.";
        yexte:version 0;
        yexte:release 1;
        yexte:correction 1;
        reference
            "RFC 7950: The YANG 1.1 Data Modeling Language";
    }

    revision 2021-04-20 {
        description
            "Initial version of the Mcpc model";
        yexte:version 0;
        yexte:release 1;
        yexte:correction 0;
        reference
            "RFC 7950: The YANG 1.1 Data Modeling Language";
    }

    augment "/me3gpp:ManagedElement/gnbcucp3gpp:GNBCUCPFunction" {

        list Mcpc {
            description
                "Configuration of mobility control at poor coverage function and "+
                "container for MCPC profiles.

                MO instance Mcpc=1 is created automatically when parent MO is "+
                "created, unless created manually in the same transaction as parent MO.

                The RDN of this MO must always be Mcpc=1.";
            key id;
            max-elements 1;
            uses top3gpp:Top_Grp {
                refine id {
                    must '. = "1"' {
                        error-message
                          "The RDN of this MO must always be Mcpc=1";
                    }
                }
            }
            yexte:precondition
                "Mcpc=1 MO instance must not be deleted unless parent MO is deleted.";
            tailf:info 'Precondition: Mcpc=1 MO instance must not be deleted unless parent MO is deleted, Configuration of mobility control at poor coverage function and container for MCPC profiles. MO instance Mcpc=1 is created automatically when parent MO is created, unless created manually in the same transaction as parent MO. The RDN of this MO must always be Mcpc=1.';
        }
    }
}
