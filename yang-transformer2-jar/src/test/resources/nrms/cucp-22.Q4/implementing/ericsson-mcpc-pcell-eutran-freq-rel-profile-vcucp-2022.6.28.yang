// Generated by eyang-preprocessor (1.22.0-48 2022-01-20 09:10:06 CET) on Jun 30, 2022, 8:31:39 AM
module ericsson-mcpc-pcell-eutran-freq-rel-profile-vcucp {
    yang-version 1.1;
    namespace "urn:rdns:com:ericsson:oammodel:ericsson-mcpc-pcell-eutran-freq-rel-profile-vcucp";
    prefix "mcpcpcelleutranfreqrelprofile";

    import tailf-common {
        prefix tailf;
    }
    import _3gpp-common-managed-element {
        prefix "me3gpp";
    }
    import _3gpp-nr-nrm-gnbcucpfunction {
        prefix "gnbcucp3gpp";
    }
    import _3gpp-common-top {
        prefix "top3gpp";
    }
    import ericsson-yang-extensions {
        prefix "yexte";
    }
    import ericsson-mcpc-vcucp {
        prefix "mcpc";
    }
    import ericsson-common-types-vcucp {
        prefix "commontypes";
    }

    organization
      "Ericsson AB";
    contact
      "Ericsson first line support via email";
    description
      "The module defines the McpcPCellEUtranFreqRelProfile data model for the Ericsson vCU-CP.

       Copyright (c) 2021-2022 Ericsson AB. All rights reserved.";

    revision 2022-06-28 {
        description
            "Removed module-status preliminary.
             Removed preliminary status from ueConfGroupType.";
        yexte:version 1;
        yexte:release 1;
        yexte:correction 0;
        reference
            "RFC 7950: The YANG 1.1 Data Modeling Language";
    }

    revision 2022-03-14 {
        description
          "Updated McpcPCellEUtranFreqRelProfile description and precondition.
           inhibitMeasForCellCandidate and rsrpCandidateB2Offsets as obsolete.
           Added attributes ueConfGroupType and userLabel.";
        yexte:version 1;
        yexte:release 0;
        yexte:correction 0;
        reference
          "RFC 7950: The YANG 1.1 Data Modeling Language";
    }

    revision 2021-11-05 {
        description
          "Update McpcPCellEUtranFreqRelProfile description and precondition.";
        yexte:version 0;
        yexte:release 1;
        yexte:correction 1;
        reference
          "RFC 7950: The YANG 1.1 Data Modeling Language";
    }

    revision 2021-04-21 {
        description
          "Initial version of the McpcPCellEUtranFreqRelProfile model";
        yexte:version 0;
        yexte:release 1;
        yexte:correction 0;
        reference
          "RFC 7950: The YANG 1.1 Data Modeling Language";
    }

    grouping ReportConfigB2RsrpOffsetsObsolete {
        description
          "Threshold offsets for report configuration setting for B2 measurement event.

           Applied when trigger quantity is RSRP.";

        leaf threshold1Offset {
            description
              "RSRP threshold1 offset value for Event B2.";
            type int32 {
                range "-100..100";
            }
            units dB;
            status obsolete {
                yexte:status-information
                "Since 22.Q1. Replaced by "+
                "McpcPCellEUtranFreqRelProfileUeCfg::rsrpCandidateB2Offsets::threshold1Offset. "+
                "Planned to be removed.";
            }
            tailf:info 'Status Info: Since 22.Q1. Replaced by McpcPCellEUtranFreqRelProfileUeCfg::rsrpCandidateB2Offsets::threshold1Offset. Planned to be removed, Obsolete, RSRP threshold1 offset value for Event B2.';
        }

        leaf threshold2EUtraOffset {
            description
              "RSRP threshold2 offset value for Event B2.";
            type int32 {
                range "-100..100";
            }
            units dB;
            status obsolete {
                yexte:status-information
                "Since 22.Q1. Replaced by "+
                "McpcPCellEUtranFreqRelProfileUeCfg::rsrpCandidateB2Offsets::threshold2EUtraOffset. "+
                "Planned to be removed.";
            }
            tailf:info 'Status Info: Since 22.Q1. Replaced by McpcPCellEUtranFreqRelProfileUeCfg::rsrpCandidateB2Offsets::threshold2EUtraOffset. Planned to be removed, Obsolete, RSRP threshold2 offset value for Event B2.';
        }
    }

    grouping McpcPCellEUtranFreqRelProfileGrp {
        description
          "Represents the McpcPCellEUtranFreqRelProfile IOC.";

        leaf inhibitMeasForCellCandidate {
            description
              "Whether UE measurement searching for PCell candidate on this frequency is inhibited.";
            type boolean;
            status obsolete {
                yexte:status-information
                "Since 22.Q1. Replaced by "+
                "McpcPCellEUtranFreqRelProfileUeCfg::inhibitMeasForCellCandidate. "+
                "Planned to be removed.";
            }
            yexte:takes-effect
              "Next usage";
            tailf:info 'Takes effect: Next usage, Status Info: Since 22.Q1. Replaced by McpcPCellEUtranFreqRelProfileUeCfg::inhibitMeasForCellCandidate. Planned to be removed, Obsolete, Whether UE measurement searching for PCell candidate on this frequency is inhibited.';
        }

        container rsrpCandidateB2Offsets {
            description
              "Downlink RSRP B2 measurement offsets when searching for PCell candidate.";
            uses ReportConfigB2RsrpOffsetsObsolete {
                status obsolete;
            }
            status obsolete {
                yexte:status-information
                "Since 22.Q1. Replaced by "+
                "McpcPCellEUtranFreqRelProfileUeCfg::rsrpCandidateB2Offsets. "+
                "Planned to be removed.";
            }
            yexte:takes-effect
              "Next usage";
            tailf:info 'Takes effect: Next usage, Status Info: Since 22.Q1. Replaced by McpcPCellEUtranFreqRelProfileUeCfg::rsrpCandidateB2Offsets. Planned to be removed, Obsolete, Downlink RSRP B2 measurement offsets when searching for PCell candidate.';
        }

        leaf ueConfGroupType {
            description
              "UE configuration Group Type.

              Defines which UE configuration group type that is applied in the "+
              "contained MO class McpcPCellEUtranFreqRelProfileUeCfg.";
            type commontypes:UeConfGroupType;
            default UE_MOBILITY_GROUP;
            yexte:disturbances
              "Changing this attribute can cause loss of traffic.";
            yexte:takes-effect
              "Next usage.";
            tailf:info 'Takes effect: Next usage, Traffic Disturbance: Changing this attribute can cause loss of traffic, UE configuration Group Type. Defines which UE configuration group type that is applied in the contained MO class McpcPCellEUtranFreqRelProfileUeCfg.';
        }
    }

    augment "/me3gpp:ManagedElement/gnbcucp3gpp:GNBCUCPFunction/mcpc:Mcpc" {

        list McpcPCellEUtranFreqRelProfile {
            description
              "Mobility control at poor coverage (MCPC) for PCell.

              Applies to UEs that use the cell as PCell. Attributes are used "+
              "on E-UTRAN frequency relation level.

              MO instance McpcPCellEUtranFreqRelProfile=Default is created "+
              "automatically when parent MO is created, unless created manually "+
              "in the same transaction as parent MO.

              MCPC for PCell is enabled for each NRCellCU MO by setting "+
              "NRCellCU::mcpcPCellEnabled attribute.
              If EUtranFreqRelation::mcpcPCellEUtranFreqRelProfileRef is "+
              "non-empty, attributes from referred MO instance are used.
              If EUtranFreqRelation::mcpcPCellEUtranFreqRelProfileRef is "+
              "empty, attribute default values according to "+
              "McpcPCellEUtranFreqRelProfile and "+
              "McpcPCellEUtranFreqRelProfileUeCfg MO class definitions are used.";
            yexte:precondition
              "McpcPCellEUtranFreqRelProfile=Default MO instance can only be "+
              "created in the same transaction as parent MO and must not be "+
              "deleted unless parent MO is deleted. Other instances can be "+
              "created and deleted manually.";
            key id;
            uses top3gpp:Top_Grp;
            container attributes {
                uses McpcPCellEUtranFreqRelProfileGrp;
                uses commontypes:UserLabelGrp;
            }
            tailf:info 'Precondition: McpcPCellEUtranFreqRelProfile=Default MO instance can only be created in the same transaction as parent MO and must not be deleted unless parent MO is deleted. Other instances can be created and deleted manually, Mobility control at poor coverage (MCPC) for PCell. Applies to UEs that use the cell as PCell. Attributes are used on E-UTRAN frequency relation level. MO instance McpcPCellEUtranFreqRelProfile=Default is created automatically when parent MO is created, unless created manually in the same transaction as parent MO. MCPC for PCell is enabled for each NRCellCU MO by setting NRCellCU::mcpcPCellEnabled attribute. If EUtranFreqRelation::mcpcPCellEUtranFreqRelProfileRef is non-empty, attributes from referred MO instance are used. If EUtranFreqRelation::mcpcPCellEUtranFreqRelProfileRef is empty, attribute default values according to McpcPCellEUtranFreqRelProfile and McpcPCellEUtranFreqRelProfileUeCfg MO class definitions are used.';
        }
    }
}
