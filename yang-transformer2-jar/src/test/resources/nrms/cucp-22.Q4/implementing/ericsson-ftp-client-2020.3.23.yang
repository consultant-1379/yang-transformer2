module ericsson-ftp-client {
  yang-version 1.1;
  namespace urn:rdns:com:ericsson:oammodel:ericsson-ftp-client;
  prefix ftpclie;
  
  import ericsson-yang-extensions { prefix yexte; }
  import ietf-inet-types { prefix inet; }  
  
  import ietf-ssh-client {
     prefix sc;
     revision-date 2019-11-20;
     description "Based on draft";
   }
   
   import ietf-tls-client {
     prefix tc;
     revision-date 2019-11-20;
     description "Based on draft";
   }
   
  organization "Ericsson AB";
  contact "Ericsson first line support via email.";
  description 
    "This module defines reusable groupings for FTP clients that
     can be used as a basis for specific FTP client instances. 

    It is recommended to review design-time defaults including used groupings
    and deviate them based on implementation needs.
    
    --- --- 
    
    The following IETF features SHOULD be supported by implementations.
    Other features MAY be implemented based on product needs.
    
    ietf-ssh-client@2019-11-20:
    ssh-client-transport-params-config 
    
    ietf-ssh-common@2019-11-20:
    ssh-ecc, ssh-dh-group-exchange, ssh-ctr, ssh-sha2 
    
    ietf-tls-client@2019-11-20:
    tls-client-hello-params-config, x509-certificate-auth
    
    ietf-tls-common@2019-11-20:
    tls-ecc, tls-dhe, tls-gcm, tls-sha2, tls_1-2, tls-1_3 

    ietf-keystore@2019-11-20:
    keystore-supported
    Usage of central keystore is preferred.
    
    --- --- 
    Copyright (c) 2019 Ericsson AB. All rights reserved.";

  revision "2020-03-23" {
    // preliminary
    description "Path to client-identity/auth-type/password corrected to
      client-identity/auth-type/password/password";        
    yexte:version 4;
    yexte:release 0;
    yexte:correction 1;
  }

  revision "2019-12-05" {
    description "Updated to latest ssh-client and tls-client
      new major needed due to draft update?";        
    yexte:version 4;
    yexte:release 0;
    yexte:correction 0;
  }

  revision "2019-09-06" {
    // ethbll
    description "Removed all data nodes. 
      Moved content into reusable groupings.
      Changed leaf names to follow IETF best practices.
      Changed recommendation on IETF features. 
      Updated to latest IETF models.
      Removed local features";        
    yexte:version 3;
    yexte:release 0;
    yexte:correction 2;
  }
    
  revision "2018-10-09" {
      description "
            Updated to use ietf-ssh-client@2018-09-20
            and ietf-tls-client@2018-09-20";        
    yexte:version 2;
    yexte:release 0;
    yexte:correction 0;
  }
    
  revision "2017-11-06" {
      description "Removed unused import";        
    yexte:version 1;
    yexte:release 0;
    yexte:correction 1;
  }
  
  revision "2017-05-26" {
      description "First version
        - Imported ssh and tls client modules of 2017-03-13
        - In relation to ECIM FileTPM 2.1";
        
    yexte:version 1;
    yexte:release 0;
    yexte:correction 0;
  }
  
  grouping sftp-client-grouping {     
    description
      "Grouping defining configuration for an SFTP client including 
       a set of (destination) sftp servers.";

    list sftp-server {
      key name;
      description "List of SFTP servers the SFTP client is to
        initiate connections to in parallel.";
        
      leaf name {
        type string;
        description "An arbitrary name for the SFTP server.";
      } 
        
      container endpoints {
        description "Container for the list of endpoints.";
        
        list endpoint {
          key name;
          min-elements 1;
          ordered-by user;
          description "A user-ordered list of endpoints that the SFTP
            client may attempt to connect to (one at a time) 
            swithcing to the next in case the connection failed. 
            Each endpoint has its own security configuration.";
            
          leaf name {
            type string;
          }
              
          leaf remote-address {
            type inet:host;
            mandatory true ;
            description "The IP address or hostname of the endpoint.
              If a domain name is configured, then the
              DNS resolution should happen on each usage
              attempt.  If the DNS resolution results in
              multiple IP addresses, the IP addresses will
              be tried according to local preference order
              until a connection has been established or
              until all IP addresses have failed.";
          }
          
          leaf remote-port {
            type inet:port-number;
            default 22;
            description "The IP port for this endpoint.  The NETCONF
              client will use the IANA-assigned well-known
              port for 'sftp' (22) if no value is specified.";
              }

          leaf remote-path {
            type string;
            description "Specifies the location or path where the
              file(s) will be stored.";
          }

          uses sc:ssh-client-grouping {
            refine client-identity/auth-type/password/password {
              description "Ericsson extension for passwords is added.";
              yexte:is-passphrase;
            }
            refine "client-identity/auth-type/public-key/public-key/" +
                "local-or-keystore/local/local-definition/private-key-type/" +
                "private-key/private-key" {
              description "Ericsson extension for secret items is added.";
              yexte:is-passphrase;
            }
          }
        }
      }
    }
  }

  grouping ftp-tls-client-grouping {     
    description
      "Grouping defining configuration for an FTP-TLS client including 
       a set of (destination) servers.";

    list ftp-tls-server {
      key name;
      description "List of FTP over TLS servers the client is to
        initiate connections to in parallel.";

      leaf name {
        type string;
      }

      container endpoints {
        description "Container for the list of endpoints.";
            
        list endpoint {
          key name;
          min-elements 1;
          description "A list of endpoints that the FTP over TLS
            client may attempt to connect to (one at a time) 
            swithcing to the next in case the connection failed. 
            Each endpoint has its own security configuration.";
                
          leaf name {
            type string;
          }
                
          leaf remote-address {
            type inet:host;
            mandatory true ;
            description "The IP address or hostname of the endpoint.
              If a domain name is configured, then the
              DNS resolution should happen on each usage
              attempt.  If the DNS resolution results in
              multiple IP addresses, the IP addresses will
              be tried according to local preference order
              until a connection has been established or
              until all IP addresses have failed.";
          }
                
          leaf remote-port {
            type inet:port-number;
            default 21;
            description "The IP port for this endpoint. The 
              client will use the IANA-assigned well-known
              port for 'ftp' (21) if no value is
              specified.";
          }

          leaf remote-path {
            type string;
            description "Specifies the location or path where the
              file(s) will be stored.";
          }

          // keystore should be used rather instead of local key
          uses tc:tls-client-grouping {
            refine "client-identity/auth-type/certificate/certificate/local-or-keystore/local/" +
                "local-definition/private-key-type/private-key/private-key" {
              description "Ericsson extension for secrets is added.";
              yexte:is-passphrase;
            }
          }
        }
      }
    }  
  }   
}
