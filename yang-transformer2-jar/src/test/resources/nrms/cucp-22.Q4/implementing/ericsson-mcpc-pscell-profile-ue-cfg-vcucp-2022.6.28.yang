// Generated by eyang-preprocessor (1.22.0-48 2022-01-20 09:10:06 CET) on Jun 30, 2022, 8:31:39 AM
module ericsson-mcpc-pscell-profile-ue-cfg-vcucp {
    yang-version 1.1;
    namespace urn:rdns:com:ericsson:oammodel:ericsson-mcpc-pscell-profile-ue-cfg-vcucp;
    prefix mcpcpscellprofuecfg;

    import tailf-common {
        prefix tailf;
    }
    import _3gpp-common-managed-element {
        prefix me3gpp;
    }
    import _3gpp-nr-nrm-gnbcucpfunction {
        prefix gnbcucp3gpp;
    }
    import _3gpp-common-top {
        prefix top3gpp;
    }
    import ericsson-yang-extensions {
        prefix yexte;
    }
    import ericsson-common-types-vcucp {
        prefix commontypes;
    }
    import ericsson-mcpc-vcucp {
        prefix mcpc;
    }
    import ericsson-mcpc-pscell-profile-vcucp {
        prefix mcpcpscellprofile;
    }

    organization
        "Ericsson AB";
    contact
        "Ericsson first line support via email";
    description
        "The module defines the McpcPSCellProfileUeCfg data model for the Ericsson vCU-CP.

        Copyright (c) 2021-2022 Ericsson AB. All rights reserved.";

    revision 2022-06-28 {
        description
            "Removed module-status preliminary.";
        yexte:version 1;
        yexte:release 1;
        yexte:correction 0;
        reference
            "RFC 7950: The YANG 1.1 Data Modeling Language";
    }

    revision 2022-03-14 {
        description
            "Updated description of McpcPSCellProfileUeCfg list.
             Range of ReportConfigA5Rsrp::threshold1 and ReportConfigA5Rsrp::threshold2
             updated to max -29 from max -26.
             Added the userLabel attribute.";
        yexte:version 1;
        yexte:release 0;
        yexte:correction 0;
        reference
            "RFC 7950: The YANG 1.1 Data Modeling Language";
    }

    revision 2021-11-05 {
        description
            "Changed the precondition on the McpcPSCellProfileUeCfg list.";
        yexte:version 0;
        yexte:release 1;
        yexte:correction 2;
        reference
            "RFC 7950: The YANG 1.1 Data Modeling Language";
    }

    revision 2021-09-20 {
        description
            "Changed the precondition on the McpcPSCellProfileUeCfg list.";
        yexte:version 0;
        yexte:release 1;
        yexte:correction 1;
        reference
            "RFC 7950: The YANG 1.1 Data Modeling Language";
    }

    revision 2021-08-11 {
        description
            "Initial version of the McpcPSCellProfileUeCfg model";
        yexte:version 0;
        yexte:release 1;
        yexte:correction 0;
        reference
            "RFC 7950: The YANG 1.1 Data Modeling Language";
    }

    grouping McpcPSCellProfileUeCfgGrp {
        description
            "Represents the McpcPSCellProfileUeCfg IOC.";

        leaf lowHighFreqPrioClassification {
            description
                "Classification of low and high frequency relation priority.

                NR frequency relation priorities are defined by "+
                "UeMCNrFreqRelProfileUeCfg::connModePrioPSCell.

                Frequency relation priority is classified as high priority if its "+
                "value is higher or equal to value of lowHighFreqPrioClassification, "+
                "else classified as low priority.";
            type int32 {
                range "0..7";
            }
            default 7;
            yexte:takes-effect
                "Next usage.";
            tailf:info 'Takes effect: Next usage, Classification of low and high frequency relation priority. NR frequency relation priorities are defined by UeMCNrFreqRelProfileUeCfg::connModePrioPSCell. Frequency relation priority is classified as high priority if its value is higher or equal to value of lowHighFreqPrioClassification, else classified as low priority.';
        }

        leaf-list mcpcQuantityList {
            min-elements 1;
            max-elements 2;
            description
                "Measurement quantities on which PSCell mobility control at poor "+
                "coverage function is applied.";
            type commontypes:McpcQuantity;
            yexte:initial-value RSRP;
            yexte:takes-effect
                "New connection";
            tailf:info 'Takes effect: New connection, Measurement quantities on which PSCell mobility control at poor coverage function is applied.';
        }

        container rsrpCandidateA5 {
            description
                "RSRP A5 measurement report criteria when searching for PSCell candidate.";
            uses commontypes:ReportConfigA5Rsrp;
            reference
                "3GPP TS 38.331";
            yexte:takes-effect
                "Next usage.";
            tailf:info 'Takes effect: Next usage, RSRP A5 measurement report criteria when searching for PSCell candidate.';
        }

        container rsrpCritical {
            description
                "RSRP measurement report criteria for detecting critical coverage.

                Only applied if rsrpCriticalEnabled is true.";
            uses commontypes:ReportConfigA2Rsrp;
            reference
                "3GPP TS 38.331";
            yexte:takes-effect
                "Next usage.";
            tailf:info 'Takes effect: Next usage, RSRP measurement report criteria for detecting critical coverage. Only applied if rsrpCriticalEnabled is true.';
        }

        leaf rsrpCriticalEnabled {
            description
                "Whether RSRP measurements for detecting critical coverage is enabled.

                RSRP measurement criteria for detecting critical coverage is defined "+
                "by rpspCritical.";
            type boolean;
            default false;
            yexte:disturbances
                "Changing this attribute can cause loss of traffic.
                Changing this attribute to true can trigger release of NR resources "+
                "if UE measurement event condition defined by rsrpCritical attribute "+
                "is fulfilled.";
            yexte:takes-effect
                "Next usage.";
            tailf:info 'Takes effect: Next usage, Traffic Disturbance: Changing this attribute can cause loss of traffic.
                Changing this attribute to true can trigger release of NR resources if UE measurement event condition defined by rsrpCritical attribute is fulfilled, Whether RSRP measurements for detecting critical coverage is enabled. RSRP measurement criteria for detecting critical coverage is defined by rpspCritical.';
        }

        leaf rsrpSearchTimeRestriction {
            description
                "Search time restriction when searching for PSCell candidate using DL "+
                "RSRP measurements.

                If set to -1, no time restriction is applied.";
            type int32 {
                range "-1|200..12000";
            }
            default -1;
            units ms;
            yexte:takes-effect
                "Next usage.";
            tailf:info 'Takes effect: Next usage, Search time restriction when searching for PSCell candidate using DL RSRP measurements. If set to -1, no time restriction is applied.';
        }

        container rsrpSearchZone {
            description
                "RSRP measurement report criteria that define entering and leaving search zone.";
            uses commontypes:ReportConfigA1A2Rsrp;
            reference
                "3GPP TS 38.331";
            yexte:takes-effect
                "Next usage.";
            tailf:info 'Takes effect: Next usage, RSRP measurement report criteria that define entering and leaving search zone.';
        }
    }

    augment "/me3gpp:ManagedElement/gnbcucp3gpp:GNBCUCPFunction/mcpc:Mcpc/mcpcpscellprofile:McpcPSCellProfile" {

        list McpcPSCellProfileUeCfg {
            description
                "Mobility control at poor coverage function for PSCell in "+
                "EN-DC, UE configuration group.

                Applies to UEs that use this cell as PSCell in EN-DC. "+
                "Attributes are used on cell level.

                MO instance McpcPSCellProfileUeCfg=Base is created "+
                "automatically when parent MO is created, unless created "+
                "manually in the same transaction as parent MO.

                The RDN of this MO must always be McpcPSCellProfileUeCfg=Base.";
            key id;
            max-elements 1;
            uses top3gpp:Top_Grp {
                refine id {
                    must '. = "Base"' {
                        error-message
                          "The RDN of this MO must always be McpcPSCellProfileUeCfg=Base";
                    }
                }
            }
            container attributes {
                uses McpcPSCellProfileUeCfgGrp;
                uses commontypes:UserLabelGrp;
            }
            yexte:precondition
                "McpcPSCellProfileUeCfg=Default MO instance must not be deleted unless "+
                "parent MO is deleted.";
            tailf:info 'Precondition: McpcPSCellProfileUeCfg=Default MO instance must not be deleted unless parent MO is deleted, Mobility control at poor coverage function for PSCell in EN-DC, UE configuration group. Applies to UEs that use this cell as PSCell in EN-DC. Attributes are used on cell level. MO instance McpcPSCellProfileUeCfg=Base is created automatically when parent MO is created, unless created manually in the same transaction as parent MO. The RDN of this MO must always be McpcPSCellProfileUeCfg=Base.';
        }
    }
}
