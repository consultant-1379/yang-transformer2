// Generated by eyang-preprocessor (1.22.0-48 2022-01-20 09:10:06 CET) on Jun 30, 2022, 8:31:44 AM
module ericsson-uemccellprofile-vcucp {
    yang-version 1.1;
    namespace "urn:rdns:com:ericsson:oammodel:ericsson-uemccellprofile-vcucp";
    prefix "uemccellprofile";

    import tailf-common {
        prefix tailf;
    }
    import _3gpp-common-managed-element {
        prefix "me3gpp";
    }
    import _3gpp-nr-nrm-gnbcucpfunction {
        prefix "gnbcucp3gpp";
    }
    import _3gpp-common-top {
        prefix "top3gpp";
    }
    import ericsson-yang-extensions {
        prefix "yexte";
    }
    import ericsson-uemc-vcucp {
        prefix "uemcvcucp";
    }
    import ericsson-common-types-vcucp {
        prefix "commontypes";
    }

    organization
      "Ericsson AB";
    contact
      "Ericsson first line support via email";
    description
      "The module defines the UeMCCellProfile data model for the Ericsson vCU-CP.

       Copyright (c) 2021-2022 Ericsson AB. All rights reserved.";

    revision 2022-06-28 {
        description
            "Removed module-status preliminary.";
        yexte:version 0;
        yexte:release 3;
        yexte:correction 0;
        reference
            "RFC 7950: The YANG 1.1 Data Modeling Language";
    }

    revision 2022-03-14 {
        description
          "Updated description and precondition for UeMCCellProfile.
           Added the userLabel attribute.";
        yexte:version 0;
        yexte:release 2;
        yexte:correction 0;
        reference
          "RFC 7950: The YANG 1.1 Data Modeling Language";
    }

    revision 2021-11-05 {
        description
          "Updated description and precondition for UeMCCellProfile.";
        yexte:version 0;
        yexte:release 1;
        yexte:correction 1;
        reference
          "RFC 7950: The YANG 1.1 Data Modeling Language";
    }

    revision 2021-04-24 {
        description
          "Initial version of the UeMCCellProfile model.";
        yexte:version 0;
        yexte:release 1;
        yexte:correction 0;
        reference
          "RFC 7950: The YANG 1.1 Data Modeling Language";
    }

    grouping UeMCCellProfileGrp {
        description
          "Represents the UeMCCellProfile IOC.";

        leaf filterCoefficientEUtraRsrp {
            description
              "Layer 3 average filter coefficient applied in UE performing RSRP " +
              "measurements on E-UTRA frequencies.";
            type int32 {
                range "0|1|2|3|4|5|6|7|8|9|11|13|15|17|19";
            }
            default 4;
            yexte:takes-effect
              "Next usage.";
            tailf:info 'Takes effect: Next usage, Layer 3 average filter coefficient applied in UE performing RSRP measurements on E-UTRA frequencies.';
        }

        leaf filterCoefficientEUtraRsrq {
            description
              "Layer 3 average filter coefficient applied in UE performing RSRQ " +
              "measurements on E-UTRA frequencies.";
            type int32 {
                range "0|1|2|3|4|5|6|7|8|9|11|13|15|17|19";
            }
            default 11;
            yexte:takes-effect
              "Next usage.";
            tailf:info 'Takes effect: Next usage, Layer 3 average filter coefficient applied in UE performing RSRQ measurements on E-UTRA frequencies.';
        }

        leaf filterCoefficientNrRsrpHigh {
            description
              "Layer 3 average filter coefficient applied in UE performing RSRP " +
              "measurements on NR frequencies.

               Filter coefficient for measurement of NR frequencies with " +
              "ARFCN-ValueNR value higher than ARFCN-ValueNR defined by attribute " +
              "freqClassificationThreshold.";
            type int32 {
                range "0..9|11|13|15|17|19";
            }
            default 4;
            reference
              "3GPP TS 38.331";
            yexte:takes-effect
              "Next usage.";
            tailf:info 'Takes effect: Next usage, Layer 3 average filter coefficient applied in UE performing RSRP measurements on NR frequencies. Filter coefficient for measurement of NR frequencies with ARFCN-ValueNR value higher than ARFCN-ValueNR defined by attribute freqClassificationThreshold.';
        }

        leaf filterCoefficientNrRsrpLow {
            description
              "Layer 3 average filter coefficient applied in UE performing RSRP " +
              "measurements on NR frequencies.

               Filter coefficient for measurement of NR frequencies with " +
              "ARFCN-ValueNR value lower than or equal to ARFCN-ValueNR defined by " +
              "attribute freqClassificationThreshold.";
            type int32 {
                range "0..9|11|13|15|17|19";
            }
            default 4;
            reference
              "3GPP TS 38.331";
            yexte:takes-effect
              "Next usage.";
            tailf:info 'Takes effect: Next usage, Layer 3 average filter coefficient applied in UE performing RSRP measurements on NR frequencies. Filter coefficient for measurement of NR frequencies with ARFCN-ValueNR value lower than or equal to ARFCN-ValueNR defined by attribute freqClassificationThreshold.';
        }

        leaf filterCoefficientNrRsrqHigh {
            description
              "Layer 3 average filter coefficient applied in UE performing RSRQ " +
              "measurements on NR frequencies.

               Filter coefficient for measurement of NR frequencies with " +
              "ARFCN-ValueNR value higher than ARFCN-ValueNR defined by attribute " +
              "freqClassificationThreshold.";
            type int32 {
                range "0..9|11|13|15|17|19";
            }
            default 11;
            reference
              "3GPP TS 38.331";
            yexte:takes-effect
              "Next usage.";
            tailf:info 'Takes effect: Next usage, Layer 3 average filter coefficient applied in UE performing RSRQ measurements on NR frequencies. Filter coefficient for measurement of NR frequencies with ARFCN-ValueNR value higher than ARFCN-ValueNR defined by attribute freqClassificationThreshold.';
        }

        leaf filterCoefficientNrRsrqLow {
            description
              "Layer 3 average filter coefficient applied in UE performing RSRQ " +
              "measurements on NR frequencies.

               Filter coefficient for measurement of NR frequencies with " +
              "ARFCN-ValueNR value lower than or equal to ARFCN-ValueNR defined by " +
              "attribute freqClassificationThreshold.";
            type int32 {
                range "0..9|11|13|15|17|19";
            }
            default 11;
            reference
              "3GPP TS 38.331";
            yexte:takes-effect
              "Next usage.";
            tailf:info 'Takes effect: Next usage, Layer 3 average filter coefficient applied in UE performing RSRQ measurements on NR frequencies. Filter coefficient for measurement of NR frequencies with ARFCN-ValueNR value lower than or equal to ARFCN-ValueNR defined by attribute freqClassificationThreshold.';
        }

        leaf freqClassificationThreshold {
            description
              "Frequency classification threshold.

               Threshold is provided as ARFCN-ValueNR value and defines which " +
              "filter coefficients that will be used by UE when measuring on NR " +
              "frequencies.";
            type int32 {
                range "0..3279164";
            }
            default 3279163;
            reference
              "3GPP TS 38.331, 3GPP TS 38.104";
            yexte:takes-effect
              "Next usage.";
            tailf:info 'Takes effect: Next usage, Frequency classification threshold. Threshold is provided as ARFCN-ValueNR value and defines which filter coefficients that will be used by UE when measuring on NR frequencies.';
        }

        leaf sMeasure {
            description
              "RSRP measurement threshold when UE is required to perform " +
              "measurements on non-serving cells.

               Corresponds to RRC parameter s-MeasureConfig and choice ssb-RSRP.
               If empty, threshold is not used.
               Value -29 corresponds to special value of ssb-RSRP = infinity.";
            type int32 {
                range "-156..-29";
            }
            yexte:initial-value -29;
            units dBm;
            reference
              "3GPP TS 38.331";
            yexte:takes-effect
              "Next usage.";
            tailf:info 'Takes effect: Next usage, RSRP measurement threshold when UE is required to perform measurements on non-serving cells. Corresponds to RRC parameter s-MeasureConfig and choice ssb-RSRP. If empty, threshold is not used. Value -29 corresponds to special value of ssb-RSRP = infinity.';
        }
    }

    augment "/me3gpp:ManagedElement/gnbcucp3gpp:GNBCUCPFunction/uemcvcucp:UeMC" {
        list UeMCCellProfile {
            description
              "UE mobility control attributes.

              The attributes are used on cell level.

              MO instance UeMCCellProfile=Default is created automatically " +
              "when parent MO is created, unless created manually in the same " +
              "transaction as parent MO.

              If NRCellCU::ueMCCellProfileRef is non-empty, attributes from " +
              "referred MO instance are used.
              If NRCellCU::ueMCCellProfileRef is empty, attribute default " +
              "values according to UeMCCellProfile MO class definitions are " +
              "used.";
            yexte:precondition
              "UeMCCellProfile=Default MO instance can only be created in the same " +
              "transaction as parent MO and must not be deleted unless parent MO " +
              "is deleted. Other instances can be created and deleted manually.";
            key id;
            uses top3gpp:Top_Grp;
            container attributes {
                uses UeMCCellProfileGrp;
                uses commontypes:UserLabelGrp;
            }
            tailf:info 'Precondition: UeMCCellProfile=Default MO instance can only be created in the same transaction as parent MO and must not be deleted unless parent MO is deleted. Other instances can be created and deleted manually, UE mobility control attributes. The attributes are used on cell level. MO instance UeMCCellProfile=Default is created automatically when parent MO is created, unless created manually in the same transaction as parent MO. If NRCellCU::ueMCCellProfileRef is non-empty, attributes from referred MO instance are used. If NRCellCU::ueMCCellProfileRef is empty, attribute default values according to UeMCCellProfile MO class definitions are used.';
        }
    }
}
