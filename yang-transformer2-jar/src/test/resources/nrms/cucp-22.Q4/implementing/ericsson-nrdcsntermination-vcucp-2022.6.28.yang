// Generated by eyang-preprocessor (1.22.0-48 2022-01-20 09:10:06 CET) on Jun 30, 2022, 8:31:41 AM
module ericsson-nrdcsntermination-vcucp {
    yang-version 1.1;
    namespace urn:rdns:com:ericsson:oammodel:ericsson-nrdcsntermination-vcucp;
    prefix nrdcsntermination;

    import tailf-common {
        prefix tailf;
    }
    import _3gpp-common-managed-element {
        prefix me3gpp;
    }
    import _3gpp-nr-nrm-gnbcucpfunction {
        prefix gnbcucp3gpp;
    }
    import _3gpp-common-top {
        prefix top3gpp;
    }
    import ericsson-yang-extensions {
        prefix yexte;
    }

    organization
      "Ericsson AB";
    contact
      "Ericsson first line support via email";
    description
      "The module defines the NrdcSnTermination data model for the Ericsson vCU-CP.

       Copyright (c) 2021-2022 Ericsson AB. All rights reserved.";

    revision 2022-06-28 {
        description
            "Removed module-status preliminary.";
        yexte:version 0;
        yexte:release 3;
        yexte:correction 0;
        reference
            "RFC 7950: The YANG 1.1 Data Modeling Language";
    }

    revision 2022-03-14 {
        description
          "Updated description, added precondition and changed max-elements of
          NrdcSnTermination.
          Added must rules regarding defaultNrdcSnTerm.
          Added dependencies to defaultNrdcSnTerm";
        yexte:version 0;
        yexte:release 2;
        yexte:correction 1;
        reference
          "RFC 7950: The YANG 1.1 Data Modeling Language";
    }

    revision 2021-11-05 {
        description
          "Preliminary status removed for NrdcSnTermination and defaultNrdcSnTerm.";
        yexte:version 0;
        yexte:release 2;
        yexte:correction 0;
        reference
          "RFC 7950: The YANG 1.1 Data Modeling Language";
    }

    revision 2021-05-24 {
        description
          "Add must rule for defaultNrdcSnTerm";
        yexte:version 0;
        yexte:release 1;
        yexte:correction 1;
        reference
          "RFC 7950: The YANG 1.1 Data Modeling Language";
    }

    revision 2021-04-14 {
        description
          "Initial version of the NrdcSnTermination model.";
        yexte:version 0;
        yexte:release 1;
        yexte:correction 0;
        reference
          "RFC 7950: The YANG 1.1 Data Modeling Language";
    }

    grouping NrdcSnTerminationGrp {
        description
          "Represents the NrdcSnTermination IOC.";

        leaf defaultNrdcSnTerm {
            description
              "Whether this instance is default NrdcSnTermination instance.

               Default instance is used when nrdcSnTerminationRef attribute is "
            + "empty for CUCP5qi.";
            type boolean;
            must "count(../../../nrdcsntermination:NrdcSnTermination/nrdcsntermination:attributes/nrdcsntermination:defaultNrdcSnTerm[. = 'true']) &lt; 2" {
                error-message
                "Can have maximum one NrdcSnTermination configured as default.";
            }
            default false;
            yexte:dependencies
                "Must be false in MO instance NrdcSnTermination="+
                "SnTerminationProhibited.";
            yexte:takes-effect
                "New connection";
            tailf:info 'Takes effect: New connection, Dependencies: Must be false in MO instance NrdcSnTermination=SnTerminationProhibited, Whether this instance is default NrdcSnTermination instance. Default instance is used when nrdcSnTerminationRef attribute is empty for CUCP5qi.';
        }
    }

    augment "/me3gpp:ManagedElement/gnbcucp3gpp:GNBCUCPFunction" {

        list NrdcSnTermination {
            description
                "Profile for Secondary Node termination.

                MO instance NrdcSnTermination=SnTerminationProhibited is created "+
                "automatically when parent MO is created, unless created manually "+
                "in the same transaction as parent MO.

                Attribute defaultNrdcSnTerm must be false in MO instance "+
                "NrdcSnTermination=SnTerminationProhibited.";
            key id;
            max-elements 30;
            uses top3gpp:Top_Grp;
            container attributes {
                uses NrdcSnTerminationGrp;
            }
            yexte:precondition
                "NrdcSnTermination=SnTerminationProhibited instance can only be "+
                "created in the same transaction as parent MO and must not be deleted "+
                "unless parent MO is deleted. Other instances can be created and "+
                "deleted manually.";

            must "count(../NrdcSnTermination) &lt; 30 or
                  count(../NrdcSnTermination/id[. = 'SnTerminationProhibited']) = 1" {
                error-message
                    "Maximum 29 NrdcSnTermination instances under a GNBCUCPFunction can be created with RDN different from SnTerminationProhibited.";
            }
            must "id != 'SnTerminationProhibited' or attributes/defaultNrdcSnTerm = 'false'" {
                error-message
                    "defaultNrdcSnTerm must be false in MO instance NrdcSnTermination=SnTerminationProhibited.";
            }
            tailf:info 'Precondition: NrdcSnTermination=SnTerminationProhibited instance can only be created in the same transaction as parent MO and must not be deleted unless parent MO is deleted. Other instances can be created and deleted manually, Profile for Secondary Node termination. MO instance NrdcSnTermination=SnTerminationProhibited is created automatically when parent MO is created, unless created manually in the same transaction as parent MO. Attribute defaultNrdcSnTerm must be false in MO instance NrdcSnTermination=SnTerminationProhibited.';
        }
    }
}
