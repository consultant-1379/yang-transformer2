// Generated by eyang-preprocessor (1.22.0-48 2022-01-20 09:10:06 CET) on Jun 30, 2022, 8:31:43 AM
module ericsson-nrfrequency-vcucp {
    yang-version 1.1;
    namespace urn:rdns:com:ericsson:oammodel:ericsson-nrfrequency-vcucp;
    prefix nrfrequency;

    import tailf-common {
        prefix tailf;
    }
    import _3gpp-common-managed-element {
        prefix me3gpp;
    }
    import _3gpp-nr-nrm-gnbcucpfunction {
        prefix gnbcucp3gpp;
    }
    import _3gpp-common-top {
        prefix top3gpp;
    }
    import _3gpp-common-yang-extensions {
        prefix yext3gpp;
    }
    import ericsson-nrnetwork-vcucp {
        prefix nrnetwork;
    }
    import ericsson-yang-extensions {
        prefix yexte;
    }
    import ericsson-notifications {
        prefix notife;
    }

    organization
        "Ericsson AB";
    contact
        "Ericsson first line support via email";
    description
        "The module defines the NRFrequency data model for the Ericsson vCU-CP.

         Copyright (c) 2021-2022 Ericsson AB. All rights reserved.";

    revision 2022-06-28 {
        description
            "Removed module-status preliminary.";
        yexte:version 5;
        yexte:release 1;
        yexte:correction 0;
        reference
            "RFC 7950: The YANG 1.1 Data Modeling Language";
    }

    revision 2022-06-16 {
        description
            "Set value range on smtcPeriodicity.";
        yexte:version 5;
        yexte:release 0;
        yexte:correction 0;
        reference
            "RFC 7950: The YANG 1.1 Data Modeling Language";
    }

    revision 2022-04-21 {
        description
            "Changed the RDN format to NRFrequency=arfcnValueNRDl-smtcScs only.";
        yexte:version 4;
        yexte:release 0;
        yexte:correction 0;
        reference
            "RFC 7950: The YANG 1.1 Data Modeling Language";
    }

    revision 2022-04-20 {
        description
            "Remove value range from smtcPeriodicity until upgrade function is created.";
        yexte:version 3;
        yexte:release 0;
        yexte:correction 1;
        reference
            "RFC 7950: The YANG 1.1 Data Modeling Language";
    }

    revision 2022-03-14 {
        description
            "Updated dependencies of arfcnValueNRDl with a new condition.
             Updated the info about matching id in all dependencies tags.
             Added missing value range to smtcPeriodicity.";
        yexte:version 3;
        yexte:release 0;
        yexte:correction 0;
        reference
            "RFC 7950: The YANG 1.1 Data Modeling Language";
    }

    revision 2021-11-05 {
        description
            "New value range for bandListManual. Update descriptions and add dependencies tags for multiple values.
            Must rule for id.";
        yexte:version 2;
        yexte:release 2;
        yexte:correction 0;
        reference
            "RFC 7950: The YANG 1.1 Data Modeling Language";
    }

    revision 2021-07-27 {
        description
            "Bug Fix, leaf-list state notifiable compatibility issue. Adds extension notife:notifiable-state-data false to bandList.";
        yexte:version 2;
        yexte:release 1;
        yexte:correction 0;
        reference
            "RFC 7950: The YANG 1.1 Data Modeling Language";
    }

    revision 2021-06-01 {
        description
            "Correction in must rule for smtcPeriodicity.";
        yexte:version 1;
        yexte:release 2;
        yexte:correction 1;
        reference
            "RFC 7950: The YANG 1.1 Data Modeling Language";
    }

    revision 2021-05-06 {
        description
            "Remove is-system-created and restricted extensions.
             Add yext3gpp:inVariant to arfcnValueNRDl and smtcScs.";
        yexte:version 1;
        yexte:release 2;
        yexte:correction 0;
        reference
            "RFC 7950: The YANG 1.1 Data Modeling Language";
    }

    revision 2021-04-06 {
        description
            "Update Ericsson MO description.";
        yexte:version 1;
        yexte:release 1;
        yexte:correction 1;
        reference
            "RFC 7950: The YANG 1.1 Data Modeling Language";
    }

    revision 2021-03-15 {
        description
            "Parity with ECIM R1A79";
        yexte:version 1;
        yexte:release 1;
        yexte:correction 0;
        reference
            "RFC 7950: The YANG 1.1 Data Modeling Language";
    }

    revision 2021-01-20 {
        description
            "Add extensions is-system-created and rrestricted.";
        yexte:version 1;
        yexte:release 0;
        yexte:correction 0;
        reference
            "RFC 7950: The YANG 1.1 Data Modeling Language";
    }

    revision 2021-01-11 {
        description
            "Initial version of the NRFrequency EndpointResource model.";
        yexte:version 0;
        yexte:release 1;
        yexte:correction 0;
        reference
            "RFC 7950: The YANG 1.1 Data Modeling Language";
    }

    grouping NRFrequencyGrp {
        description "NRFrequency MO and related measurement parameters.";
        reference "Ericsson documentation";

        leaf arfcnValueNRDl {
            description
                "Absolute frequency applicable for a downlink NR carrier frequency associated with the SSB.

                This attribute is broadcast in SIB4.";
            reference "3GPP TS 38.104";
            mandatory true;
            type int32 {
                range "0..3279165";
            }
            yext3gpp:inVariant;
            yexte:dependencies
                "Must match part of the id (see the NRFrequency description).
                Must be unique among NRFrequency MO instances referenced by "+
                "NRFreqRelation MO instances under NRCellCU MO instance.";
            tailf:info 'Dependencies: Must match part of the id (see the NRFrequency description).
                Must be unique among NRFrequency MO instances referenced by NRFreqRelation MO instances under NRCellCU MO instance, Absolute frequency applicable for a downlink NR carrier frequency associated with the SSB. This attribute is broadcast in SIB4.';
        }

        leaf-list bandList {
            description
                "List of all NR bands the NRFrequency belongs to.

                Calculated by the system based on arfcnValueNRDl and smtcScs.

                If configured, bandListManual is used instead of bandList.";
            reference "3GPP TS 38.104";
            config false;
            notife:notifiable-state-data false;
            max-elements 32;
            type uint32 {
                range "1..1024";
            }
            tailf:meta-data notife:notifiable-state-data {
                tailf:meta-value false;
            }
        }

        leaf-list bandListManual {
            max-elements 32;
            description
                "Configured list of bands to be used by NRFrequency.

                If present, this list is used instead of NRFrequency::bandList.

                Bands specified in NRFrequency::bandListManual must be intersection "+
                "of possible bands for given NRFrequency configuration.
                Possible bands are displayed in NRFrequency::bandList.
                Example, if NRFrequency::bandList contains bands 77 and 78, "+
                "NRFrequency::bandListManual contains 77, 78, or both.

                Recommendation is that this list has same content as "+
                "NRCellDU::bandListManual for cells with same frequency. This "+
                "recommendation is for 3GPP compliance.

                Order of NR bands listed in NRFrequency::bandListManual corresponds "+
                "to order of bands in frequencyBandList in SIB4.";
            type int32 {
                range "1..5|7|8|12..14|18|20|24..26|28..30|34|38..41|48|50|51|53|65|66|70|"+
                    "71|74..86|89..95|97..99|257..261";
            }
            reference
                "3GPP TS 38.104";
            yexte:takes-effect
                "New connection";
            tailf:info 'Takes effect: New connection, Configured list of bands to be used by NRFrequency. If present, this list is used instead of NRFrequency::bandList. Bands specified in NRFrequency::bandListManual must be intersection of possible bands for given NRFrequency configuration. Possible bands are displayed in NRFrequency::bandList. Example, if NRFrequency::bandList contains bands 77 and 78, NRFrequency::bandListManual contains 77, 78, or both. Recommendation is that this list has same content as NRCellDU::bandListManual for cells with same frequency. This recommendation is for 3GPP compliance. Order of NR bands listed in NRFrequency::bandListManual corresponds to order of bands in frequencyBandList in SIB4.';
        }

        leaf gscn {
            description
                "NR frequencies on the Global Synchronization Channel Raster.

                If empty, SSB is not placed on synchronization raster.";
            config false;
            type int32;
            reference
            "3GPP TS 38.104";
        }

        leaf smtcDuration {
            description
                "Duration of measurement window where SSBs are received.

                Broadcast in SIB4.";
            reference "3GPP TS 38.331";
            type int32 {
                range "1..5";
            }
            default 5;
            units ms;
            yexte:dependencies
                "Might need to match part of the id (see the NRFrequency description).";
            tailf:info 'Dependencies: Might need to match part of the id (see the NRFrequency description), Duration of measurement window where SSBs are received. Broadcast in SIB4.';
        }

        leaf smtcOffset {
            description
                "Offset of measurement window where SSBs are received.

                Broadcast in SIB4.";
            reference "3GPP TS 38.331";
            type int32 {
                range "0..159";
            }
            default 0;
            units ms;
            must 'current() &lt; ../smtcPeriodicity' {
                error-message
                    "smtcOffset must be less than smtcPeriodicity";
            }
            yexte:dependencies
                "smtcOffset &lt; smtcPeriodicity
                Might need to match part of the id (see the NRFrequency description).";
            tailf:info 'Dependencies: smtcOffset &lt; smtcPeriodicity
                Might need to match part of the id (see the NRFrequency description), Offset of measurement window where SSBs are received. Broadcast in SIB4.';
        }

        leaf smtcPeriodicity {
            description
                "Periodicity of measurement window where SSBs are received.

                Broadcast in SIB4.";
            reference "3GPP TS 38.331";
            type int32 {
                range "5|10|20|40|80|160";
            }
            default 20;
            units ms;
            must 'current() &gt; ../smtcOffset' {
                error-message
                  "smtcPeriodicity must be greater than smtcOffset";
            }
            yexte:dependencies
                "smtcPeriodicity &gt; smtcOffset
                Might need to match part of the id (see the NRFrequency description).";
            tailf:info 'Dependencies: smtcPeriodicity &gt; smtcOffset
                Might need to match part of the id (see the NRFrequency description), Periodicity of measurement window where SSBs are received. Broadcast in SIB4.';
        }

        leaf smtcScs {
            description
                "Subcarrier Spacing for the SSBs.

                Broadcast in SIB4.";
            reference "3GPP TS 38.213";
            mandatory true;
            type int32 {
                range "15 | 30 | 120 | 240";
            }
            units kHz;
            must '((../arfcnValueNRDl) &lt; 2016667 and (current() &lt;= 30)) or (current() &gt;= 120)' {
                error-message
                  "smtcScs must be 15 or 30 kHz for FR1 and 120 or 240 kHz for FR2.";
            }
            yexte:dependencies
                "Must match part of the id (see the NRFrequency description).
                If arfcnValueNRDl is less than 2016667 (FR1), valid smtcScs values "+
                "are 15 and 30 kHz.
                If arfcnValueNRDl is greater or equal than 2016667 (FR2), valid "+
                "smtcScs values are 120 and 240 kHz.";
            yext3gpp:inVariant;
            tailf:info 'Dependencies: Must match part of the id (see the NRFrequency description).
                If arfcnValueNRDl is less than 2016667 (FR1), valid smtcScs values are 15 and 30 kHz.
                If arfcnValueNRDl is greater or equal than 2016667 (FR2), valid smtcScs values are 120 and 240 kHz, Subcarrier Spacing for the SSBs. Broadcast in SIB4.';
        }
    }

    augment "/me3gpp:ManagedElement/gnbcucp3gpp:GNBCUCPFunction/nrnetwork:NRNetwork" {

        list NRFrequency {
            description
                "NRFrequency and related measurement parameters.

                This MO is created automatically. Can also be created and "+
                "deleted manually.

                Created automatically when X2, Xn, or F1 message is received, "+
                "unless it already exists.

                The RDN of this MO must be NRFrequency=arfcnValueNRDl-smtcScs.

                Example:
                NRFrequency=630000-30";
            key id;
            max-elements 64;
            uses top3gpp:Top_Grp;
            container attributes {
                uses NRFrequencyGrp;
            }

            must './id = concat(string(current()/attributes/arfcnValueNRDl),"-",string(current()/attributes/smtcScs))' {
                error-message
                    "The RDN of this MO must have the format NRFrequency=arfcnValueNRDl-smtcScs.";
            }
        }
    }
}
