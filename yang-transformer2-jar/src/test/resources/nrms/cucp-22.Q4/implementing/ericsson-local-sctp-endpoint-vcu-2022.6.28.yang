// Generated by eyang-preprocessor (1.22.0-48 2022-01-20 09:10:06 CET) on Jun 30, 2022, 8:31:38 AM
module ericsson-local-sctp-endpoint-vcu {
    yang-version 1.1;
    namespace urn:rdns:com:ericsson:oammodel:ericsson-local-sctp-endpoint-vcu;
    prefix localsctpep;

    import ericsson-transport-types-vcu {
        prefix transtypes;
    }
    import ericsson-yang-extensions {
        prefix yexte;
    }

    organization
        "Ericsson AB";
    contact
        "Ericsson first line support via email";
    description
        "The module defines the abstract LocalSctpEndpoint data model for the Ericsson vCU.

    Copyright (c) 2021-2022 Ericsson AB. All rights reserved.";

    revision 2022-06-28 {
        description
            "Removed module-status preliminary.";
        yexte:version 0;
        yexte:release 2;
        yexte:correction 0;
        reference
            "RFC 7950: The YANG 1.1 Data Modeling Language";
    }

    revision 2021-01-13 {
        description
            "Initial version of the abstract LocalSctpEndpoint model.";
        yexte:version 0;
        yexte:release 1;
        yexte:correction 0;
        reference
            "RFC 7950: The YANG 1.1 Data Modeling Language";
    }

    grouping LocalSctpEndpointGrp {
        description " Represents the LocalSctpEndpoint IOC.";

        leaf sctpEndpointId {
            description
                "Reference to used SctpEndpoint MO in the Transport Service.";
            mandatory true;
            type transtypes:ReferenceId;
        }

        leaf-list interfaceList {
            description
                "Contains all interface types using this endpoint.";
            type transtypes:InterfaceName;
        }
    }
}
