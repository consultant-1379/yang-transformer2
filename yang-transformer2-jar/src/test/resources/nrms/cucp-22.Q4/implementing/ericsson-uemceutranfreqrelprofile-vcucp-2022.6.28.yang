// Generated by eyang-preprocessor (1.22.0-48 2022-01-20 09:10:06 CET) on Jun 30, 2022, 8:31:44 AM
module ericsson-uemceutranfreqrelprofile-vcucp {
    yang-version 1.1;
    namespace "urn:rdns:com:ericsson:oammodel:ericsson-uemceutranfreqrelprofile-vcucp";
    prefix "uemceutranfreqrelprofilevcucp";

    import tailf-common {
        prefix tailf;
    }
    import _3gpp-common-managed-element {
        prefix "me3gpp";
    }
    import _3gpp-nr-nrm-gnbcucpfunction {
        prefix "gnbcucp3gpp";
    }
    import _3gpp-common-top {
        prefix "top3gpp";
    }
    import ericsson-yang-extensions {
        prefix "yexte";
    }
    import ericsson-uemc-vcucp {
        prefix "uemcvcucp";
    }
    import ericsson-common-types-vcucp {
        prefix "commontypes";
    }

    organization
      "Ericsson AB";
    contact
      "Ericsson first line support via email";
    description
      "The module defines the UeMCEUtranFreqRelProfile data model for the Ericsson vCU-CP.

       Copyright (c) 2021-2022 Ericsson AB. All rights reserved.";

    revision 2022-06-28 {
        description
            "Removed module-status preliminary.
             Removed preliminary status from ueConfGroupType.";
        yexte:version 1;
        yexte:release 1;
        yexte:correction 0;
        reference
            "RFC 7950: The YANG 1.1 Data Modeling Language";
    }

    revision 2022-03-14 {
        description
          "Updated description and precondition for UeMCEUtranFreqRelProfile.
           Marked blindRwrAllowed, connModeAllowedPCell and connModePrioPCell as obsolete.
           Added attributes ueConfGroupType and userLabel.";
        yexte:version 1;
        yexte:release 0;
        yexte:correction 0;
        reference
          "RFC 7950: The YANG 1.1 Data Modeling Language";
    }

    revision 2021-11-05 {
        description
          "Updated description and precondition for UeMCEUtranFreqRelProfile.";
        yexte:version 0;
        yexte:release 1;
        yexte:correction 1;
        reference
          "RFC 7950: The YANG 1.1 Data Modeling Language";
    }

    revision 2021-04-16 {
        description
          "Initial version of the UeMCEUtranFreqRelProfile model.";
        yexte:version 0;
        yexte:release 1;
        yexte:correction 0;
        reference
          "RFC 7950: The YANG 1.1 Data Modeling Language";
    }

    grouping UeMCEUtranFreqRelProfileGrp {
        description
          "Represents the UeMCEUtranFreqRelProfile IOC.";

        leaf blindRwrAllowed {
            description
              "Whether this frequency relation is used as blind release with redirect candidate.

               Applied at blind release with redirect triggered by poor coverage or when UE fails capability check.

               If true for more than one E-UTRAN frequency relation, frequency relation with lowest ARFCN is used.
               If false for all E-UTRAN frequency relations, UE will be released to idle without redirection.";
            type boolean;
            status obsolete {
                yexte:status-information
                "Since 22.Q1. Replaced by "+
                "UeMCEUtranFreqRelProfileUeCfg::blindRwrAllowed. Planned to be "+
                "removed.";
            }
            yexte:dependencies
              "Value true is only allowed if connModeAllowedPCell is true.";
            yexte:takes-effect
              "Next usage.";
            tailf:info 'Takes effect: Next usage, Dependencies: Value true is only allowed if connModeAllowedPCell is true, Status Info: Since 22.Q1. Replaced by UeMCEUtranFreqRelProfileUeCfg::blindRwrAllowed. Planned to be removed, Obsolete, Whether this frequency relation is used as blind release with redirect candidate. Applied at blind release with redirect triggered by poor coverage or when UE fails capability check. If true for more than one E-UTRAN frequency relation, frequency relation with lowest ARFCN is used. If false for all E-UTRAN frequency relations, UE will be released to idle without redirection.';
        }

        leaf connModeAllowedPCell {
            description
              "Whether placing PCell on E-UTRAN frequency defined by E-UTRAN frequency relation is allowed.

               Applies to UEs that use cell as PCell for poor coverage triggered handover or blind release with redirect to this cell. Blind release with redirect can be triggered by poor coverage or when UE fails capability check.";
            type boolean;
            status obsolete {
                yexte:status-information
                "Since 22.Q1. Replaced by "+
                "UeMCEUtranFreqRelProfileUeCfg::connModeAllowedPCell. Planned to be "+
                "removed.";
            }
            yexte:dependencies
              "Value false is not allowed if blindRwrAllowed is true..";
            yexte:takes-effect
              "Next usage.";
            tailf:info 'Takes effect: Next usage, Dependencies: Value false is not allowed if blindRwrAllowed is true., Status Info: Since 22.Q1. Replaced by UeMCEUtranFreqRelProfileUeCfg::connModeAllowedPCell. Planned to be removed, Obsolete, Whether placing PCell on E-UTRAN frequency defined by E-UTRAN frequency relation is allowed. Applies to UEs that use cell as PCell for poor coverage triggered handover or blind release with redirect to this cell. Blind release with redirect can be triggered by poor coverage or when UE fails capability check.';
        }

        leaf connModePrioPCell {
            description
              "Connected mode PCell priority for E-UTRAN frequency relation.

               Applies to UEs that use cell as PCell.

               Used to decide preference on which E-UTRAN frequency to place PCell in connected mode.

               0 means frequency relation with lowest priority.
               7 means frequency relation with highest priority.

               Applicable only when connModeAllowedPCell attribute is set to true.";
            type int32 {
                range "0..7";
            }
            status obsolete {
                yexte:status-information
                "Since 22.Q1. Replaced by "+
                "UeMCEUtranFreqRelProfileUeCfg::connModePrioPCell. Planned to be "+
                "removed.";
            }
            yexte:takes-effect
              "Next usage.";
            tailf:info 'Takes effect: Next usage, Status Info: Since 22.Q1. Replaced by UeMCEUtranFreqRelProfileUeCfg::connModePrioPCell. Planned to be removed, Obsolete, Connected mode PCell priority for E-UTRAN frequency relation. Applies to UEs that use cell as PCell. Used to decide preference on which E-UTRAN frequency to place PCell in connected mode. 0 means frequency relation with lowest priority. 7 means frequency relation with highest priority. Applicable only when connModeAllowedPCell attribute is set to true.';
        }

        leaf ueConfGroupType {
            description
              "UE configuration Group Type.

              Defines which UE configuration group type that is applied in the "+
              "contained MO class UeMCEUtranFreqRelProfileUeCfg.";
            type commontypes:UeConfGroupType;
            default UE_MOBILITY_GROUP;
            yexte:disturbances
              "Changing this attribute can cause loss of traffic.";
            yexte:takes-effect
              "Next usage.";
            tailf:info 'Takes effect: Next usage, Traffic Disturbance: Changing this attribute can cause loss of traffic, UE configuration Group Type. Defines which UE configuration group type that is applied in the contained MO class UeMCEUtranFreqRelProfileUeCfg.';
        }
    }

    augment "/me3gpp:ManagedElement/gnbcucp3gpp:GNBCUCPFunction/uemcvcucp:UeMC" {
        list UeMCEUtranFreqRelProfile {
            description
              "UE mobility control attributes used on E-UTRAN frequency "+
              "relation level.

              MO instance UeMCEUtranFreqRelProfile=Default is created "+
              "automatically when parent MO is created, unless created manually "+
              "in the same transaction as parent MO.

              If EUtranFreqRelation::ueMCEUtranFreqRelProfileRef attribute is "+
              "non-empty, attributes from referred MO instance are used.
              If EUtranFreqRelation::ueMCEUtranFreqRelProfileRef attribute is "+
              "empty, attribute default values according to "+
              "UeMCEUtranFreqRelProfile and UeMCEUtranFreqRelProfileUeCfg MO "+
              "class definitions are used.";
            yexte:precondition
              "UeMCEUtranFreqRelProfile=Default MO instance can only be created "+
              "in the same transaction as parent MO and must not be deleted "+
              "unless parent MO is deleted. Other instances can be created and "+
              "deleted manually.";
            key id;
            uses top3gpp:Top_Grp;
            container attributes {
                uses UeMCEUtranFreqRelProfileGrp;
                uses commontypes:UserLabelGrp;
            }
            tailf:info 'Precondition: UeMCEUtranFreqRelProfile=Default MO instance can only be created in the same transaction as parent MO and must not be deleted unless parent MO is deleted. Other instances can be created and deleted manually, UE mobility control attributes used on E-UTRAN frequency relation level. MO instance UeMCEUtranFreqRelProfile=Default is created automatically when parent MO is created, unless created manually in the same transaction as parent MO. If EUtranFreqRelation::ueMCEUtranFreqRelProfileRef attribute is non-empty, attributes from referred MO instance are used. If EUtranFreqRelation::ueMCEUtranFreqRelProfileRef attribute is empty, attribute default values according to UeMCEUtranFreqRelProfile and UeMCEUtranFreqRelProfileUeCfg MO class definitions are used.';
        }
    }
}
