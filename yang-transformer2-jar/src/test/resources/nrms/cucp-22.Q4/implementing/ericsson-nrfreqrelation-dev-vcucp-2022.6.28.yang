// Generated by eyang-preprocessor (1.22.0-48 2022-01-20 09:10:06 CET) on Jun 30, 2022, 8:31:42 AM
module ericsson-nrfreqrelation-dev-vcucp {
    yang-version 1.1;
    namespace urn:rdns:com:ericsson:oammodel:ericsson-nrfreqrelation-dev-vcucp;
    prefix nrfreqrel3gppdev;

    import _3gpp-common-managed-element {
        prefix me3gpp;
    }
    import _3gpp-nr-nrm-gnbcucpfunction {
        prefix gnbcucp3gpp;
    }
    import _3gpp-nr-nrm-nrcellcu {
        prefix nrcellcu3gpp;
    }
    import _3gpp-nr-nrm-nrfreqrelation {
        prefix nrfreqrel3gpp;
    }
    import ericsson-nrcellcu-ext-vcucp {
        prefix nrcellcu3gppext;
    }
    import ericsson-yang-extensions {
        prefix yexte;
    }

    organization
      "Ericsson AB";
    contact
      "Ericsson first line support via email";
    description
      "The module defines the NRFreqRelation data model deviations for the Ericsson vCU-CP.

       Copyright (c) 2021-2022 Ericsson AB. All rights reserved.";

    revision 2022-06-28 {
        description
            "Removed module-status preliminary.";
        yexte:version 0;
        yexte:release 3;
        yexte:correction 0;
        reference
            "RFC 7950: The YANG 1.1 Data Modeling Language";
    }

    revision 2022-03-14 {
        description
            "Removed not-supported from cellReselectionSubPriority.";
        yexte:version 0;
        yexte:release 2;
        yexte:correction 0;
        reference
          "RFC 7950: The YANG 1.1 Data Modeling Language";
    }
    revision 2021-06-06 {
        description
          "Add must rules related to threshXHighQ and threshXLowQ.";
        yexte:version 0;
        yexte:release 1;
        yexte:correction 1;
        reference
          "RFC 7950: The YANG 1.1 Data Modeling Language";
    }
    revision 2021-03-22 {
        description
          "Initial version of the NRFreqRelation model.";
        yexte:version 0;
        yexte:release 1;
        yexte:correction 0;
        reference
          "RFC 7950: The YANG 1.1 Data Modeling Language";
    }

    deviation /me3gpp:ManagedElement/gnbcucp3gpp:GNBCUCPFunction/nrcellcu3gpp:NRCellCU/nrfreqrel3gpp:NRFreqRelation/nrfreqrel3gpp:ManagedNFService {
        description
          "Managed Network Function Service is not supported for NRFreqRelation.";
        deviate not-supported;
    }

    deviation /me3gpp:ManagedElement/gnbcucp3gpp:GNBCUCPFunction/nrcellcu3gpp:NRCellCU/nrfreqrel3gpp:NRFreqRelation/nrfreqrel3gpp:PerfMetricJob {
        description
          "Performance Metric Job is not supported for NRFreqRelation.";
        deviate not-supported;
    }

    deviation /me3gpp:ManagedElement/gnbcucp3gpp:GNBCUCPFunction/nrcellcu3gpp:NRCellCU/nrfreqrel3gpp:NRFreqRelation/nrfreqrel3gpp:ThresholdMonitor {
        description
          "Threshold Monitor is not supported for NRFreqRelation.";
        deviate not-supported;
    }

    deviation /me3gpp:ManagedElement/gnbcucp3gpp:GNBCUCPFunction/nrcellcu3gpp:NRCellCU/nrfreqrel3gpp:NRFreqRelation/nrfreqrel3gpp:TraceJob {
        description
          "Trace Job is not supported for NRFreqRelation.";
        deviate not-supported;
    }

    deviation /me3gpp:ManagedElement/gnbcucp3gpp:GNBCUCPFunction/nrcellcu3gpp:NRCellCU/nrfreqrel3gpp:NRFreqRelation/nrfreqrel3gpp:attributes/nrfreqrel3gpp:offsetMO {
        description
          "NRFreqRelation::offsetMO is not supported.";
        deviate not-supported;
    }
    deviation /me3gpp:ManagedElement/gnbcucp3gpp:GNBCUCPFunction/nrcellcu3gpp:NRCellCU/nrfreqrel3gpp:NRFreqRelation/nrfreqrel3gpp:attributes/nrfreqrel3gpp:blackListEntry {
        description
          "NRFreqRelation::blackListEntry is not supported.";
        deviate not-supported;
    }

    deviation /me3gpp:ManagedElement/gnbcucp3gpp:GNBCUCPFunction/nrcellcu3gpp:NRCellCU/nrfreqrel3gpp:NRFreqRelation/nrfreqrel3gpp:attributes/nrfreqrel3gpp:blackListEntryIdleMode {
        description
          "NRFreqRelation::blackListEntryIdleMode is not supported.";
        deviate not-supported;
    }

    deviation "/me3gpp:ManagedElement/gnbcucp3gpp:GNBCUCPFunction/nrcellcu3gpp:NRCellCU/nrfreqrel3gpp:NRFreqRelation/nrfreqrel3gpp:attributes" {
        deviate add {
            must "(./nrfreqrel3gpp:threshXHighQ and ../../nrcellcu3gpp:attributes/nrcellcu3gppext:threshServingLowQ) or
                  (not(./nrfreqrel3gpp:threshXHighQ) and not(../../nrcellcu3gpp:attributes/nrcellcu3gppext:threshServingLowQ))" {
                error-message
                  "threshXHighQ must be empty if NRCellCU::threshServingLowQ is empty or set if "
                + "NRCellCU::threshServingLowQ is set.";
            }
            must "(./nrfreqrel3gpp:threshXLowQ and ../../nrcellcu3gpp:attributes/nrcellcu3gppext:threshServingLowQ) or
                  (not(./nrfreqrel3gpp:threshXLowQ) and not(../../nrcellcu3gpp:attributes/nrcellcu3gppext:threshServingLowQ))" {
                error-message
                  "threshXLowQ must be empty if NRCellCU::threshServingLowQ is empty or set if "
                + "NRCellCU::threshServingLowQ is set.";
            }
        }
    }
}
