// Generated by eyang-preprocessor (1.22.0-48 2022-01-20 09:10:06 CET) on Jun 30, 2022, 8:31:37 AM
module ericsson-externaleutrancell-vcucp {
    yang-version 1.1;
    namespace "urn:rdns:com:ericsson:oammodel:ericsson-externaleutrancell-vcucp";
    prefix "exteutrancell";

    import tailf-common {
        prefix tailf;
    }
    import _3gpp-common-managed-element {
        prefix "me3gpp";
    }
    import _3gpp-nr-nrm-gnbcucpfunction {
        prefix "gnbcucp3gpp";
    }
    import _3gpp-common-yang-types {
        prefix "types3gpp";
    }
    import _3gpp-common-top {
        prefix "top3gpp";
    }
    import ericsson-eutranetwork-vcucp {
        prefix "eutranet";
    }
    import ericsson-eutranfrequency-vcucp {
        prefix "eutranfrequency";
    }
    import ericsson-externalenbfunction-vcucp {
        prefix "extenb";
    }
    import ericsson-yang-extensions {
        prefix "yexte";
    }

    organization
        "Ericsson AB";
    contact
        "Ericsson first line support via email";
    description
        "The module defines the ExternalEUtranCell data model for the Ericsson vCU-CP.

        Copyright (c) 2021-2022 Ericsson AB. All rights reserved.";

    revision 2022-06-28 {
        description
            "Removed module-status preliminary.";
        yexte:version 3;
        yexte:release 1;
        yexte:correction 0;
        reference
            "RFC 7950: The YANG 1.1 Data Modeling Language";
    }

    revision 2022-03-14 {
        description
            "Updated description of eUtranFrequencyRef";
        yexte:version 3;
        yexte:release 0;
        yexte:correction 2;
        reference
            "RFC 7950: The YANG 1.1 Data Modeling Language";
    }

    revision 2021-11-05 {
        description
            "Fix must statement for cellLocalId";
        yexte:version 3;
        yexte:release 0;
        yexte:correction 1;
        reference
            "RFC 7950: The YANG 1.1 Data Modeling Language";
    }

    revision 2021-09-02 {
        description
            "Bug Fix, remove mandatory from operationalState, and update description.";
        yexte:version 3;
        yexte:release 0;
        yexte:correction 0;
        reference
            "RFC 7950: The YANG 1.1 Data Modeling Language";
    }

    revision 2021-06-08 {
        description
            "Changed error messages for must statements.";
        yexte:version 2;
        yexte:release 1;
        yexte:correction 1;
        reference
            "RFC 7950: The YANG 1.1 Data Modeling Language";
    }

    revision 2021-05-06 {
        description
            "Remove is-system-created and restricted extensions from configurable attributes";
        yexte:version 2;
        yexte:release 1;
        yexte:correction 0;
        reference
            "RFC 7950: The YANG 1.1 Data Modeling Language";
    }

    revision 2021-03-30 {
        description
            "Add Ericsson descriptions and tags to attributes.
             Replaced the separate ExternalEUtranCellFDD/TDD lists under ExternalENBFunction
              with an ExternalEUtranCell list.";
        yexte:version 2;
        yexte:release 0;
        yexte:correction 0;
        reference
            "RFC 7950: The YANG 1.1 Data Modeling Language";
    }

    revision 2021-03-24 {
        description
            "Correct must statement for MO reference.";
        yexte:version 1;
        yexte:release 1;
        yexte:correction 1;
        reference
            "RFC 7950: The YANG 1.1 Data Modeling Language";
    }

    revision 2021-03-22 {
        description
            "Parity with ECIM R1A79.";
        yexte:version 1;
        yexte:release 1;
        yexte:correction 0;
        reference
            "RFC 7950: The YANG 1.1 Data Modeling Language";
    }

    revision 2021-02-22 {
        description
            "Correct order for revision history.";
        yexte:version 1;
        yexte:release 0;
        yexte:correction 1;
        reference
            "RFC 7950: The YANG 1.1 Data Modeling Language";
    }

    revision 2021-01-20 {
        description
            "Add extensions is-system-created and restricted.";
        yexte:version 1;
        yexte:release 0;
        yexte:correction 0;
        reference
            "RFC 7950: The YANG 1.1 Data Modeling Language";
    }

    revision 2021-01-11 {
        description
            "Initial version of the ExternalEUtranCell model.";
        yexte:version 0;
        yexte:release 1;
        yexte:correction 0;
        reference
            "RFC 7950: The YANG 1.1 Data Modeling Language";
    }

    grouping ExternalEUtranCellGrp {
        description "Represents the ExternalEUtranCell IOC.";

        list pLMNIdList {
            description "Additional PLMN IDs supported in External E-UTRAN cell.";
            key "mcc mnc";
            max-elements 5;
            uses types3gpp:PLMNId;
            yexte:takes-effect "New connection";
            tailf:info 'Takes effect: New connection, Additional PLMN IDs supported in External E-UTRAN cell.';
        }

        leaf cellLocalId {
            description
                "RBS internal ID attribute for EUtranCell.

                Together with node ID and PLMN, this is a universally unique cell ID.";
            type int32 {
                range "0..255";
            }
            default 0;
            must ". = 0 or (count(../../../exteutrancell:ExternalEUtranCell/exteutrancell:attributes/exteutrancell:cellLocalId[current() = .])) = 1" {
                error-message
                    "All ExternalEUtranCells under the same ExternalENBFunction must have a unique cellLocalId.";
            }
            yexte:dependencies
                "Must be unique among all ExternalEUtranCell MO instances within an "+
                "ExternalENBFunction MO instance.";
            tailf:info 'Dependencies: Must be unique among all ExternalEUtranCell MO instances within an ExternalENBFunction MO instance, RBS internal ID attribute for EUtranCell. Together with node ID and PLMN, this is a universally unique cell ID.';
        }

        leaf dlChannelBandwidth {
            description
                "DL channel bandwidth in LTE cell.

                Empty if there is no EN-DC X2 connection.";
            config false;
            type int32 {
                range "1400|3000|5000|10000|15000|20000";
            }
            units kHz;
        }

        leaf earfcnDL {
            description
                "Channel number for central DL frequency.

                Mapping from channel number to physical frequency for specified "+
                "E-UTRA bands is described in 3GPP TS 36.104. Values that can be used "+
                "depend on national, operator-specific frequency allocation and on "+
                "supported frequency bands in RBS.

                Empty if there is no EN-DC X2 connection.";
            config false;
            type int32 {
                range "1..17999|46590..262143";
            }
            reference
                "3GPP TS 28.541";
        }

        leaf earfcnUL {
            description
                "Channel number for central UL frequency.

                Mapping from channel number to physical frequency for specified "+
                "E-UTRA bands is described in 3GPP TS 36.104. Values that can be used "+
                "depend on national, operator-specific frequency allocation and on "+
                "supported frequency bands in RBS. Value 0 means UL channel number is "+
                "not available for the DL-only bands.

                Empty if there is no EN-DC X2 connection.";
            config false;
            type int32 {
                range "0|18000..35999|46590..262143";
            }
            reference
                "3GPP TS 28.541";
        }

        leaf eUtranFrequencyRef {
            description
                "Reference to an instance of EUtranFrequency MO.

                Referenced EUtranFrequency must be under EUtraNetwork under the same "+
                "GNBCUCPFunction as ExternalEUtranCell.

                If empty, ExternalEUtranCell MO instance is not selected as target "+
                "cell of IRAT handover from NR to LTE.";
            type types3gpp:DistinguishedName;
            must "re-match(current(), 'ManagedElement=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,GNBCUCPFunction=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,EUtraNetwork=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,EUtranFrequency=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?') and
                  re-match(current(), concat('ManagedElement=', ../../../../../../me3gpp:id, ',.*')) and
                  re-match(current(), concat('.*GNBCUCPFunction=', ../../../../../gnbcucp3gpp:id, ',.*')) and
                  count(../../../../../eutranet:EUtraNetwork[re-match(current(), concat('.*EUtraNetwork=', eutranet:id, ',.*'))]/eutranfrequency:EUtranFrequency[re-match(current(), concat('.*EUtranFrequency=', eutranfrequency:id))]) &gt; 0" {
                error-message
                    "eUtranFrequencyRef must refer to an EUtranFrequency under the same GNBCUCPFunction.";
            }
            yexte:takes-effect "Next usage.";
            tailf:info 'Takes effect: Next usage, Reference to an instance of EUtranFrequency MO. Referenced EUtranFrequency must be under EUtraNetwork under the same GNBCUCPFunction as ExternalEUtranCell. If empty, ExternalEUtranCell MO instance is not selected as target cell of IRAT handover from NR to LTE.';
        }

        leaf operationalState {
            description
              "The operational state.";
            type types3gpp:OperationalState;
            config false;
            reference "ITU-T Rec. X.731";
        }

        leaf pci {
            description "Physical-layer cell ID.";
            type int32 {
                range "0..503";
            }
            default 0;
            reference "3GPP TS 36.211";
            yexte:takes-effect "Next usage.";
            tailf:info 'Takes effect: Next usage, Physical-layer cell ID.';
        }

        leaf tac {
            description
                "TAC for external E-UTRAN cell.";
            type int32 {
                range "0..65535";
            }
            default 0;
            yexte:takes-effect "Next usage.";
            tailf:info 'Takes effect: Next usage, TAC for external E-UTRAN cell.';
        }

        leaf ulChannelBandwidth {
            description
                "UL channel bandwidth in LTE cell.

                Empty if there is no EN-DC X2 connection.";
            config false;
            type int32 {
                range "1400|3000|5000|10000|15000|20000";
            }
            units kHz;
        }
    }

    augment "/me3gpp:ManagedElement/gnbcucp3gpp:GNBCUCPFunction/eutranet:EUtraNetwork/extenb:ExternalENBFunction" {
        list ExternalEUtranCell {
            description
                "External E-UTRAN cell.

                Contains parameters that are specific for this cell.";
            key id;
            max-elements 24;
            uses top3gpp:Top_Grp;
            container attributes {
                uses ExternalEUtranCellGrp;
            }
            reference "3GPP TS 28.658";
        }
    }
}
