// Generated by eyang-preprocessor (1.22.0-48 2022-01-20 09:10:06 CET) on Jun 30, 2022, 8:31:44 AM
module ericsson-termpointtognb-vcucp {
    yang-version 1.1;
    namespace "urn:rdns:com:ericsson:oammodel:ericsson-termpointtognb-vcucp";
    prefix "tptognb";

    import tailf-common {
        prefix tailf;
    }
    import _3gpp-common-managed-element {
        prefix "me3gpp";
    }
    import _3gpp-nr-nrm-gnbcucpfunction {
        prefix "gnbcucp3gpp";
    }
    import _3gpp-common-yang-types {
        prefix "types3gpp";
    }
    import _3gpp-common-top {
        prefix "top3gpp";
    }
    import ietf-inet-types {
        prefix "inet";
    }
    import ericsson-nrnetwork-vcucp {
        prefix "nrnetwork";
    }
    import ericsson-externalgnbcucpfunction-vcucp {
        prefix "externalgnbcucpfunctionvcucp";
    }
    import ericsson-yang-extensions {
        prefix "yexte";
    }
    import ericsson-yang-types {
        prefix "typese";
    }
    import ericsson-notifications {
        prefix notife;
    }

    organization
      "Ericsson AB";
    contact
      "Ericsson first line support via email";
    description
      "The module defines the TermPointToGNB data model for the Ericsson vCU-CP.

       Copyright (c) 2021-2022 Ericsson AB. All rights reserved.";

    revision 2022-06-28 {
        description
            "Removed module-status preliminary.";
        yexte:version 1;
        yexte:release 2;
        yexte:correction 0;
        reference
            "RFC 7950: The YANG 1.1 Data Modeling Language";
    }

    revision 2021-11-05 {
        description
            "Update the description for administrativeState, ipv4Address, and ipv6Address.
            Update takes-effect and remove precondition for ipv4Address and ipv6Address.";
        yexte:version 1;
        yexte:release 1;
        yexte:correction 1;
        reference
            "RFC 7950: The YANG 1.1 Data Modeling Language";
    }

    revision 2021-07-27 {
        description
            "Bug Fix, leaf-list state notifiable compatibility issue. Adds extension notife:notifiable-state-data false to availabilityStatus.";
        yexte:version 1;
        yexte:release 1;
        yexte:correction 0;
        reference
            "RFC 7950: The YANG 1.1 Data Modeling Language";
    }

    revision 2021-05-06 {
        description
            "Remove is-system-created and restricted extensions from configurable attributes";
        yexte:version 0;
        yexte:release 2;
        yexte:correction 0;
        reference
            "RFC 7950: The YANG 1.1 Data Modeling Language";
    }

    revision 2021-04-30 {
        description
          "Corrected description and tags for the usedIpAddress attribute.";
        yexte:version 0;
        yexte:release 1;
        yexte:correction 1;
        reference
          "RFC 7950: The YANG 1.1 Data Modeling Language";
    }

    revision 2021-03-29 {
        description
          "Initial version of the TermPointToGNB model.";
        yexte:version 0;
        yexte:release 1;
        yexte:correction 0;
        reference
          "RFC 7950: The YANG 1.1 Data Modeling Language";
    }

    grouping TermPointToGNBGrp {
        description
          "Represents the TermPointToGNB IOC.";

        leaf administrativeState {
            description
              "The administrative state.

              If set to SHUTTINGDOWN, the state is immediately brought to LOCKED.";
            type types3gpp:AdministrativeState;
            default LOCKED;
            reference
              "ITU-T Rec. X.731";
            yexte:disturbances "Changing this attribute to LOCKED causes loss of traffic.";
            tailf:info 'Traffic Disturbance: Changing this attribute to LOCKED causes loss of traffic, The administrative state. If set to SHUTTINGDOWN, the state is immediately brought to LOCKED.';
        }

        leaf-list availabilityStatus {
            description
              "The availability status.

               It contains details about operational state.";
            type typese:avail-status;
            config false;
            notife:notifiable-state-data false;
            reference
              "ITU-T Rec. X.731";
            tailf:meta-data notife:notifiable-state-data {
                tailf:meta-value false;
            }
        }

        leaf ipv4Address {
            description
              "IPv4 address of the peer gNodeB.

               Four fields, separated by dots.

              Each field consists of up to three digits. Value of each field is in "+
              "range 0-255.

              This attribute can be overridden by system if "+
              "GNBCUCPFunction::xnIpAddrViaNgActive is true.";
            type inet:ipv4-address-no-zone;
            yexte:initial-value "0.0.0.0";
            yexte:takes-effect
              "Next MO unlock if changed by operator";
            tailf:info 'Takes effect: Next MO unlock if changed by operator, IPv4 address of the peer gNodeB. Four fields, separated by dots. Each field consists of up to three digits. Value of each field is in range 0-255. This attribute can be overridden by system if GNBCUCPFunction::xnIpAddrViaNgActive is true.';
        }

        leaf ipv6Address {
            description
              "IPv6 address of peer gNodeB.

              Eight fields, separated by colons.

              Each field consists of up to four hexadecimal characters. Value of "+
              "each field is in range 0-FFFF.

              Leading zeroes can be omitted in a field, and multiple groups of 16 "+
              "bits of zeroes can be compressed to ::

              The :: can appear only once in an address.

              This attribute can be overridden by system if "+
              "GNBCUCPFunction::xnIpAddrViaNgActive is true.";
            type inet:ipv6-address-no-zone;
            yexte:initial-value "::";
            yexte:takes-effect
              "Next MO unlock if changed by operator";
            tailf:info 'Takes effect: Next MO unlock if changed by operator, IPv6 address of peer gNodeB. Eight fields, separated by colons. Each field consists of up to four hexadecimal characters. Value of each field is in range 0-FFFF. Leading zeroes can be omitted in a field, and multiple groups of 16 bits of zeroes can be compressed to :: The :: can appear only once in an address. This attribute can be overridden by system if GNBCUCPFunction::xnIpAddrViaNgActive is true.';
        }

        leaf operationalState {
            description
              "The operational state.";
            type types3gpp:OperationalState;
            config false;
            reference
              "ITU-T Rec. X.731";
        }

        leaf usedIpAddress {
            description
              "Destination address used in underlying SCTP association.";
            config false;
            type string;
        }

        list usedPLMNId {
            description
              "PLMNId used in underlying SCTP association.

               Used to select SctpEndPoint of Xn-C in local IP address selection for SCTP association.";
            max-elements 1;
            config false;
            uses types3gpp:PLMNId;
        }
    }

    augment "/me3gpp:ManagedElement/gnbcucp3gpp:GNBCUCPFunction/nrnetwork:NRNetwork/externalgnbcucpfunctionvcucp:ExternalGNBCUCPFunction" {
        list TermPointToGNB {
            description
              "Local gNodeB termination point of Xn link between gNodeB and neighbor gNodeB.

               This MO is created automatically. Can also be created and deleted manually.

               Created automatically when Xn interface is set up, unless it already exists.
               Deleted automatically.

               When created automatically, the RDN of this MO is TermPointToGNB=auto1.";
            key id;
            max-elements 1;
            uses top3gpp:Top_Grp;
            container attributes {
                uses TermPointToGNBGrp;
            }
            reference
              "3GPP TS 38.423";
        }
    }
}
