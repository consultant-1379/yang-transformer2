// Generated by eyang-preprocessor (1.22.0-48 2022-01-20 09:10:06 CET) on Sep 4, 2022, 12:23:59 PM
module ericsson-up-sel-entry-ue-cfg-vcucp {
    yang-version 1.1;
    namespace urn:rdns:com:ericsson:oammodel:ericsson-up-sel-entry-ue-cfg-vcucp;
    prefix upselentryuecfgvcucp;

    import tailf-common {
        prefix tailf;
    }
    import _3gpp-common-managed-element {
        prefix me3gpp;
    }
    import _3gpp-nr-nrm-gnbcucpfunction {
        prefix gnbcucp3gpp;
    }
    import _3gpp-common-top {
        prefix top3gpp;
    }
    import _3gpp-common-yang-types {
        prefix types3gpp;
    }
    import ericsson-yang-extensions {
        prefix yexte;
    }
    import ericsson-up-selection-vcucp {
        prefix upselectionvcucp;
    }
    import ericsson-up-sel-table-vcucp {
        prefix upseltablevcucp;
    }
    import ericsson-up-sel-entry-vcucp {
        prefix upselentryvcucp;
    }
    import ericsson-up-domains-vcucp {
        prefix updomainsvcucp;
    }
    import ericsson-up-domain-vcucp {
        prefix updomainvcucp;
    }

    organization
      "Ericsson AB";
    contact
      "Ericsson first line support via email";
    description
      "The module defines the UPSelEntryUeCfg data model for the Ericsson vCU-CP.

       Copyright (c) 2022 Ericsson AB. All rights reserved.";

    revision 2022-08-29 {
        description
          "Removed module-status preliminary.
           Removed preliminary status from:
            - list UPSelEntryUeCfg
            - leaf upDomainRef";
        yexte:version 0;
        yexte:release 2;
        yexte:correction 0;
        reference
          "RFC 7950: The YANG 1.1 Data Modeling Language";
    }

    revision 2022-04-20 {
        description
          "Initial version of the UPSelEntryUeCfg model";
        yexte:version 0;
        yexte:release 1;
        yexte:correction 0;
        reference
          "RFC 7950: The YANG 1.1 Data Modeling Language";
    }

    grouping UPSelEntryUeCfgGrp {
        description
          "Represents the UPSelEntryUeCfg IOC.";
        leaf upDomainRef {
            description
              "Reference to UPDomain MO instance.

               Automatically set to UPDomain=Default MO instance, unless manually set to refer to another MO instance.";

            type types3gpp:DistinguishedName;
            must "re-match(current(), 'ManagedElement=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,GNBCUCPFunction=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,UPSelection=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,UPDomains=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,UPDomain=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?') and
                  re-match(current(), concat('ManagedElement=', ../../../../../../../me3gpp:id, ',.*')) and
                  re-match(current(), concat('.*GNBCUCPFunction=', ../../../../../../gnbcucp3gpp:id, ',.*')) and
                  re-match(current(), concat('.*UPSelection=', ../../../../../upselectionvcucp:id, ',.*')) and
                  count(../../../../../updomainsvcucp:UPDomains[re-match(current(), concat('.*UPDomains=', updomainsvcucp:id, ',.*'))]/updomainvcucp:UPDomain[re-match(current(), concat('.*UPDomain=', updomainvcucp:id))]) > 0" {
                error-message
                  "upDomainRef must refer to an UPDomain under the same GNBCUCPFunction.";
            }
            yexte:dependencies
                "Referenced UPDomain must be under same GNBCUCPFunction.

                A PLMN ID can not belong to more than one UPSelEntry instance that reference the same UPDomain instance.";
            yexte:takes-effect
              "New connection";
            tailf:info 'Takes effect: New connection, Dependencies: Referenced UPDomain must be under same GNBCUCPFunction.

                A PLMN ID can not belong to more than one UPSelEntry instance that reference the same UPDomain instance, Reference to UPDomain MO instance. Automatically set to UPDomain=Default MO instance, unless manually set to refer to another MO instance.';
        }
    }

    augment "/me3gpp:ManagedElement/gnbcucp3gpp:GNBCUCPFunction/upselectionvcucp:UPSelection/upseltablevcucp:UPSelTable/upselentryvcucp:UPSelEntry" {
        list UPSelEntryUeCfg {
            description
              "Represents User Plane Selection Entry UE Config.


               MO instance UPSelEntryUeCfg=Base is created "
            + "automatically when parent MO is created, unless created "
            + "manually in the same transaction as parent MO.";
            key id;
            max-elements 1;
            uses top3gpp:Top_Grp {
                refine id {
                    must '. = "Base"' {
                        error-message
                          "The RDN of this MO must always be UPSelEntryUeCfg=Base";
                    }
                }
            }
            container attributes {
                uses UPSelEntryUeCfgGrp;
            }
            yexte:precondition
                "UPSelEntryUeCfg=Base MO instance must not be deleted unless parent MO is deleted.";
            tailf:info 'Precondition: UPSelEntryUeCfg=Base MO instance must not be deleted unless parent MO is deleted, Represents User Plane Selection Entry UE Config. MO instance UPSelEntryUeCfg=Base is created automatically when parent MO is created, unless created manually in the same transaction as parent MO.';
        }
    }
}
