// Generated by eyang-preprocessor (1.22.0-48 2022-01-20 09:10:06 CET) on Sep 4, 2022, 12:23:59 PM
module ericsson-up-domain-vcucp {
    yang-version 1.1;
    namespace urn:rdns:com:ericsson:oammodel:ericsson-up-domain-vcucp;
    prefix updomainvcucp;

    import tailf-common {
        prefix tailf;
    }
    import _3gpp-common-managed-element {
        prefix me3gpp;
    }
    import _3gpp-nr-nrm-gnbcucpfunction {
        prefix gnbcucp3gpp;
    }
    import _3gpp-common-top {
        prefix top3gpp;
    }
    import ericsson-yang-extensions {
        prefix yexte;
    }
    import ericsson-up-selection-vcucp {
        prefix upselectionvcucp;
    }
    import ericsson-up-domains-vcucp {
        prefix updomainsvcucp;
    }

    organization
      "Ericsson AB";
    contact
      "Ericsson first line support via email";
    description
      "The module defines the UPDomain data model for the Ericsson vCU-CP.

       Copyright (c) 2022 Ericsson AB. All rights reserved.";

    revision 2022-08-29 {
        description
          "Removed module-status preliminary.
           Removed preliminary status from:
            - list UPDomain
            - leaf userPlaneDomain";
        yexte:version 0;
        yexte:release 2;
        yexte:correction 0;
        reference
          "RFC 7950: The YANG 1.1 Data Modeling Language";
    }

    revision 2022-04-20 {
        description
          "Initial version of the UPDomain model";
        yexte:version 0;
        yexte:release 1;
        yexte:correction 0;
        reference
          "RFC 7950: The YANG 1.1 Data Modeling Language";
    }

    grouping UPDomainGrp {
        description
          "Represents the UPDomain IOC.";
        leaf userPlaneDomain {
            description
              "User Plane Domain name.

              Must match CUUPTemplate::userPlaneDomain for at least one CU-UP instance.

              Value set to 'defaultUPD' in automatically created instance UPDomain=Default.";
            type string;
            mandatory true;
            yexte:disturbances
                "Changing this attribute can cause loss of traffic.";
            yexte:dependencies
                "userPlaneDomain must be unique across UPDomain MO instances.

                Value 'defaultUPD' is only allowed in UPDomain=Default instance";
            yexte:takes-effect
                "New connection";
            tailf:info "Takes effect: New connection, Dependencies: userPlaneDomain must be unique across UPDomain MO instances.

                Value 'defaultUPD' is only allowed in UPDomain=Default instance, Traffic Disturbance: Changing this attribute can cause loss of traffic, User Plane Domain name. Must match CUUPTemplate::userPlaneDomain for at least one CU-UP instance. Value set to 'defaultUPD' in automatically created instance UPDomain=Default.";
        }
    }

    augment "/me3gpp:ManagedElement/gnbcucp3gpp:GNBCUCPFunction/upselectionvcucp:UPSelection/updomainsvcucp:UPDomains" {
        list UPDomain {
            description
              "Representation of a User Plane Domain.

               MO instance UPDomain=Default is created "
            + "automatically when parent MO is created, unless created "
            + "manually in the same transaction as parent MO.";
            key id;
            uses top3gpp:Top_Grp;
            unique "attributes/userPlaneDomain";
            container attributes {
                uses UPDomainGrp;
            }
            yexte:precondition
                "UPDomain=Default MO instance can only be created " +
                "in the same transaction as parent MO and must not be deleted " +
                "unless parent MO is deleted. Other instances can be created " +
                "and deleted manually.";
            must "./id = 'Default' or not(./attributes/userPlaneDomain = 'defaultUPD')" {
                error-message
                  "userPlaneDomain value 'defaultUPD' is only allowed in the Default configuration instance.";
            }
            tailf:info 'Precondition: UPDomain=Default MO instance can only be created in the same transaction as parent MO and must not be deleted unless parent MO is deleted. Other instances can be created and deleted manually, Representation of a User Plane Domain. MO instance UPDomain=Default is created automatically when parent MO is created, unless created manually in the same transaction as parent MO.';
        }
    }
}
