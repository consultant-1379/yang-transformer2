module _3gpp-nr-nrm-gnbcucpfunction {
  yang-version 1.1;
  namespace "urn:3gpp:sa5:_3gpp-nr-nrm-gnbcucpfunction";
  prefix "gnbcucp3gpp";
    
  import _3gpp-common-yang-types { prefix types3gpp; }
  import _3gpp-common-managed-function { prefix mf3gpp; }
  import _3gpp-common-managed-element { prefix me3gpp; }
  import _3gpp-common-top { prefix top3gpp; }
  import _3gpp-nr-nrm-rrmpolicy { prefix nrrrmpolicy3gpp; }

  organization "3GPP SA5";
  contact "https://www.3gpp.org/DynaReport/TSG-WG--S5--officials.htm?Itemid=464";
  description "Defines the YANG mapping of the GNBCUCPFunction Information 
    Object Class (IOC) that is part of the NR Network Resource Model (NRM).";
  reference "3GPP TS 28.541 5G Network Resource Model (NRM)";

  revision 2020-08-06 { reference "CR-0333"; }
  revision 2020-08-03 { reference "CR-0321"; }
  revision 2020-06-03 { reference "CR-0286"; }
  revision 2020-05-08 { reference S5-203316 ; }
  revision 2020-04-28 { reference "0260"; }
  revision 2020-02-14 { reference S5-20XXXX ; }
  revision 2019-10-28 { reference S5-193518 ; }
  revision 2019-06-17 {
    description "Initial revision";
  }

  feature DESManagementFunction {
    description "Classs representing Distributed SON or Domain-Centralized SON Energy Saving feature";
  }

  feature DANRManagementFunction {
    description "Classs representing D-SON function of ANR Management feature";
  }

  feature DRACHOptimizationFunction {
    description "Classs representing D-SON function of RACH optimization feature";
  }

  feature DMROFunction {
    description "Classs representing D-SON function of MRO feature";
  }
 
  grouping GNBCUCPFunctionGrp {
    description "Represents the GNBCUCPFunction IOC.";
    reference "3GPP TS 28.541";
    uses mf3gpp:ManagedFunctionGrp;
    uses nrrrmpolicy3gpp:RRMPolicy_Grp;

    leaf gNBId {
      description "Identifies a gNB within a PLMN. The gNB Identifier (gNB ID)
        is part of the NR Cell Identifier (NCI) of the gNB cells.";
      reference "gNB ID in 3GPP TS 38.300, Global gNB ID in 3GPP TS 38.413";
      mandatory true;
      type int64 { range "0..4294967295"; }
    }

    leaf gNBIdLength {
      description "Indicates the number of bits for encoding the gNB ID.";
      reference "gNB ID in 3GPP TS 38.300, Global gNB ID in 3GPP TS 38.413";
      mandatory true;
      type int32 { range "22..32"; }
    }

    leaf gNBCUName {
      description "Identifies the Central Unit of an gNB.";
      reference "3GPP TS 38.473";
      mandatory true;
      type string { length "1..150"; }
    }

    list pLMNId {
      description "The PLMN identifier to be used as part of the global RAN
        node identity.";
      key "mcc mnc";
      min-elements 1;
      max-elements 1;
      uses types3gpp:PLMNId;
    } 

    leaf-list x2BlackList {
      type string;
      description "List of nodes to which X2 connections are prohibited.";
    }

    leaf-list x2WhiteList {
      type string;
      description "List of nodes to which X2 connections are enforced.";
    }

    leaf-list xnBlackList {
      type string;
      description "List of nodes to which Xn connections are prohibited.";
    }

    leaf-list xnWhiteList {
      type string;
      description "List of nodes to which X2 connections are enforced.";
    }

    leaf-list xnHOBlackList {
      type string;
      description "List of nodes to which handovers over  Xn are prohibited.";
         }
    leaf configurable5QISetRef {
      type types3gpp:DistinguishedName;
      description "DN of the Configurable5QISet that the GNBCUCPFunction supports (is associated to).";
    }

    leaf-list x2HOBlackList {
      type string;
      description "List of nodes to which handovers over X2 are prohibited.";
    }
    leaf dynamic5QISetRef {
      type types3gpp:DistinguishedName;
      description "DN of the Dynamic5QISet that the GNBCUCPFunction supports (is associated to).";
    }
  }

  augment "/me3gpp:ManagedElement" {

    list GNBCUCPFunction {
      description "Represents the logical function CU-CP of gNB and en-gNB.";
      reference "3GPP TS 28.541";
      key id;
      uses top3gpp:Top_Grp;
      container attributes {    
        uses GNBCUCPFunctionGrp;
      }
      uses mf3gpp:ManagedFunctionContainedClasses;
    }
  }
}
