// Generated by eyang-preprocessor (1.22.0-48 2022-01-20 09:10:06 CET) on Jun 30, 2022, 8:31:44 AM
module ericsson-uemcnrfreqrelprofileuecfg-vcucp {
    yang-version 1.1;
    namespace "urn:rdns:com:ericsson:oammodel:ericsson-uemcnrfreqrelprofileuecfg-vcucp";
    prefix "uemcnrfreqrelprofileuecfgvcucp";

    import tailf-common {
        prefix tailf;
    }
    import _3gpp-common-managed-element {
        prefix "me3gpp";
    }
    import _3gpp-nr-nrm-gnbcucpfunction {
        prefix "gnbcucp3gpp";
    }
    import _3gpp-common-top {
        prefix "top3gpp";
    }
    import ericsson-yang-extensions {
        prefix "yexte";
    }
    import ericsson-uemc-vcucp {
        prefix uemcvcucp;
    }
    import ericsson-uemcnrfreqrelprofile-vcucp {
        prefix uemcnrfreqrelprofilevcucp;
    }
    import ericsson-common-types-vcucp {
        prefix commontypes;
    }

    organization
      "Ericsson AB";
    contact
      "Ericsson first line support via email";
    description
      "The module defines the UeMCNrFreqRelProfileUeCfg data model for the Ericsson vCU-CP.

       Copyright (c) 2021-2022 Ericsson AB. All rights reserved.";

    revision 2022-06-28 {
        description
            "Removed module-status preliminary.
             Removed preliminary status from prefUeGroupList, ueConfGroupList and ueGroupList.";
        yexte:version 1;
        yexte:release 1;
        yexte:correction 0;
        reference
            "RFC 7950: The YANG 1.1 Data Modeling Language";
    }

    revision 2022-03-14 {
        description
          "Updated description and precondition for UeMCNrFreqRelProfileUeCfg.
           Updated description for connModeAllowedPSCell and connModePrioPSCell.
           Added attributes prefUeGroupList, ueConfGroupList, ueGroupList and userLabel.
           Added must-rules.";
        yexte:version 1;
        yexte:release 0;
        yexte:correction 0;
        reference
          "RFC 7950: The YANG 1.1 Data Modeling Language";
    }

    revision 2021-11-05 {
        description
          "Updated description for connModeAllowedPSCell and connModePrioPSCell.
           Updated precondition for UeMCNrFreqRelProfileUeCfg.";
        yexte:version 0;
        yexte:release 2;
        yexte:correction 1;
        reference
          "RFC 7950: The YANG 1.1 Data Modeling Language";
    }

    revision 2021-10-04 {
        description
          "Added the attributes connModeAllowedPCell and connModePrioPCell.";
        yexte:version 0;
        yexte:release 2;
        yexte:correction 0;
        reference
          "RFC 7950: The YANG 1.1 Data Modeling Language";
    }

    revision 2021-09-13 {
        description
          "Initial version of the UeMCNrFreqRelProfileUeCfg model.";
        yexte:version 0;
        yexte:release 1;
        yexte:correction 0;
        reference
          "RFC 7950: The YANG 1.1 Data Modeling Language";
    }

    grouping UeMCNrFreqRelProfileUeCfgGrp {
        description
            "Represents the UeMCNrFreqRelProfileUeCfg IOC.";

        leaf connModeAllowedPCell {
            description
                "Whether it is allowed to place PCell on NR frequency defined by NR "+
                "frequency relation.

                Applies to UEs which use cell as PCell.";
            type boolean;
            default false;
            yexte:takes-effect
                "Next usage.";
            tailf:info 'Takes effect: Next usage, Whether it is allowed to place PCell on NR frequency defined by NR frequency relation. Applies to UEs which use cell as PCell.';
        }

        leaf connModeAllowedPSCell {
            description
                "Whether PSCell can be placed on NR frequency defined by NR frequency "+
                "relation.

                Applies to UEs that use this cell as PSCell in EN-DC.

                Note: gNodeB is only using attribute value for this attribute from "+
                "the UeMCNrFreqRelProfileUeCfg=Base instance.";
            type boolean;
            default false;
            yexte:takes-effect
                "Next usage.";
            tailf:info 'Takes effect: Next usage, Whether PSCell can be placed on NR frequency defined by NR frequency relation. Applies to UEs that use this cell as PSCell in EN-DC. Note: gNodeB is only using attribute value for this attribute from the UeMCNrFreqRelProfileUeCfg=Base instance.';
        }

        leaf connModePrioPCell {
            description
              "Connected mode PCell priority for NR frequency relation.

               Applies to UEs that use cell as PCell.

               Used to decide preference on which NR frequency to place PCell in " +
              "connected mode.

               0 means frequency relation with lowest priority.
               7 means frequency relation with highest priority.

               Applicable only when connModeAllowedPCell is true.";
            type int32 {
                range "0..7";
            }
            default 7;
            yexte:takes-effect
                "Next usage.";
            tailf:info 'Takes effect: Next usage, Connected mode PCell priority for NR frequency relation. Applies to UEs that use cell as PCell. Used to decide preference on which NR frequency to place PCell in connected mode. 0 means frequency relation with lowest priority. 7 means frequency relation with highest priority. Applicable only when connModeAllowedPCell is true.';
        }

        leaf connModePrioPSCell {
            description
                "Connected mode PSCell priority for NR frequency relation.

                Applies to UEs that use this cell as PSCell in EN-DC.

                Used to decide preference on which NR frequency to place PSCell in "+
                "connected mode.

                0 means frequency relation with lowest priority.
                7 means frequency relation with highest priority.

                Applicable only when connModeAllowedPSCell is true.

                Note: gNodeB is only using attribute value for this attribute from "+
                "the UeMCNrFreqRelProfileUeCfg=Base instance.";
            type int32 {
                range "0..7";
            }
            default 7;
            yexte:takes-effect
                "Next usage.";
            tailf:info 'Takes effect: Next usage, Connected mode PSCell priority for NR frequency relation. Applies to UEs that use this cell as PSCell in EN-DC. Used to decide preference on which NR frequency to place PSCell in connected mode. 0 means frequency relation with lowest priority. 7 means frequency relation with highest priority. Applicable only when connModeAllowedPSCell is true. Note: gNodeB is only using attribute value for this attribute from the UeMCNrFreqRelProfileUeCfg=Base instance.';
        }

        leaf-list prefUeGroupList {
            max-elements 8;
            ordered-by user;
            description
                "Preference UE group list.

                List of preference UE group identifiers.

                If empty, the MO instance matches preference UE group identifiers "+
                "not defined in prefUeGroupList of any other MO instances under "+
                "parent MO instance.";
            type int32 {
                range "1..255";
            }
            yexte:dependencies
                "Combinations of pair of preference UE group Identifier in "+
                "prefUeGroupList and UE group identifier in ueGroupList must be "+
                "unique among UeMCNrFreqRelProfileUeCfg instances under same parent "+
                "UeMCNrFreqRelProfile instance.

                For all preference UE group identifiers in prefUeGroupList "+
                "attributes under same parent UeMCNrFreqRelProfile MO instance, "+
                "exactly one UeMCNrFreqRelProfileUeCfg MO instance must exist that "+
                "combines the given preference UE group identifier with an empty "+
                "ueGroupList.";
            yexte:disturbances
                "Changing this attribute can cause loss of traffic.";
            yexte:takes-effect
                "Next usage.";
            must "count(../../../UeMCNrFreqRelProfileUeCfg/attributes[prefUeGroupList = current()
                    and count(ueGroupList) = 0] ) = 1" {
                error-message
                    "Exactly one UeMCNrFreqRelProfileUeCfg instance under an "+
                    "UeMCNrFreqRelProfile must combine a specific preference UE "+
                    "group identifier in attribute prefUeGroupList with an empty ueGroupList";
            }
            tailf:info 'Takes effect: Next usage, Traffic Disturbance: Changing this attribute can cause loss of traffic, Dependencies: Combinations of pair of preference UE group Identifier in prefUeGroupList and UE group identifier in ueGroupList must be unique among UeMCNrFreqRelProfileUeCfg instances under same parent UeMCNrFreqRelProfile instance.

                For all preference UE group identifiers in prefUeGroupList attributes under same parent UeMCNrFreqRelProfile MO instance, exactly one UeMCNrFreqRelProfileUeCfg MO instance must exist that combines the given preference UE group identifier with an empty ueGroupList, Preference UE group list. List of preference UE group identifiers. If empty, the MO instance matches preference UE group identifiers not defined in prefUeGroupList of any other MO instances under parent MO instance.';
        }

        leaf-list ueConfGroupList {
            max-elements 32;
            ordered-by user;
            description
                "UE configuration group list.

                List of UE configuration group identifiers.

                If empty, the MO instance matches all UE configuration group "+
                "identifiers.

                Which UE configuration group type that is applied is defined by "+
                "attribute ueConfGroupType in parent MO class instance.";
            type int32 {
                range "1..255";
            }
            yexte:dependencies
                "A given UE configuration group identifier can be defined in only one "+
                "ueConfGroupList among UeMCNrFreqRelProfileUeCfg instances under same "+
                "parent UeMCNrFreqRelProfile instance.";
            yexte:disturbances
                "Changing this attribute can cause loss of traffic.";
            yexte:takes-effect
                "Next usage.";
            must "count(../../../UeMCNrFreqRelProfileUeCfg/attributes[ueConfGroupList = current() ]) &lt;=1" {
                error-message
                    "Only one UeMCNrFreqRelProfileUeCfg instance under an "+
                    "UeMCNrFreqRelProfile can include a specific UE configuration "+
                    "group identifier in attribute ueConfGroupList.";
            }
            tailf:info 'Takes effect: Next usage, Traffic Disturbance: Changing this attribute can cause loss of traffic, Dependencies: A given UE configuration group identifier can be defined in only one ueConfGroupList among UeMCNrFreqRelProfileUeCfg instances under same parent UeMCNrFreqRelProfile instance, UE configuration group list. List of UE configuration group identifiers. If empty, the MO instance matches all UE configuration group identifiers. Which UE configuration group type that is applied is defined by attribute ueConfGroupType in parent MO class instance.';
        }

        leaf-list ueGroupList {
            max-elements 16;
            ordered-by user;
            description
                "UE group list.

                List of UE group identifiers.

                If empty, the MO instance matches all UE group identifiers.";
            type int32 {
                range "1..255";
            }
            yexte:dependencies
                "Combinations of pair of preference UE group Identifier in "+
                "prefUeGroupList and UE group identifier in ueGroupList must be "+
                "unique among UeMCNrFreqRelProfileUeCfg instances under same parent "+
                "UeMCNrFreqRelProfile instance.

                Combination of a UE group identifier in UeGroupList and empty "+
                "prefUeGroupList must be unique among UeMCNrFreqRelProfileUeCfg "+
                "instances under same parent UeMCNrFreqRelProfile instance.";
            yexte:disturbances
                "Changing this attribute can cause loss of traffic.";
            yexte:takes-effect
                "Next usage.";
            must "count(../prefUeGroupList) &gt; 0
                  or count(../../../UeMCNrFreqRelProfileUeCfg/attributes[ueGroupList = current()
                     and count(prefUeGroupList) = 0] ) &lt;= 1" {
                error-message
                    "Only one UeMCNrFreqRelProfileUeCfg instance under an "+
                    "UeMCNrFreqRelProfile can combine a specific UE group "+
                    "identifier in attribute ueGroupList with an empty prefUeGroupList.";
            }
            tailf:info 'Takes effect: Next usage, Traffic Disturbance: Changing this attribute can cause loss of traffic, Dependencies: Combinations of pair of preference UE group Identifier in prefUeGroupList and UE group identifier in ueGroupList must be unique among UeMCNrFreqRelProfileUeCfg instances under same parent UeMCNrFreqRelProfile instance.

                Combination of a UE group identifier in UeGroupList and empty prefUeGroupList must be unique among UeMCNrFreqRelProfileUeCfg instances under same parent UeMCNrFreqRelProfile instance, UE group list. List of UE group identifiers. If empty, the MO instance matches all UE group identifiers.';
        }
    }

    augment "/me3gpp:ManagedElement/gnbcucp3gpp:GNBCUCPFunction/uemcvcucp:UeMC/uemcnrfreqrelprofilevcucp:UeMCNrFreqRelProfile" {
        list UeMCNrFreqRelProfileUeCfg {
            description
                "UE mobility control attributes, UE configuration group.

                Attributes are used on NR frequency relation level.

                MO instance UeMCNrFreqRelProfileUeCfg=Base is created "+
                "automatically when parent MO is created, unless created "+
                "manually in the same transaction as parent MO.

                Attributes prefUeGroupList, ueGroupList and ueConfGroupList "+
                "must be empty in instance UeMCNrFreqRelProfileUeCfg=Base but "+
                "cannot all be empty in other instances of "+
                "UeMCNrFreqRelProfileUeCfg under same parent "+
                "UeMCNrFreqRelProfile.";
            key id;
            max-elements 32;
            uses top3gpp:Top_Grp;
            container attributes {
                uses UeMCNrFreqRelProfileUeCfgGrp;
                uses commontypes:UserLabelGrp;
            }
            must "count(../uemcnrfreqrelprofileuecfgvcucp:UeMCNrFreqRelProfileUeCfg) &lt; 32 or
                  count(../uemcnrfreqrelprofileuecfgvcucp:UeMCNrFreqRelProfileUeCfg/id[. = 'Base']) = 1" {
                error-message
                    "Maximum 31 UeMCNrFreqRelProfileUeCfg instances under UeMCNrFreqRelProfile can be created with RDN different from Base";
            }
            must "count(../UeMCNrFreqRelProfileUeCfg/attributes[prefUeGroupList = current()/attributes/prefUeGroupList
                  and ueGroupList = current()/attributes/ueGroupList] ) &lt;= 1" {
                error-message
                    "The combinations of a pair of UE group identifier in ueGroupList "+
                    "and preference UE group identifier in prefUeGroupList must be "+
                    "unique among UeMCNrFreqRelProfileUeCfg under an "+
                    "UeMCNrFreqRelProfile";
            }
            must "./id = 'Base'
                    or not ( count(./attributes/ueConfGroupList) = 0
                             and count(./attributes/ueGroupList) = 0
                             and count(./attributes/prefUeGroupList) = 0 )" {
                error-message
                    "UeMCNrFreqRelProfileUeCfg::prefUeGroupList, ueGroupList and "+
                    "ueConfGroupList can only be empty in the UeMCNrFreqRelProfileUeCfg=Base "+
                    "instance.";
            }
            must "./id != 'Base'
                    or ( count(./attributes/ueConfGroupList) = 0
                         and count(./attributes/ueGroupList) = 0
                         and count(./attributes/prefUeGroupList) = 0 )" {
                error-message
                    "UeMCNrFreqRelProfileUeCfg::prefUeGroupList, ueGroupList and "+
                    "ueConfGroupList must be empty in the UeMCNrFreqRelProfileUeCfg=Base "+
                    "instance.";
            }
            yexte:precondition
                "UeMCNrFreqRelProfileUeCfg=Base MO instance can only be created "+
                "in the same transaction as parent MO and must not be deleted "+
                "unless parent MO is deleted. Other instances can be created "+
                "and deleted manually.

                Maximum 31 UeMCNrFreqRelProfileUeCfg instances, with RDN "+
                "different from Base, can be created.";
            tailf:info 'Precondition: UeMCNrFreqRelProfileUeCfg=Base MO instance can only be created in the same transaction as parent MO and must not be deleted unless parent MO is deleted. Other instances can be created and deleted manually.

                Maximum 31 UeMCNrFreqRelProfileUeCfg instances, with RDN different from Base, can be created, UE mobility control attributes, UE configuration group. Attributes are used on NR frequency relation level. MO instance UeMCNrFreqRelProfileUeCfg=Base is created automatically when parent MO is created, unless created manually in the same transaction as parent MO. Attributes prefUeGroupList, ueGroupList and ueConfGroupList must be empty in instance UeMCNrFreqRelProfileUeCfg=Base but cannot all be empty in other instances of UeMCNrFreqRelProfileUeCfg under same parent UeMCNrFreqRelProfile.';
        }
    }
}
