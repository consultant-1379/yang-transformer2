// Generated by eyang-preprocessor (1.22.0-48 2022-01-20 09:10:06 CET) on Jun 30, 2022, 8:31:41 AM
module ericsson-nrcellrelation-dev-vcucp {
    yang-version 1.1;
    namespace urn:rdns:com:ericsson:oammodel:ericsson-nrcellrelation-dev-vcucp;
    prefix nrcellrel3gppdev;

    import _3gpp-common-managed-element {
        prefix me3gpp;
    }
    import _3gpp-nr-nrm-gnbcucpfunction {
        prefix gnbcucp3gpp;
    }
    import _3gpp-nr-nrm-nrcellcu {
        prefix nrcellcu3gpp;
    }
    import _3gpp-nr-nrm-nrcellrelation {
        prefix nrcellrel3gpp;
    }
    import ericsson-yang-extensions {
        prefix yexte;
    }

    organization
      "Ericsson AB";
    contact
      "Ericsson first line support via email";
    description
      "The module defines the NRCellCU data model deviations for the Ericsson vCU-CP.

       Copyright (c) 2020-2022 Ericsson AB. All rights reserved.";

    revision 2022-06-28 {
        description
            "Removed module-status preliminary.";
        yexte:version 0;
        yexte:release 2;
        yexte:correction 0;
        reference
            "RFC 7950: The YANG 1.1 Data Modeling Language";
    }

    revision 2020-03-23 {
        description
          "Deviations on _3gpp-nr-nrm-nrcellrelation.";
        yexte:version 0;
        yexte:release 1;
        yexte:correction 0;
        reference
          "RFC 7950: The YANG 1.1 Data Modeling Language";
    }

    deviation /me3gpp:ManagedElement/gnbcucp3gpp:GNBCUCPFunction/nrcellcu3gpp:NRCellCU/nrcellrel3gpp:NRCellRelation/nrcellrel3gpp:ManagedNFService {
        description
        "Managed Network Function Service is not supported for GNBCUCPFunction.";
        deviate not-supported;
    }

    deviation /me3gpp:ManagedElement/gnbcucp3gpp:GNBCUCPFunction/nrcellcu3gpp:NRCellCU/nrcellrel3gpp:NRCellRelation/nrcellrel3gpp:PerfMetricJob {
        description
        "Performance Metric Job is not supported for GNBCUCPFunction.";
        deviate not-supported;
    }

    deviation /me3gpp:ManagedElement/gnbcucp3gpp:GNBCUCPFunction/nrcellcu3gpp:NRCellCU/nrcellrel3gpp:NRCellRelation/nrcellrel3gpp:ThresholdMonitor {
        description
        "Threshold Monitor is not supported for GNBCUCPFunction.";
        deviate not-supported;
    }

    deviation /me3gpp:ManagedElement/gnbcucp3gpp:GNBCUCPFunction/nrcellcu3gpp:NRCellCU/nrcellrel3gpp:NRCellRelation/nrcellrel3gpp:TraceJob {
        description
        "Trace Job is not supported for GNBCUCPFunction.";
        deviate not-supported;
    }

    deviation /me3gpp:ManagedElement/gnbcucp3gpp:GNBCUCPFunction/nrcellcu3gpp:NRCellCU/nrcellrel3gpp:NRCellRelation/nrcellrel3gpp:attributes/nrcellrel3gpp:nRTCI {
        description
          "NrCellRelation::nRTCI is not supported.";
        deviate not-supported;
    }

    deviation /me3gpp:ManagedElement/gnbcucp3gpp:GNBCUCPFunction/nrcellcu3gpp:NRCellCU/nrcellrel3gpp:NRCellRelation/nrcellrel3gpp:attributes/nrcellrel3gpp:cellIndividualOffset {
        description
          "NrCellRelation::cellIndividualOffset is not supported.";
        deviate not-supported;
    }

    deviation /nrcellrel3gpp:isESCoveredBy {
        // This can be removed or changed when upgrading to newer 3gpp files where they have corrected this attribute.
        description
          "isESCoveredBy is incorrectly placed outside the grouping in _3gpp-nr-nrm-nrcellrelation.";
        deviate not-supported;
    }
}
