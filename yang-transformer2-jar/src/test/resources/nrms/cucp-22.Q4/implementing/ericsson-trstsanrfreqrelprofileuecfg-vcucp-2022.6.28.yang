// Generated by eyang-preprocessor (1.22.0-48 2022-01-20 09:10:06 CET) on Jun 30, 2022, 8:31:44 AM
module ericsson-trstsanrfreqrelprofileuecfg-vcucp {
    yang-version 1.1;
    namespace "urn:rdns:com:ericsson:oammodel:ericsson-trstsanrfreqrelprofileuecfg-vcucp";
    prefix trstsanrfreqrelprofileuecfg;

    import tailf-common {
        prefix tailf;
    }
    import _3gpp-common-managed-element {
        prefix "me3gpp";
    }
    import _3gpp-nr-nrm-gnbcucpfunction {
        prefix "gnbcucp3gpp";
    }
    import _3gpp-common-top {
        prefix "top3gpp";
    }
    import ericsson-yang-extensions {
        prefix "yexte";
    }
    import ericsson-common-types-vcucp {
        prefix "commontypes";
    }
    import ericsson-trafficsteering-vcucp {
        prefix "trafficsteering";
    }
    import ericsson-trstsanrfreqrelprofile-vcucp {
        prefix "trstsanrfreqrelprofile";
    }

    organization
      "Ericsson AB";
    contact
      "Ericsson first line support via email";
    description
      "The module defines the TrStSaNrFreqRelProfileUeCfg data model for the Ericsson vCU-CP.

       Copyright (c) 2021-2022 Ericsson AB. All rights reserved.";

    revision 2022-06-28 {
        description
            "Removed module-status preliminary.
             Removed preliminary status from TrStSaNrFreqRelProfileUeCfg.
             Removed preliminary status from pCellAllowed and rsrpPCellCandidateOffset.";
        yexte:version 0;
        yexte:release 3;
        yexte:correction 0;
        reference
            "RFC 7950: The YANG 1.1 Data Modeling Language";
    }

    revision 2022-03-14 {
        description
          "Updated max-elements, precondition and description of TrStSaNrFreqRelProfileUeCfg.
           Added rule for number of instances that could be created.
           Removed must statement that checks id for TrStSaNrFreqRelProfileUeCfg.
           Added the userLabel attribute.";
        yexte:version 0;
        yexte:release 2;
        yexte:correction 0;
        reference
          "RFC 7950: The YANG 1.1 Data Modeling Language";
    }

    revision 2021-11-05 {
        description
          "Initial version of the TrStSaNrFreqRelProfileUeCfg model.";
        yexte:version 0;
        yexte:release 1;
        yexte:correction 0;
        reference
          "RFC 7950: The YANG 1.1 Data Modeling Language";
    }

    grouping TrStSaNrFreqRelProfileUeCfgGrp {
        description
            "Represents the TrStSaNrFreqRelProfileUeCfg IOC.";

        leaf pCellAllowed {
            description
                "Whether traffic steering is allowed to choose PCell candidates on NR "+
                "frequency.

                NR frequency defined by NR frequency relation.";
            type boolean;
            default false;
            yexte:dependencies
                "Only one NRFreqRelation MO instance under NRCellCU can refer to a "+
                "TrStSaNrFreqRelProfile with attribute "+
                "TrStSaNrFreqRelationUeCfg::pCellAllowed set to true.";
            yexte:takes-effect
                "Next usage";
            tailf:info 'Takes effect: Next usage, Dependencies: Only one NRFreqRelation MO instance under NRCellCU can refer to a TrStSaNrFreqRelProfile with attribute TrStSaNrFreqRelationUeCfg::pCellAllowed set to true, Whether traffic steering is allowed to choose PCell candidates on NR frequency. NR frequency defined by NR frequency relation.';
        }

        leaf rsrpPCellCandidateOffset {
            description
                "RSRP measurement threshold offset that defines minimum RSRP value "+
                "for NR PCell candidate.

                Used in combination with TrStSaCellProfileUeCfg::rsrpPCellCandidate "+
                "in capability-aware PCell selection function.";
            type int32 {
                range "-100..100";
            }
            default 0;
            units dB;
            yexte:takes-effect
                "Next usage";
            tailf:info 'Takes effect: Next usage, RSRP measurement threshold offset that defines minimum RSRP value for NR PCell candidate. Used in combination with TrStSaCellProfileUeCfg::rsrpPCellCandidate in capability-aware PCell selection function.';
        }
    }

    augment "/me3gpp:ManagedElement/gnbcucp3gpp:GNBCUCPFunction/trafficsteering:TrafficSteering/trstsanrfreqrelprofile:TrStSaNrFreqRelProfile" {
        list TrStSaNrFreqRelProfileUeCfg {
            description
                "Traffic steering function for PCell and SCells in NR "+
                "Standalone, UE configuration group.

                Applicable to UEs that use this cell as PCell in NR "+
                "Standalone. Attributes are used on NR frequency relation level.

                TrStSaNrFreqRelProfileUeCfg=Base MO instance is created "+
                "automatically when parent MO is created, unless created "+
                "manually in the same transaction as parent MO.";
            key id;
            max-elements 32;
            uses top3gpp:Top_Grp;
            container attributes {
                uses TrStSaNrFreqRelProfileUeCfgGrp;
                uses commontypes:UserLabelGrp;
            }
            yexte:precondition
                "TrStSaNrFreqRelProfileUeCfg=Base MO instance can only be "+
                "created in the same transaction as parent MO and must not be "+
                "deleted unless parent MO is deleted. Other instances can be "+
                "created and deleted manually.

                Maximum 31 TrStSaNrFreqRelProfileUeCfg instances, with RDN "+
                "different from Base, can be created.";

            must "count(../TrStSaNrFreqRelProfileUeCfg) &lt; 32 or
                  count(../TrStSaNrFreqRelProfileUeCfg/id[. = 'Base']) = 1" {
                error-message
                    "Maximum 31 TrStSaNrFreqRelProfileUeCfg instances under an "+
                    "TrStSaNrFreqRelProfile can be created with RDN different from Base.";
            }
            tailf:info 'Precondition: TrStSaNrFreqRelProfileUeCfg=Base MO instance can only be created in the same transaction as parent MO and must not be deleted unless parent MO is deleted. Other instances can be created and deleted manually.

                Maximum 31 TrStSaNrFreqRelProfileUeCfg instances, with RDN different from Base, can be created, Traffic steering function for PCell and SCells in NR Standalone, UE configuration group. Applicable to UEs that use this cell as PCell in NR Standalone. Attributes are used on NR frequency relation level. TrStSaNrFreqRelProfileUeCfg=Base MO instance is created automatically when parent MO is created, unless created manually in the same transaction as parent MO.';
        }
    }
}
