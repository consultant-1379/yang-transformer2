// Generated by eyang-preprocessor (1.22.0-48 2022-01-20 09:10:06 CET) on Jun 30, 2022, 8:31:44 AM
module ericsson-trstsacellprofile-vcucp {
    yang-version 1.1;
    namespace "urn:rdns:com:ericsson:oammodel:ericsson-trstsacellprofile-vcucp";
    prefix trstsacellprofile;

    import tailf-common {
        prefix tailf;
    }
    import _3gpp-common-managed-element {
        prefix "me3gpp";
    }
    import _3gpp-nr-nrm-gnbcucpfunction {
        prefix "gnbcucp3gpp";
    }
    import _3gpp-common-top {
        prefix "top3gpp";
    }
    import ericsson-yang-extensions {
        prefix "yexte";
    }
    import ericsson-trafficsteering-vcucp {
        prefix "trafficsteering";
    }
    import ericsson-common-types-vcucp {
        prefix "commontypes";
    }

    organization
      "Ericsson AB";
    contact
      "Ericsson first line support via email";
    description
      "The module defines the TrStSaCellProfile data model for the Ericsson vCU-CP.

       Copyright (c) 2021-2022 Ericsson AB. All rights reserved.";

    revision 2022-06-28 {
        description
            "Removed module-status preliminary.
             Removed preliminary status from TrStSaCellProfile.";
        yexte:version 0;
        yexte:release 3;
        yexte:correction 0;
        reference
            "RFC 7950: The YANG 1.1 Data Modeling Language";
    }

    revision 2022-03-14 {
        description
          "Updated description of TrStSaCellProfile model.
           Added the userLabel attribute.";
        yexte:version 0;
        yexte:release 2;
        yexte:correction 0;
        reference
          "RFC 7950: The YANG 1.1 Data Modeling Language";
    }

    revision 2021-11-05 {
        description
          "Initial version of the TrStSaCellProfile model.";
        yexte:version 0;
        yexte:release 1;
        yexte:correction 0;
        reference
          "RFC 7950: The YANG 1.1 Data Modeling Language";
    }

    augment "/me3gpp:ManagedElement/gnbcucp3gpp:GNBCUCPFunction/trafficsteering:TrafficSteering" {
        list TrStSaCellProfile {
            description
                "Traffic steering function for PCell and SCells in NR Standalone.

                Applicable to UEs that use this cell as PCell in NR Standalone. "+
                "Attributes are used on cell level.

                TrStSaCellProfile=Default MO instance is created automatically "+
                "when parent MO is created, unless created manually in the same "+
                "transaction as parent MO.

                If NRCellCU::trStSaCellProfileRef is non-empty, attributes from "+
                "referenced MO instance are used.
                If NRCellCU::trStSaCellProfileRef is empty, attribute default "+
                "values according to TrStSaCellProfile and TrStSaCellProfileUeCfg "+
                "MO class definitions are used.";
            key id;
            uses top3gpp:Top_Grp;
            container attributes {
                uses commontypes:UserLabelGrp;
            }
            yexte:precondition
                "TrStSaCellProfile=Default MO must not be deleted unless "+
                "parent MO is deleted. Other instances can be created and "+
                "deleted manually.";
            tailf:info 'Precondition: TrStSaCellProfile=Default MO must not be deleted unless parent MO is deleted. Other instances can be created and deleted manually, Traffic steering function for PCell and SCells in NR Standalone. Applicable to UEs that use this cell as PCell in NR Standalone. Attributes are used on cell level. TrStSaCellProfile=Default MO instance is created automatically when parent MO is created, unless created manually in the same transaction as parent MO. If NRCellCU::trStSaCellProfileRef is non-empty, attributes from referenced MO instance are used. If NRCellCU::trStSaCellProfileRef is empty, attribute default values according to TrStSaCellProfile and TrStSaCellProfileUeCfg MO class definitions are used.';
        }
    }
}
