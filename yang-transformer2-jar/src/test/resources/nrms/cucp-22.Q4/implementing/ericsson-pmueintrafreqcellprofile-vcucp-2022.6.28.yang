// Generated by eyang-preprocessor (1.22.0-48 2022-01-20 09:10:06 CET) on Jun 30, 2022, 8:31:43 AM
module ericsson-pmueintrafreqcellprofile-vcucp {
    yang-version 1.1;
    namespace "urn:rdns:com:ericsson:oammodel:ericsson-pmueintrafreqcellprofile-vcucp";
    prefix "pmueintrafreqcellprofilevcucp";

    import tailf-common {
        prefix tailf;
    }
    import _3gpp-common-managed-element {
        prefix "me3gpp";
    }
    import _3gpp-nr-nrm-gnbcucpfunction {
        prefix "gnbcucp3gpp";
    }
    import _3gpp-common-top {
        prefix "top3gpp";
    }
    import ericsson-yang-extensions {
        prefix "yexte";
    }
    import ericsson-common-types-vcucp {
        prefix commontypes;
    }
    import ericsson-pmuemeas-vcucp {
        prefix pmuemeasvcucp;
    }

    organization
      "Ericsson AB";
    contact
      "Ericsson first line support via email";
    description
      "The module defines the PmUeIntraFreqCellProfile data model for the Ericsson vCU-CP.

       Copyright (c) 2021-2022 Ericsson AB. All rights reserved.";

    revision 2022-06-28 {
        description
            "Removed module-status preliminary.";
        yexte:version 0;
        yexte:release 4;
        yexte:correction 0;
        reference
            "RFC 7950: The YANG 1.1 Data Modeling Language";
    }

    revision 2022-03-14 {
        description
          "Import usage of ReportInterval and ReportAmount from commontypes.
           Added the userLabel attribute.";
        yexte:version 0;
        yexte:release 3;
        yexte:correction 0;
        reference
          "RFC 7950: The YANG 1.1 Data Modeling Language";
    }

    revision 2021-05-19 {
        description
          "Remove is-system-created and restricted extension.";
        yexte:version 0;
        yexte:release 2;
        yexte:correction 0;
        reference
          "RFC 7950: The YANG 1.1 Data Modeling Language";
    }

    revision 2021-05-05 {
        description
          "Initial version of the PmUeIntraFreqCellProfile model.";
        yexte:version 0;
        yexte:release 1;
        yexte:correction 0;
        reference
          "RFC 7950: The YANG 1.1 Data Modeling Language";
    }

    typedef PmUeReportType {
        description
          "Report type selected for PM purpose.";

        type enumeration {
            enum PERIODICAL {
                value 0;
                description
                  "Periodical measurement report.";
            }

            enum EVENT_A2 {
                value 1;
                description
                  "Event A2 measurement report.";
            }

            enum EVENT_A3 {
                value 2;
                description
                  "Event A3 measurement report.";
            }
        }
    }

    grouping ReportQuantityCell {
        description
          "Cell measurement quantities to be included in measurement report.";

        leaf rsrp {
            description
              "Whether RSRP quantity is included in measurement report.";
            type boolean;
            default true;
            reference
              "3GPP TS 38.331";
        }

        leaf rsrq {
            description
              "Whether RSRQ quantity is included in measurement report.";
            type boolean;
            default true;
            reference
              "3GPP TS 38.331";
        }

        leaf sinr {
            description
              "Whether SINR quantity is included in measurement report.";
            type boolean;
            default false;
            reference
              "3GPP TS 38.331";
        }
    }

    grouping PmUeIntraFreqCellProfileGrp {
        description
          "Represents the PmUeIntraFreqCellProfile IOC.";

        leaf maxReportCells {
            description
              "Maximum number of non-serving cells included in measurement report.";
            type int32 {
                range "1..8";
            }
            default 4;
            reference
              "3GPP TS 38.331";
            yexte:takes-effect
              "New connection";
            tailf:info 'Takes effect: New connection, Maximum number of non-serving cells included in measurement report.';
        }

        leaf pmUeReportType {
            description
              "Report type used in PM UE measurement.";
            type PmUeReportType;
            default PERIODICAL;
            yexte:takes-effect
              "New connection";
            tailf:info 'Takes effect: New connection, Report type used in PM UE measurement.';
        }

        leaf reportAmount {
            description
              "Number of periodical or event-triggered measurement reports.";
            type commontypes:ReportAmount;
            default R2;
            reference
              "3GPP TS 38.331";
            yexte:disturbances
              "Large report interval setting can cause high measurement report load.";
            yexte:takes-effect
              "New connection";
            tailf:info 'Takes effect: New connection, Traffic Disturbance: Large report interval setting can cause high measurement report load, Number of periodical or event-triggered measurement reports.';
        }

        container reportConfigA2Rsrp {
            description
              "Event A2 measurement reporting criteria.

               Applied if reportType is EVENT_A2 and trigger quantity is RSRP.";
            uses commontypes:ReportConfigA1A2Rsrp;
            reference
              "3GPP TS 38.331";
            yexte:takes-effect
              "Next usage";
            tailf:info 'Takes effect: Next usage, Event A2 measurement reporting criteria. Applied if reportType is EVENT_A2 and trigger quantity is RSRP.';
        }

        container reportConfigA2Rsrq {
            description
              "Event A2 measurement reporting criteria.

               Applied if reportType is EVENT_A2 and trigger quantity is RSRQ.";
            uses commontypes:ReportConfigA1A2Rsrq;
            reference
              "3GPP TS 38.331";
            yexte:takes-effect
              "Next usage";
            tailf:info 'Takes effect: Next usage, Event A2 measurement reporting criteria. Applied if reportType is EVENT_A2 and trigger quantity is RSRQ.';
        }

        container reportConfigA3Rsrp {
            description
              "Event A3 measurement reporting criteria.

               Applied if reportType is EVENT_A3 and trigger quantity is RSRP.";
            uses commontypes:ReportConfigA3Rsrp;
            reference
              "3GPP TS 38.331";
            yexte:takes-effect
              "Next usage";
            tailf:info 'Takes effect: Next usage, Event A3 measurement reporting criteria. Applied if reportType is EVENT_A3 and trigger quantity is RSRP.';
        }

        container reportConfigA3Rsrq {
            description
              "Event A3 measurement reporting criteria.

               Applied if reportType is EVENT_A3 and trigger quantity is RSRQ.";
            uses commontypes:ReportConfigA3Rsrq;
            reference
              "3GPP TS 38.331";
            yexte:takes-effect
              "Next usage";
            tailf:info 'Takes effect: Next usage, Event A3 measurement reporting criteria. Applied if reportType is EVENT_A3 and trigger quantity is RSRQ.';
        }

        leaf reportInterval {
            description
              "Interval for periodical or event-triggered measurement reports.";
            type commontypes:ReportInterval;
            default MIN_1;
            reference
              "3GPP TS 38.331";
            yexte:disturbances
              "A short report interval setting can cause high measurement report "+
              "load.";
            yexte:takes-effect
              "New connection";
            tailf:info 'Takes effect: New connection, Traffic Disturbance: A short report interval setting can cause high measurement report load, Interval for periodical or event-triggered measurement reports.';
        }

        container reportQuantityCell {
            description
              "Cell measurement quantities to be included in measurement report.";
            uses ReportQuantityCell;
            reference
              "3GPP TS 38.331";
            yexte:takes-effect
              "New connection";
            tailf:info 'Takes effect: New connection, Cell measurement quantities to be included in measurement report.';
        }

        leaf triggerQuantity {
            description
              "Measurement quantity that triggers event A2 or A3 measurements.

               Applied when reportType is EVENT_A2 or EVENT_A3.";
            type commontypes:TriggerQuantity;
            default RSRP;
            reference
              "3GPP TS 38.331";
            yexte:takes-effect
              "New connection";
            tailf:info 'Takes effect: New connection, Measurement quantity that triggers event A2 or A3 measurements. Applied when reportType is EVENT_A2 or EVENT_A3.';
        }

        leaf ueSelectionRatio {
            description
              "UE selection ratio for PM UE measurements configuration.";
            type int32 {
                range "0..1000";
            }
            default 100;
            units "0.1 %";
            yexte:disturbances
              "Large report interval setting can cause high measurement report load.";
            yexte:takes-effect
              "New connection";
            tailf:info 'Takes effect: New connection, Traffic Disturbance: Large report interval setting can cause high measurement report load, UE selection ratio for PM UE measurements configuration.';
        }
    }

    augment "/me3gpp:ManagedElement/gnbcucp3gpp:GNBCUCPFunction/pmuemeasvcucp:PmUeMeas" {
        list PmUeIntraFreqCellProfile {
            description
              "Profile for PM intra-frequency UE measurements.

               If NRCellCU::pmUeIntraFreqCellProfileRef is non-empty, attributes from referred MO instance are used.
               If NRCellCU::pmUeIntraFreqCellProfileRef is empty, attribute default values according to MO class definition are used.";
            key id;
            max-elements 10;
            uses top3gpp:Top_Grp;
            container attributes {
                uses PmUeIntraFreqCellProfileGrp;
                uses commontypes:UserLabelGrp;
            }
        }
    }
}
