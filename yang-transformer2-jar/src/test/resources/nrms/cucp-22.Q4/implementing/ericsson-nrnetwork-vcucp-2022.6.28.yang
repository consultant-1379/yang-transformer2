// Generated by eyang-preprocessor (1.22.0-48 2022-01-20 09:10:06 CET) on Jun 30, 2022, 8:31:43 AM
module ericsson-nrnetwork-vcucp {
    yang-version 1.1;
    namespace urn:rdns:com:ericsson:oammodel:ericsson-nrnetwork-vcucp;
    prefix nrnetwork;

    import tailf-common {
        prefix tailf;
    }
    import _3gpp-common-managed-element {
        prefix me3gpp;
    }
    import _3gpp-nr-nrm-gnbcucpfunction {
        prefix gnbcucp3gpp;
    }
    import _3gpp-common-yang-extensions {
        prefix yext3gpp;
    }
    import _3gpp-common-top {
        prefix top3gpp;
    }
    import ericsson-yang-extensions {
        prefix yexte;
    }

    organization
    "Ericsson AB";
    contact
    "Ericsson first line support via email";
    description
    "The module defines the NRNetwork data model for the Ericsson vCU-CP.

     Copyright (c) 2021-2022 Ericsson AB. All rights reserved.";

    revision 2022-06-28 {
        description
            "Removed module-status preliminary.";
        yexte:version 2;
        yexte:release 1;
        yexte:correction 0;
        reference
            "RFC 7950: The YANG 1.1 Data Modeling Language";
    }

    revision 2022-04-20 {
        description
            "Marked simpleNRFreqSmtc as obsolete.";
        yexte:version 2;
        yexte:release 0;
        yexte:correction 0;
        reference
            "RFC 7950: The YANG 1.1 Data Modeling Language";
    }

    revision 2021-11-05 {
        description
            "Add attribute simpleNRFreqSmtc.";
        yexte:version 1;
        yexte:release 2;
        yexte:correction 0;
        reference
            "RFC 7950: The YANG 1.1 Data Modeling Language";
    }

    revision 2021-05-06 {
        description
            "Remove is-system-created extensions.";
        yexte:version 1;
        yexte:release 1;
        yexte:correction 0;
        reference
            "RFC 7950: The YANG 1.1 Data Modeling Language";
    }

    revision 2021-04-06 {
        description
            "Updated Ericsson MO description.";
        yexte:version 1;
        yexte:release 0;
        yexte:correction 1;
        reference
            "RFC 7950: The YANG 1.1 Data Modeling Language";
    }

    revision 2021-01-20 {
        description
            "Add extensions is-system-created.";
        yexte:version 1;
        yexte:release 0;
        yexte:correction 0;
        reference
            "RFC 7950: The YANG 1.1 Data Modeling Language";
    }

    revision 2021-01-11 {
        description
            "Initial version of the NRNetwork model.";
        yexte:version 0;
        yexte:release 1;
        yexte:correction 0;
        reference
            "RFC 7950: The YANG 1.1 Data Modeling Language";
    }

    grouping NRNetworkGrp {
        description
        "Represents the NRNetwork IOC.";

        leaf simpleNRFreqSmtc {
            description
                "Whether simplified SSB timing configuration is enabled in "+
                "NRFrequency MO.

                When true, the following NRFrequency attributes do not need to match "+
                "the RDN of this attribute:
                - smtcDuration
                - smtcOffset
                - smtcPeriodicity

                Value can only be set at creation.
                When true, value cannot be set to false again.";
            yexte:restricted;
            type boolean;
            yext3gpp:inVariant;
            status obsolete {
                yexte:status-information
                    "Since 22.17. Simple NRFrequency RDN is only supported.";
            }
            tailf:info 'Status Info: Since 22.17. Simple NRFrequency RDN is only supported, Obsolete, Whether simplified SSB timing configuration is enabled in NRFrequency MO. When true, the following NRFrequency attributes do not need to match the RDN of this attribute: - smtcDuration - smtcOffset - smtcPeriodicity Value can only be set at creation. When true, value cannot be set to false again.';
        }
    }

    augment "/me3gpp:ManagedElement/gnbcucp3gpp:GNBCUCPFunction" {
        list NRNetwork {
            description
                "Container for MOs related to NR networks.

                This MO is created automatically. Can also be created and deleted "+
                "manually.

                Created automatically when Xn message is received, unless it "+
                "already exists.

                When created automatically, the RDN of this MO is NRNetwork=1.";
            key id;
            max-elements 1;
            uses top3gpp:Top_Grp;
            container attributes {
                uses NRNetworkGrp;
            }
        }
    }
}
