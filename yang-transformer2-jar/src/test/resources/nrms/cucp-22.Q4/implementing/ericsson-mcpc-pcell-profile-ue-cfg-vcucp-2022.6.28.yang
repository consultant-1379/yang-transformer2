// Generated by eyang-preprocessor (1.22.0-48 2022-01-20 09:10:06 CET) on Jun 30, 2022, 8:31:39 AM
module ericsson-mcpc-pcell-profile-ue-cfg-vcucp {
    yang-version 1.1;
    namespace "urn:rdns:com:ericsson:oammodel:ericsson-mcpc-pcell-profile-ue-cfg-vcucp";
    prefix "mcpcpcellprofileuecfg";

    import tailf-common {
        prefix tailf;
    }
    import _3gpp-common-managed-element {
        prefix "me3gpp";
    }
    import _3gpp-nr-nrm-gnbcucpfunction {
        prefix "gnbcucp3gpp";
    }
    import _3gpp-common-top {
        prefix "top3gpp";
    }
    import ericsson-common-types-vcucp {
        prefix "commontypes";
    }
    import ericsson-yang-extensions {
        prefix "yexte";
    }
    import ericsson-mcpc-vcucp {
        prefix "mcpc";
    }
    import ericsson-mcpc-pcell-profile-vcucp {
        prefix "mcpcpcellprofile";
    }

    organization
        "Ericsson AB";
    contact
        "Ericsson first line support via email";
    description
        "The module defines the McpcPCellProfileUeCfg data model for the Ericsson vCU-CP.

        Copyright (c) 2022 Ericsson AB. All rights reserved.";

    revision 2022-06-28 {
        description
            "Removed module-status preliminary.
             Removed preliminary status from McpcPCellProfileUeCfg.";
        yexte:version 1;
        yexte:release 1;
        yexte:correction 0;
        reference
            "RFC 7950: The YANG 1.1 Data Modeling Language";
    }

    revision 2022-06-16 {
        description
            "Setting the correct max value of -29 on ReportConfigB2Rsrp::threshold1.";
        yexte:version 1;
        yexte:release 0;
        yexte:correction 0;
        reference
            "RFC 7950: The YANG 1.1 Data Modeling Language";
    }

    revision 2022-04-13 {
        description
            "Range of ReportConfigB2Rsrp::threshold1 temporary reverted to max -26 until upgrade is ready.";
        yexte:version 0;
        yexte:release 1;
        yexte:correction 1;
        reference
            "RFC 7950: The YANG 1.1 Data Modeling Language";
    }

    revision 2022-03-14 {
        description
            "Initial version of the McpcPCellProfileUeCfg model";
        yexte:version 0;
        yexte:release 1;
        yexte:correction 0;
        reference
            "RFC 7950: The YANG 1.1 Data Modeling Language";
    }

    grouping ReportConfigB2Rsrp {
        description
            "Report configuration settings for B2 measurement event when trigger quantity is RSRP.";

        leaf hysteresis {
            description
                "Hysteresis value for event B2.";
            type int32 {
                range "0..150";
            }
            must ". mod 5 = 0" {
                error-message
                    "The value must set with resolution/step of 5";
            }
            default 10;
            units "0.1 dB";
            reference
                "3GPP TS 38.331";
        }

        leaf threshold1 {
            description
                "RSRP threshold1 value for event B2.

                Value -29 defines threshold1 to infinity.";
            type int32 {
                range "-156..-29";
            }
            default -156;
            units dBm;
            reference
                "3GPP TS 38.331";
        }

        leaf threshold2EUtra {
            description
                "RSRP threshold2 value for event B2.";
            type int32 {
                range "-140..-44";
            }
            default -140;
            units dBm;
            reference
                "3GPP TS 38.331";
        }

        leaf timeToTrigger {
            description
                "Time-to-trigger value for eventB2.";
            type int32 {
                range "0|40|64|80|100|128|160|256|320|480|512|640|1024|1280|2560|5120";
            }
            default 640;
            units ms;
            reference
                "3GPP TS 38.331";
        }
    }

    grouping McpcPCellProfileUeCfgGrp {
        description
            "Represents the McpcPCellProfileUeCfg IOC.";

        leaf lowHighFreqPrioClassification {
            description
                "Classification of low and high frequency relation priority.

                NR frequency relation priorities are defined by "+
                "UeMCNrFreqRelProfile::connModePrioPCell attribute.

                E-UTRAN frequency relation priorities are defined by "+
                "UeMCEutranFreqRelProfile::connModePrioPCell attribute.

                Frequency relation priority is classified as high priority if it "+
                "equals or is higher than value of lowHighFreqPrioClassification, "+
                "else classified as low priority.";
            type int32 {
                range "0..7";
            }
            default 7;
            yexte:takes-effect
                "Next usage";
            tailf:info 'Takes effect: Next usage, Classification of low and high frequency relation priority. NR frequency relation priorities are defined by UeMCNrFreqRelProfile::connModePrioPCell attribute. E-UTRAN frequency relation priorities are defined by UeMCEutranFreqRelProfile::connModePrioPCell attribute. Frequency relation priority is classified as high priority if it equals or is higher than value of lowHighFreqPrioClassification, else classified as low priority.';
        }

        leaf-list mcpcQuantityList {
            min-elements 1;
            max-elements 2;
            ordered-by user;
            description
                "Measurement quantities on which PCell Mobility Control at Poor "+
                "Coverage function shall be applied.";
            type commontypes:McpcQuantity;
            yexte:initial-value RSRP;
            yexte:takes-effect
              "New connection";
            tailf:info 'Takes effect: New connection, Measurement quantities on which PCell Mobility Control at Poor Coverage function shall be applied.';
        }

        leaf-list prefUeGroupList {
            max-elements 8;
            ordered-by user;
            description
                "Preference UE group list.

                List of preference UE group identifiers.

                If empty, the MO instance matches preference UE group identifiers "+
                "not defined in prefUeGroupList of any other MO instances under "+
                "parent MO instance.";
            type int32 {
                range "1..255";
            }
            yexte:dependencies
                "Combinations of pair of preference UE group Identifier in "+
                "prefUeGroupList and UE group identifier in ueGroupList must be "+
                "unique among McpcPCellProfileUeCfg instances under same parent "+
                "McpcPCellProfile instance.

                For all preference UE group identifiers in prefUeGroupList "+
                "attributes under same parent McpcPCellProfile MO instance, exactly "+
                "one McpcPCellProfileUeCfg MO instance must exist that combines the "+
                "given preference UE group identifier with an empty ueGroupList.";
            yexte:disturbances
                "Changing this attribute can cause loss of traffic.";
            yexte:takes-effect
                "Next usage.";
            must "count(../../../McpcPCellProfileUeCfg/attributes[prefUeGroupList = current()
                    and count(ueGroupList) = 0] ) = 1" {
                error-message
                    "Exactly one McpcPCellProfileUeCfg instance under an "+
                    "McpcPCellProfile must combine a specific preference UE "+
                    "group identifier in attribute prefUeGroupList with an empty ueGroupList.";
            }
            tailf:info 'Takes effect: Next usage, Traffic Disturbance: Changing this attribute can cause loss of traffic, Dependencies: Combinations of pair of preference UE group Identifier in prefUeGroupList and UE group identifier in ueGroupList must be unique among McpcPCellProfileUeCfg instances under same parent McpcPCellProfile instance.

                For all preference UE group identifiers in prefUeGroupList attributes under same parent McpcPCellProfile MO instance, exactly one McpcPCellProfileUeCfg MO instance must exist that combines the given preference UE group identifier with an empty ueGroupList, Preference UE group list. List of preference UE group identifiers. If empty, the MO instance matches preference UE group identifiers not defined in prefUeGroupList of any other MO instances under parent MO instance.';
        }

        container rsrpCandidateA5 {
            description
                "RSRP A5 measurement report criteria when searching for PCell candidate.";
            uses commontypes:ReportConfigA5Rsrp;
            reference
                "3GPP TS 38.331";
            yexte:takes-effect
                "Next usage.";
            tailf:info 'Takes effect: Next usage, RSRP A5 measurement report criteria when searching for PCell candidate.';
        }

        container rsrpCandidateB2 {
            description
                "RSRP B2 measurement report criteria when searching for PCell candidate.";
            uses ReportConfigB2Rsrp;
            reference
                "3GPP TS 38.331";
            yexte:takes-effect
                "Next usage.";
            tailf:info 'Takes effect: Next usage, RSRP B2 measurement report criteria when searching for PCell candidate.';
        }

        container rsrpCritical {
            description
                "RSRP measurement report criteria for detecting critical coverage.";
            uses commontypes:ReportConfigA1A2Rsrp;
            reference
                "3GPP TS 38.331";
            yexte:takes-effect
                "Next usage.";
            tailf:info 'Takes effect: Next usage, RSRP measurement report criteria for detecting critical coverage.';
        }

        leaf rsrpCriticalEnabled {
            description
                "Whether RSRP measurement for detecting critical coverage is enabled.

                RSRP measurement criteria for detecting critical coverage is defined "+
                "by rsrpCritical attribute.";
            type boolean;
            default false;
            yexte:disturbances
                "Changing this attribute to true can trigger release of NR resources "+
                "if UE measurement event condition defined by rsrpCritical attribute "+
                "is been fulfilled.";
            yexte:takes-effect
                "Next usage.";
            tailf:info 'Takes effect: Next usage, Traffic Disturbance: Changing this attribute to true can trigger release of NR resources if UE measurement event condition defined by rsrpCritical attribute is been fulfilled, Whether RSRP measurement for detecting critical coverage is enabled. RSRP measurement criteria for detecting critical coverage is defined by rsrpCritical attribute.';
        }

        leaf rsrpSearchTimeRestriction {
            description
                "Search time restriction when searching for PCell candidate using DL "+
                "RSRP measurements.

                If set to -1, no time restriction is applied.";
            type int32 {
                range "-1|10..12000";
            }
            default -1;
            units ms;
            yexte:takes-effect
                "Next usage.";
            tailf:info 'Takes effect: Next usage, Search time restriction when searching for PCell candidate using DL RSRP measurements. If set to -1, no time restriction is applied.';
        }

        container rsrpSearchZone {
            description
                "RSRP measurement report criteria that define entering and leaving search zone.";
            uses commontypes:ReportConfigA1A2Rsrp;
            reference
                "3GPP TS 38.331";
            yexte:takes-effect
                "Next usage.";
            tailf:info 'Takes effect: Next usage, RSRP measurement report criteria that define entering and leaving search zone.';
        }

        leaf-list ueConfGroupList {
            max-elements 32;
            ordered-by user;
            description
                "UE configuration group list.

                List of UE configuration group identifiers.

                If empty, the MO instance matches all UE configuration group "+
                "identifiers.

                Which UE configuration group type that is applied is defined by "+
                "attribute ueConfGroupType in parent MO class instance.";
            type int32 {
                range "1..255";
            }
            yexte:dependencies
                "A given UE configuration group identifier can be defined in only one "+
                "ueConfGroupList among McpcPCellProfileUeCfg instances under same "+
                "parent McpcPCellProfile instance.";
            yexte:disturbances
                "Changing this attribute can cause loss of traffic.";
            yexte:takes-effect
                "Next usage.";
            must "count(../../../McpcPCellProfileUeCfg/attributes[ueConfGroupList = current() ]) &lt;= 1" {
                error-message
                    "Only one McpcPCellProfileUeCfg instance under an "+
                    "McpcPCellProfile can include a specific UE configuration "+
                    "group identifier in attribute ueConfGroupList.";
            }
            tailf:info 'Takes effect: Next usage, Traffic Disturbance: Changing this attribute can cause loss of traffic, Dependencies: A given UE configuration group identifier can be defined in only one ueConfGroupList among McpcPCellProfileUeCfg instances under same parent McpcPCellProfile instance, UE configuration group list. List of UE configuration group identifiers. If empty, the MO instance matches all UE configuration group identifiers. Which UE configuration group type that is applied is defined by attribute ueConfGroupType in parent MO class instance.';
        }

        leaf-list ueGroupList {
            max-elements 16;
            ordered-by user;
            description
                "UE group list.

                List of UE group identifiers.

                If empty, the MO instance matches all UE group identifiers.";
            type int32 {
                range "1..255";
            }
            yexte:dependencies
                "Combinations of pair of UE group Identifier and preference UE group "+
                "Identifier in ueGroupList and prefUeGroupList must be unique among "+
                "McpcPCellProfileUeCfg instances defined under same parent "+
                "McpcPCellProfile instance.

                Combination of a UE group identifier in UeGroupList and empty "+
                "prefUeGroupList must be unique among McpcPCellProfileUeCfg instances "+
                "under same parent McpcPCellProfile instance.";
            yexte:disturbances
                "Changing this attribute can cause loss of traffic.";
            yexte:takes-effect
                "Next usage.";
            must "count(../prefUeGroupList) &gt; 0 or
                  count(../../../McpcPCellProfileUeCfg/attributes[ueGroupList = current()
                    and count(prefUeGroupList) = 0] ) &lt;= 1" {
                error-message
                    "Only one McpcPCellProfileUeCfg instance under an "+
                    "McpcPCellProfile can combine a specific UE group identifier "+
                    "in attribute ueGroupList with an empty prefUeGroupList.";
            }
            tailf:info 'Takes effect: Next usage, Traffic Disturbance: Changing this attribute can cause loss of traffic, Dependencies: Combinations of pair of UE group Identifier and preference UE group Identifier in ueGroupList and prefUeGroupList must be unique among McpcPCellProfileUeCfg instances defined under same parent McpcPCellProfile instance.

                Combination of a UE group identifier in UeGroupList and empty prefUeGroupList must be unique among McpcPCellProfileUeCfg instances under same parent McpcPCellProfile instance, UE group list. List of UE group identifiers. If empty, the MO instance matches all UE group identifiers.';
        }
    }

    augment "/me3gpp:ManagedElement/gnbcucp3gpp:GNBCUCPFunction/mcpc:Mcpc/mcpcpcellprofile:McpcPCellProfile" {
        list McpcPCellProfileUeCfg {
            description
                "Mobility control at coor coverage (MCPC) for PCell, UE "+
                "configuration group.

                Applies to UEs that use cell as PCell. Attributes are used on "+
                "cell level.

                MO instance McpcPCellProfileUeCfg=Base is created "+
                "automatically when parent MO is created, unless created "+
                "manually in the same transaction as parent MO.

                Attributes prefUeGroupList, ueGroupList and ueConfGroupList "+
                "must be empty in instance McpcPCellProfileUeCfg=Base but "+
                "cannot all be empty in other instances of "+
                "McpcPCellProfileUeCfg under same parent McpcPCellProfile.";
            yexte:precondition
                "McpcPCellProfileUeCfg=Base MO instance can only be created in "+
                "the same transaction as parent MO and must not be deleted unless "+
                "parent MO is deleted. Other instances can be created and "+
                "deleted manually.

                Maximum 31 McpcPCellProfileUeCfg instances, with RDN different "+
                "from Base, can be created.";
            key id;
            uses top3gpp:Top_Grp;
            max-elements 32;
            container attributes {
                uses McpcPCellProfileUeCfgGrp;
                uses commontypes:UserLabelGrp;
            }
            must "count(../McpcPCellProfileUeCfg) &lt; 32 or
                  count(../McpcPCellProfileUeCfg/id[. = 'Base'] ) = 1" {
                error-message
                    "Maximum 31 McpcPCellProfileUeCfg instances under an "+
                    "McpcPCellProfile can be created with RDN different from Base.";
            }
            must "count(../McpcPCellProfileUeCfg/attributes[prefUeGroupList = current()/attributes/prefUeGroupList
                    and ueGroupList = current()/attributes/ueGroupList] ) &lt;= 1" {
                error-message
                    "The combinations of a pair of UE group identifier in ueGroupList "+
                    "and preference UE group identifier in prefUeGroupList must be "+
                    "unique among McpcPCellProfileUeCfg under an McpcPCellProfile.";
            }
            must "./id != 'Base'
                    or ( count(./attributes/ueConfGroupList) = 0
                         and count(./attributes/ueGroupList) = 0
                         and count(./attributes/prefUeGroupList) = 0 )" {
                error-message
                    "prefUeGroupList, ueGroupList and ueConfGroupList must be empty "+
                    "in the McpcPCellProfileUeCfg=Base instance.";
            }
            must "./id = 'Base'
                    or not ( count(./attributes/ueConfGroupList) = 0
                             and count(./attributes/ueGroupList) = 0
                             and count(./attributes/prefUeGroupList) =  0 )" {
                error-message
                    "prefUeGroupList, ueGroupList and ueConfGroupList can only be empty "+
                    "in the McpcPCellProfileUeCfg=Base instance.";
            }
            tailf:info 'Precondition: McpcPCellProfileUeCfg=Base MO instance can only be created in the same transaction as parent MO and must not be deleted unless parent MO is deleted. Other instances can be created and deleted manually.

                Maximum 31 McpcPCellProfileUeCfg instances, with RDN different from Base, can be created, Mobility control at coor coverage (MCPC) for PCell, UE configuration group. Applies to UEs that use cell as PCell. Attributes are used on cell level. MO instance McpcPCellProfileUeCfg=Base is created automatically when parent MO is created, unless created manually in the same transaction as parent MO. Attributes prefUeGroupList, ueGroupList and ueConfGroupList must be empty in instance McpcPCellProfileUeCfg=Base but cannot all be empty in other instances of McpcPCellProfileUeCfg under same parent McpcPCellProfile.';
        }
    }
}
