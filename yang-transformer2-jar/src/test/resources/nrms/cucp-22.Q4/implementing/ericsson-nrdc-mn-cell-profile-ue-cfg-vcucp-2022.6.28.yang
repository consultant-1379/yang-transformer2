// Generated by eyang-preprocessor (1.22.0-48 2022-01-20 09:10:06 CET) on Jun 30, 2022, 8:31:41 AM
module ericsson-nrdc-mn-cell-profile-ue-cfg-vcucp {
    yang-version 1.1;
    namespace "urn:rdns:com:ericsson:oammodel:ericsson-nrdc-mn-cell-profile-ue-cfg-vcucp";
    prefix nrdcmncellprofileuecfg;

    import tailf-common {
        prefix tailf;
    }
    import _3gpp-common-managed-element {
        prefix "me3gpp";
    }
    import _3gpp-nr-nrm-gnbcucpfunction {
        prefix "gnbcucp3gpp";
    }
    import _3gpp-common-top {
        prefix "top3gpp";
    }
    import ericsson-yang-extensions {
        prefix "yexte";
    }
    import ericsson-nrdc-control-vcucp {
        prefix "nrdccontrol";
    }
    import ericsson-nrdc-mn-cell-profile-vcucp {
        prefix "nrdcmncellprofile";
    }

    organization
        "Ericsson AB";
    contact
        "Ericsson first line support via email";
    description
        "The module defines the NrdcMnCellProfileUeCfg data model for the Ericsson vCU-CP.

        Copyright (c) 2022 Ericsson AB. All rights reserved.";

    revision 2022-06-28 {
        description
            "Removed module-status preliminary.
             Removed preliminary status from NrdcMnCellProfileUeCfg.";
        yexte:version 0;
        yexte:release 2;
        yexte:correction 0;
        reference
            "RFC 7950: The YANG 1.1 Data Modeling Language";
    }

    revision 2022-03-14 {
        description
            "Initial version of the NrdcMnCellProfileUeCfg model.";
        yexte:version 0;
        yexte:release 1;
        yexte:correction 0;
        reference
            "RFC 7950: The YANG 1.1 Data Modeling Language";
    }

    grouping ReportConfigA4Rsrp {
        description
          "Report configuration settings for A4 measurement event when trigger "+
          "quantity is RSRP.";
        leaf hysteresis {
            description
              "Hysteresis value for RSRP in UE event A4 measurement.";
            type int32 {
                range "0..150";
            }
            default 10;
            units "0.1 dB";
            must ". mod 5 = 0" {
                error-message
                  "The value must set with resolution/step of 5";
            }
            reference
              "3GPP TS 38.331";
        }

        leaf threshold {
            description
              "RSRP threshold value for UE event A4 measurement.";
            type int32 {
                range "-156..-29";
            }
            default -156;
            units dBm;
            reference
              "3GPP TS 38.331";
        }

        leaf timeToTrigger {
            description
              "Time-to-trigger value for RSRP in UE event A4 measurement.";
            type int32 {
                range "0|40|64|80|100|128|160|256|320|480|512|640|1024|1280|2560|5120";
            }
            default 0;
            units ms;
            reference
              "3GPP TS 38.331";
        }
    }

    grouping NrdcMnCellProfileUeCfgGrp {
        description
            "Represents the NrdcMnCellProfileUeCfg IOC.";

        leaf nrdcEnabled {
            description
              "Whether NR-NR Dual Connectivity is enabled for the PCell in Master "+
              "Node.";
            type boolean;
            default false;
            yexte:takes-effect
              "Next usage";
            tailf:info 'Takes effect: Next usage, Whether NR-NR Dual Connectivity is enabled for the PCell in Master Node.';
        }

        leaf nrdcMeasRestartTime {
            description
              "Time to wait for next A4 measurement period to find suitable PSCell "+
              "candidate for NR-DC.";
            type int32 {
                range "40..240000";
            }
            default 15000;
            units ms;
            yexte:takes-effect
              "Next usage.";
            tailf:info 'Takes effect: Next usage, Time to wait for next A4 measurement period to find suitable PSCell candidate for NR-DC.';
        }

        leaf nrdcMeasTime {
            description
              "Time in which UE performs A4 measurements to find suitable PSCell "+
              "candidate for NR-DC.";
            type int32 {
                range "40..120000";
            }
            default 2000;
            units ms;
            yexte:takes-effect
              "Next usage.";
            tailf:info 'Takes effect: Next usage, Time in which UE performs A4 measurements to find suitable PSCell candidate for NR-DC.';
        }

        container rsrpPSCellCandidate {
            description
              "RSRP A4 measurement report criteria when searching for PSCell "+
              "candidate.";

            uses ReportConfigA4Rsrp;
            yexte:takes-effect
              "Next usage";
            tailf:info 'Takes effect: Next usage, RSRP A4 measurement report criteria when searching for PSCell candidate.';
        }
    }

    augment "/me3gpp:ManagedElement/gnbcucp3gpp:GNBCUCPFunction/nrdccontrol:NrdcControl/nrdcmncellprofile:NrdcMnCellProfile" {
        list NrdcMnCellProfileUeCfg {
            description
              "NR-NR Dual Connectivity control for PCell in Master Node, UE "+
              "configuration group.

              Applies to UEs which use the cell as PCell in Master Node. "+
              "Attributes are used on cell level.

              MO instance NrdcMnCellProfileUeCfg=Base is created "+
              "automatically when parent MO is created, unless created "+
              "manually in the same transaction as parent MO.

              The RDN of this MO must always be NrdcMnCellProfileUeCfg=Base.";
            yexte:precondition
              "NrdcMnCellProfileUeCfg=Base MO instance can only be created in "+
              "the same transaction as parent MO and must not be deleted unless "+
              "parent MO is deleted.";
            key id;
            max-elements 1;
            uses top3gpp:Top_Grp {
                refine id {
                    must '. = "Base"' {
                        error-message
                          "The RDN of this MO must always be NrdcMnCellProfileUeCfg=Base";
                    }
                }
            }
            container attributes {
                uses NrdcMnCellProfileUeCfgGrp;
            }
            tailf:info 'Precondition: NrdcMnCellProfileUeCfg=Base MO instance can only be created in the same transaction as parent MO and must not be deleted unless parent MO is deleted, NR-NR Dual Connectivity control for PCell in Master Node, UE configuration group. Applies to UEs which use the cell as PCell in Master Node. Attributes are used on cell level. MO instance NrdcMnCellProfileUeCfg=Base is created automatically when parent MO is created, unless created manually in the same transaction as parent MO. The RDN of this MO must always be NrdcMnCellProfileUeCfg=Base.';
        }
    }
}
