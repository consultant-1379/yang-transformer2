// Generated by eyang-preprocessor (1.24.0-23 2022-06-22 14:11:55 CEST) on Jun 28, 2022, 10:45:18 AM
module ericsson-transport-types-vcu {
    yang-version 1.1;
    namespace urn:rdns:com:ericsson:oammodel:ericsson-transport-types-vcu;
    prefix transtypes;

    import ericsson-yang-extensions {
        prefix yexte;
    }

    organization
        "Ericsson AB";
    contact
        "Ericsson first line support via email";
    description
        "The module defines common types used by the transport classes for the Ericsson vCU.

    Copyright (c) 2021-2022 Ericsson AB. All rights reserved.";

    revision 2022-06-28 {
        description
            "Removed module-status preliminary.";
        yexte:version 0;
        yexte:release 2;
        yexte:correction 0;
        reference
            "RFC 7950: The YANG 1.1 Data Modeling Language";
    }

    revision 2021-01-12 {
        description
            "Initial revision.";
        yexte:version 0;
        yexte:release 1;
        yexte:correction 0;
        reference
            "RFC 7950: The YANG 1.1 Data Modeling Language";
    }

    typedef InterfaceName {
        type enumeration {
            enum E1 {
                value 1;
                description "E1 for control and user plane.";
            }
            enum F1 {
                value 3;
                description "F1 for control and user plane.";
            }
            enum NG {
                value 4;
                description "NG for control and user plane.";
            }
            enum S1 {
                value 5;
                description "S1 for user plane.";
            }
            enum XN {
                value 6;
                description "Xn for control and user plane.";
            }
            enum X2 {
                value 7;
                description "X2 for control and user plane.";
            }
        }
    }

    typedef PortNumber {
        description "Valid port numbers for protocols such as UDP, TCP and SCTP.";
        type uint16 {
            range "1..65535";
        }
    }

    typedef ReferenceId {
        description "MO identifier.";
        type string;
    }
}
