// Generated by eyang-preprocessor (1.22.0-48 2022-01-20 09:10:06 CET) on Sep 4, 2022, 12:23:58 PM
module ericsson-nrfreqrelation-ext-vcucp {
    yang-version 1.1;
    namespace urn:rdns:com:ericsson:oammodel:ericsson-nrfreqrelation-ext-vcucp;
    prefix nrfreqrel3gppext;

    import tailf-common {
        prefix tailf;
    }
    import _3gpp-common-managed-element {
        prefix me3gpp;
    }
    import _3gpp-nr-nrm-gnbcucpfunction {
        prefix gnbcucp3gpp;
    }
    import _3gpp-nr-nrm-nrcellcu {
        prefix nrcellcu3gpp;
    }
    import _3gpp-nr-nrm-nrfreqrelation {
        prefix nrfreqrel3gpp;
    }
    import _3gpp-common-yang-types {
        prefix types3gpp;
    }
    import _3gpp-common-yang-extensions {
        prefix yext3gpp;
    }
    import ericsson-mcpc-vcucp {
        prefix mcpc;
    }
    import ericsson-mcpc-pcell-nr-freq-rel-profile-vcucp {
        prefix mcpcpcellnrfreqrelprofile;
    }
    import ericsson-mcpc-pscell-nr-freq-rel-profile-vcucp {
        prefix mcpcpscellnrfreqrelprofile;
    }
    import ericsson-nrnetwork-vcucp {
        prefix nrnetwork;
    }
    import ericsson-nrfrequency-vcucp {
        prefix nrfrequency;
    }
    import ericsson-yang-extensions {
        prefix yexte;
    }
    import ericsson-uemc-vcucp {
        prefix uemcvcucp;
    }
    import ericsson-uemcnrfreqrelprofile-vcucp {
        prefix uemcnrfreqrelprofilevcucp;
    }
    import ericsson-intrafreqmc-vcucp {
        prefix intrafreqmc;
    }
    import ericsson-intrafreqmcfreqrelprofile-vcucp {
        prefix intrafreqmcfreqrelprofile;
    }
    import ericsson-trafficsteering-vcucp {
        prefix trafficsteering;
    }
    import ericsson-trstsanrfreqrelprofile-vcucp {
        prefix trstsanrfreqrelprofile;
    }

    organization
      "Ericsson AB";
    contact
      "Ericsson first line support via email";
    description
      "The module defines the NRFreqRelation data model extensions for the Ericsson vCU-CP.

       Copyright (c) 2021-2022 Ericsson AB. All rights reserved.";

    revision 2022-08-10 {
        description
            "Updated dependencies description for cellReselectionPriority.";
        yexte:version 2;
        yexte:release 1;
        yexte:correction 1;
        reference
            "RFC 7950: The YANG 1.1 Data Modeling Language";
    }

    revision 2022-06-28 {
        description
            "Removed module-status preliminary.
             Removed preliminary status from trStSaNrFreqRelProfileRef.";
        yexte:version 2;
        yexte:release 1;
        yexte:correction 0;
        reference
            "RFC 7950: The YANG 1.1 Data Modeling Language";
    }

    revision 2022-06-16 {
        description
            "Set missing range on cellReselectionPriority.";
        yexte:version 2;
        yexte:release 0;
        yexte:correction 0;
        reference
            "RFC 7950: The YANG 1.1 Data Modeling Language";
    }

    revision 2022-04-20 {
        description
            "Restore old type on cellReselectionPriority due to issues with changing type.";
        yexte:version 1;
        yexte:release 4;
        yexte:correction 1;
        reference
            "RFC 7950: The YANG 1.1 Data Modeling Language";
    }

    revision 2022-03-14 {
        description
            "Updated description of NRFreqRelation.
            Updated description and type of cellReselectionPriority.
            Updated description of cellReselectionSubPriority.
            Added dependencies to nRFrequencyRef.
            Updated description of plmnIdList.";
        yexte:version 1;
        yexte:release 4;
        yexte:correction 0;
        reference
            "RFC 7950: The YANG 1.1 Data Modeling Language";
    }

    revision 2021-11-09 {
        description
            "Add the attributes anrMeasOn, intraFreqMCFreqRelProfileRef and trStSaNrFreqRelProfileRef.
             Update description and add dependencies for mcpcPCellNrFreqRelProfileRef.
             Remove takes-effect from qRxLevMin.";
        yexte:version 1;
        yexte:release 3;
        yexte:correction 0;
        reference
            "RFC 7950: The YANG 1.1 Data Modeling Language";
    }

    revision 2021-09-20 {
        description
            "Add the mcpcPSCellNrFreqRelProfileRef attribute.
             Update description for ueMCNrFreqRelProfileRef.";
        yexte:version 1;
        yexte:release 2;
        yexte:correction 0;
        reference
            "RFC 7950: The YANG 1.1 Data Modeling Language";
    }

    revision 2021-06-08 {
        description
            "Changed error messages for must statements.";
        yexte:version 1;
        yexte:release 1;
        yexte:correction 1;
        reference
            "RFC 7950: The YANG 1.1 Data Modeling Language";
    }

    revision 2021-05-06 {
        description
          "Remove is-system-created and restricted extensions.
           Add yext3gpp:inVariant to nRFrequencyRef.";
        yexte:version 1;
        yexte:release 1;
        yexte:correction 0;
        reference
          "RFC 7950: The YANG 1.1 Data Modeling Language";
    }

    revision 2021-04-27 {
        description
          "Add must rules to nRFrequencyRef and mcpcPCellNrFreqRelProfileRef.";
        yexte:version 1;
        yexte:release 0;
        yexte:correction 2;
        reference
          "RFC 7950: The YANG 1.1 Data Modeling Language";
    }

    revision 2021-04-21 {
        description
          "Correct must statement for MO reference.";
        yexte:version 1;
        yexte:release 0;
        yexte:correction 1;
        reference
          "RFC 7950: The YANG 1.1 Data Modeling Language";
    }

    revision 2021-03-22 {
        description
          "Initial version of the NRFreqRelation model.";
        yexte:version 1;
        yexte:release 0;
        yexte:correction 0;
        reference
          "RFC 7950: The YANG 1.1 Data Modeling Language";
    }

    deviation /me3gpp:ManagedElement/gnbcucp3gpp:GNBCUCPFunction/nrcellcu3gpp:NRCellCU/nrfreqrel3gpp:NRFreqRelation {
        deviate add {
            yexte:updated-description
                "Mobility relation between NR cell and an NR frequency.

                Must use an NRFrequency on the Global Synchronization Channel "+
                "Raster (indicated in NRFrequency::gscn) for Standalone operation.
                Frequency relation not on the GSCN are not included in SIB4, nor "+
                "used for PCell mobility.

                Created automatically when F1 or Xn message is received and cell "+
                "frequency is in frequency range defined in "+
                "NRFreqRelationTemplate.

                When created automatically, the RDN of this MO is "+
                "NrFreqRelation=auto<arfcn>_<scs>.";
        }
    }

    deviation /me3gpp:ManagedElement/gnbcucp3gpp:GNBCUCPFunction/nrcellcu3gpp:NRCellCU/nrfreqrel3gpp:NRFreqRelation/nrfreqrel3gpp:attributes/nrfreqrel3gpp:cellReselectionPriority {
        deviate replace {
            type uint32 {
                range "0..7";
            }
            default 7;
        }
        deviate add {
            yexte:updated-description
                "Absolute priority of carrier frequency used by cell reselection "+
                "procedure.

                This attribute is broadcast in SIB2 or SIB4, depending on whether "+
                "related frequency is intra-frequency or inter-frequency.
                Value 0 means lowest priority.
                Value must be unique between RATs. This means that equal priorities "+
                "between RATs are not supported.";
            yexte:dependencies
                "The cellReselectionPriority must be unique between NRFreqRelations "+
                "and EUtranFreqRelations under the same NRCellCU.
                If NRCellCU::transmitSib2 is true at least one intra-frequency NRFreqRelation "+
                "instance under NRCellCU must have cellReselectionPriority different than -1.
                If NRCellCU::transmitSib4 is true atleast one inter-frequency NRFreqRelation "+
                "instance under NRCellCU must have cellReselectionPriority different than -1.";
            yexte:takes-effect "Next cell unlock";
        }
    }

    deviation /me3gpp:ManagedElement/gnbcucp3gpp:GNBCUCPFunction/nrcellcu3gpp:NRCellCU/nrfreqrel3gpp:NRFreqRelation/nrfreqrel3gpp:attributes/nrfreqrel3gpp:cellReselectionSubPriority {
        deviate add {
            yexte:updated-description
                "Subpriority value of NR carrier frequency.

                Subpriority value added to value of cellReselectionPriority to "+
                "obtain absolute priority of carrier frequency.
                If empty, this attribute is not broadcast in SIB2 and SIB4.
                This attribute is broadcast accompanied by cellReselectionPriority "+
                "in SIB2 or SIB4, depending on whether related frequency is "+
                "intra-frequency or inter-frequency.";
            yexte:takes-effect
                "New connection for RRCRelease message.
                Otherwise, immediately.";
        }
    }

    deviation /me3gpp:ManagedElement/gnbcucp3gpp:GNBCUCPFunction/nrcellcu3gpp:NRCellCU/nrfreqrel3gpp:NRFreqRelation/nrfreqrel3gpp:attributes/nrfreqrel3gpp:nRFrequencyRef {
        deviate add {
            must "re-match(current(), 'ManagedElement=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,GNBCUCPFunction=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,NRNetwork=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,NRFrequency=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?') and
                  re-match(current(), concat('ManagedElement=', ../../../../../me3gpp:id, ',.*')) and
                  re-match(current(), concat('.*GNBCUCPFunction=', ../../../../gnbcucp3gpp:id, ',.*')) and
                  count(../../../../nrnetwork:NRNetwork[re-match(current(), concat('.*NRNetwork=', nrnetwork:id, ',.*'))]/nrfrequency:NRFrequency[re-match(current(), concat('.*NRFrequency=', nrfrequency:id))]) > 0" {
                error-message
                    "nRFrequencyRef must refer to an NRFrequency";
            }
            yexte:updated-description
                "Reference to an instance of NRFrequency MO.

                 Must be unique among NRFreqRelations under an NRCellCU.";
            yext3gpp:inVariant;
            yexte:dependencies
                "Value of NRFrequency::arfcnValueNRDl must be unique among "+
                "NRFrequency MO instances referenced by NRFreqRelation MO instances "+
                "under NRCellCU MO instance.";
        }
    }

    deviation /me3gpp:ManagedElement/gnbcucp3gpp:GNBCUCPFunction/nrcellcu3gpp:NRCellCU/nrfreqrel3gpp:NRFreqRelation/nrfreqrel3gpp:attributes/nrfreqrel3gpp:pMax {
        deviate replace {
            type int32 {
                range "-30..26";
            }
        }
        deviate add {
            yexte:initial-value 23;
            yexte:updated-description
               "Parameter used to calculate Pcompensation at cell reselection.

                Corresponds to parameter PEMAX in 3GPP TS 38.101.
                This attribute is broadcast in SIB2 or SIB4, depending on whether related frequency is intra-frequency or inter-frequency.
                If empty, value is not broadcast in SIB2 and SIB4 and UE applies maximum power according to 3GPP TS 38.101.
                Only applicable for Low-Band and Mid-Band cells.";
            yexte:takes-effect "Next cell unlock";
        }
    }

    deviation /me3gpp:ManagedElement/gnbcucp3gpp:GNBCUCPFunction/nrcellcu3gpp:NRCellCU/nrfreqrel3gpp:NRFreqRelation/nrfreqrel3gpp:attributes/nrfreqrel3gpp:qQualMin {
        deviate replace {
            type int32 {
                range "-43..-12";
            }
        }
        deviate delete {
            default 0;
        }
        deviate add {
            yexte:updated-description
                "Minimum required quality level RSRQ in the cell.

                This attribute is broadcast in SIB2 or SIB4, depending on whether the related frequency is intra-frequency or inter-frequency.
                If the attribute is set to empty, the value is not broadcast in SIB2 or SIB4, and the UE applies the default value of negative infinity for Qqualmin in 3GPP TS 38.304.";
            yexte:takes-effect "Next cell unlock";
        }
    }

    deviation /me3gpp:ManagedElement/gnbcucp3gpp:GNBCUCPFunction/nrcellcu3gpp:NRCellCU/nrfreqrel3gpp:NRFreqRelation/nrfreqrel3gpp:attributes/nrfreqrel3gpp:qRxLevMin {
        // Replace deviate for removing the Mandatory statement is deliberately added here instead of the -ext file since the YANG validator gives an error if this is separated from the default value statement (not present for this attribute).
        deviate replace {
            mandatory false;
        }
        deviate add {
            default -140;
            must ". mod 2 = 0" {
                error-message
                  "qRxLevMin must be set with resolution/step of 2.";
            }
            yexte:updated-description
                "Minimum received RSRP level in cell reselection.

                This attribute is broadcast in SIB2 or SIB4, depending on whether the related frequency is intra-frequency or inter-frequency.
                Corresponds to parameter Qrxlevmin in 3GPP TS 38.304.";
        }
    }

    deviation /me3gpp:ManagedElement/gnbcucp3gpp:GNBCUCPFunction/nrcellcu3gpp:NRCellCU/nrfreqrel3gpp:NRFreqRelation/nrfreqrel3gpp:attributes/nrfreqrel3gpp:threshXHighP {
        // Replace deviate for removing the Mandatory statement is deliberately added here instead of the -ext file since the YANG validator gives an error if this is separated from the default value statement (not present for this attribute).
        deviate replace {
            mandatory false;
        }
        deviate add {
            default 4;
            must ". mod 2 = 0" {
                error-message
                  "threshXHighP must be set with resolution/step of 2.";
            }
            yexte:updated-description
                "RSRP threshold level for reselection to higher priority.

                Each frequency of NR can have a specific threshold.";
            yexte:takes-effect "Next cell unlock";
        }
    }

    deviation /me3gpp:ManagedElement/gnbcucp3gpp:GNBCUCPFunction/nrcellcu3gpp:NRCellCU/nrfreqrel3gpp:NRFreqRelation/nrfreqrel3gpp:attributes/nrfreqrel3gpp:threshXHighQ {
        // Replace deviate for removing the Mandatory statement is deliberately added here instead of the -ext file since the YANG validator gives an error if this is separated from the default value statement (not present for this attribute).
        deviate replace {
            mandatory false;
        }
        deviate add {
            yexte:updated-description
                "RSRQ threshold level for reselection to higher priority.

                 Threshold used by UE when reselecting towards a higher priority frequency X from the actual serving frequency.
                 Each frequency of NR can have a specific threshold.
                 If empty, value is not broadcast in SIB4.";
            yexte:dependencies "Must be empty if NRCellCU::threshServingLowQ is empty or set if NRCellCU::threshServingLowQ is set.";
            yexte:takes-effect "Next cell unlock";
        }
    }

    deviation /me3gpp:ManagedElement/gnbcucp3gpp:GNBCUCPFunction/nrcellcu3gpp:NRCellCU/nrfreqrel3gpp:NRFreqRelation/nrfreqrel3gpp:attributes/nrfreqrel3gpp:threshXLowP {
        // Replace deviate for removing the Mandatory statement is deliberately added here instead of the -ext file since the YANG validator gives an error if this is separated from the default value statement (not present for this attribute).
        deviate replace {
            mandatory false;
        }
        deviate add {
            default 0;
            must ". mod 2 = 0" {
                error-message
                  "threshXLowP must be set with resolution/step of 2.";
            }
            yexte:updated-description
                "RSRP threshold level for reselection to lower priority.

                Each frequency of NR can have a specific threshold.";
            yexte:takes-effect "Next cell unlock";
        }
    }

    deviation /me3gpp:ManagedElement/gnbcucp3gpp:GNBCUCPFunction/nrcellcu3gpp:NRCellCU/nrfreqrel3gpp:NRFreqRelation/nrfreqrel3gpp:attributes/nrfreqrel3gpp:threshXLowQ {
        // Replace deviate for removing the Mandatory statement is deliberately added here instead of the -ext file since the YANG validator gives an error if this is separated from the default value statement (not present for this attribute).
        deviate replace {
            mandatory false;
        }
        deviate add {
            yexte:updated-description
                "RSRQ threshold level for reselection to lower priority.

                 The threshold used by the UE when reselecting towards a lower priority frequency X from the current serving frequency.
                 Each frequency of NR can have a specific threshold.
                 If the attribute is set to empty the value is not broadcast in SIB.";
            yexte:dependencies "Must be empty if NRCellCU::threshServingLowQ is empty or set if NRCellCU::threshServingLowQ is set.";
            yexte:takes-effect "Next cell unlock";
        }
    }

    deviation /me3gpp:ManagedElement/gnbcucp3gpp:GNBCUCPFunction/nrcellcu3gpp:NRCellCU/nrfreqrel3gpp:NRFreqRelation/nrfreqrel3gpp:attributes/nrfreqrel3gpp:tReselectionNR {
        // Replace deviate for removing the Mandatory statement is deliberately added here instead of the -ext file since the YANG validator gives an error if this is separated from the default value statement (not present for this attribute).
        deviate replace {
            mandatory false;
        }
        deviate add {
            default 2;
            yexte:updated-description
                "Time interval that evaluates the criteria before the reselection can be done.

                This attribute is broadcast in SIB2 or SIB4, depending on whether the related frequency is intra-frequency or inter-frequency.";
            yexte:takes-effect "Next cell unlock";
        }
    }

    deviation /me3gpp:ManagedElement/gnbcucp3gpp:GNBCUCPFunction/nrcellcu3gpp:NRCellCU/nrfreqrel3gpp:NRFreqRelation/nrfreqrel3gpp:attributes/nrfreqrel3gpp:tReselectionNRSfHigh {
        // Replace deviate for removing the Mandatory statement is deliberately added here instead of the -ext file since the YANG validator gives an error if this is separated from the default value statement (not present for this attribute).
        deviate replace {
            mandatory false;
        }
        deviate add {
            yexte:updated-description
                "Speed-dependent scaling factor for TreselectionNR.

                For NR intra-frequency or inter-frequency cell reselection, concerned mobility control related parameter is multiplied with this factor if UE is in high mobility state.
                This attribute is broadcast in SIB2 or SIB4, depending on whether related frequency is intra-frequency or inter-frequency.
                If empty, no t-ReselectionNR-SF will be broadcast in SIB2 or SIB4.";
            yexte:takes-effect "New connection";
        }
    }

    deviation /me3gpp:ManagedElement/gnbcucp3gpp:GNBCUCPFunction/nrcellcu3gpp:NRCellCU/nrfreqrel3gpp:NRFreqRelation/nrfreqrel3gpp:attributes/nrfreqrel3gpp:tReselectionNRSfMedium {
        // Replace deviate for removing the Mandatory statement is deliberately added here instead of the -ext file since the YANG validator gives an error if this is separated from the default value statement (not present for this attribute).
        deviate replace {
            mandatory false;
        }
        deviate add {
            yexte:updated-description
                "Speed-dependent scaling factor for TreselectionNR.

                For NR intra-frequency or inter-frequency cell reselection, concerned mobility control related parameter is multiplied with this factor if UE is in medium mobility state.
                This attribute is broadcast in SIB2 or SIB4, depending on whether related frequency is intra-frequency or inter-frequency.
                If empty, no t-ReselectionNR-SF will be broadcast in SIB2 or SIB4.";
            yexte:takes-effect "New connection";
        }
    }

    grouping NRFreqRelationVCUCPGrp {
        description
          "Ericsson extensions to the 3gpp NRFreqRelation.";
        reference
          "Ericsson documentation";

        leaf anrMeasOn {
            description
                "Whether ANR measurement on referenced frequency is enabled.";
            type boolean;
            default true;
        }

        leaf intraFreqMCFreqRelProfileRef {
            description
                "Reference to instance of IntraFreqMCFreqRelProfile MO.

                If non-empty, attributes from referenced MO instance are used.
                If empty, attribute default values according to "+
                "IntraFreqMCFreqRelProfile and IntraFreqMCFreqRelProfileUeCfg MO "+
                "class definitions are used.";
            type types3gpp:DistinguishedName;
            must "re-match(current(), 'ManagedElement=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,GNBCUCPFunction=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,IntraFreqMC=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,IntraFreqMCFreqRelProfile=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?') and
                  re-match(current(), concat('ManagedElement=', ../../../../../me3gpp:id, ',.*')) and
                  re-match(current(), concat('.*GNBCUCPFunction=', ../../../../gnbcucp3gpp:id, ',.*')) and
                  count(../../../../intrafreqmc:IntraFreqMC[re-match(current(), concat('.*IntraFreqMC=', intrafreqmc:id, ',.*'))]/intrafreqmcfreqrelprofile:IntraFreqMCFreqRelProfile[re-match(current(), concat('.*IntraFreqMCFreqRelProfile=', intrafreqmcfreqrelprofile:id))]) > 0" {
                description
                    "The instance identifier must point at a IntraFreqMCFreqRelProfile MO.

                    Example of a valid value is
                    ManagedElement=1,GNBCUCPFunction=1,"+
                    "IntraFreqMC=1,IntraFreqMCFreqRelProfile=Default";
                error-message
                    "intraFreqMCFreqRelProfileRef must refer to an IntraFreqMCFreqRelProfile under the same GNBCUCPFunction.";
            }
            yexte:dependencies
                "Referenced IntraFreqMCFreqRelProfile must be under IntraFreqMC MO "+
                "and under same GNBCUCPFunction as NRCellCU.";
            yexte:takes-effect
                "Next usage.";
            tailf:info 'Takes effect: Next usage, Dependencies: Referenced IntraFreqMCFreqRelProfile must be under IntraFreqMC MO and under same GNBCUCPFunction as NRCellCU, Reference to instance of IntraFreqMCFreqRelProfile MO. If non-empty, attributes from referenced MO instance are used. If empty, attribute default values according to IntraFreqMCFreqRelProfile and IntraFreqMCFreqRelProfileUeCfg MO class definitions are used.';
        }

        leaf mcpcPCellNrFreqRelProfileRef {
            description
                "Reference to instance of McpcPCellNrFreqRelProfile MO.

                If non-empty, attributes from referenced MO instance are used.
                If empty, attribute default values according to MO class definition "+
                "are used.";
            type types3gpp:DistinguishedName;
            must "re-match(current(), 'ManagedElement=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,GNBCUCPFunction=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,Mcpc=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,McpcPCellNrFreqRelProfile=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?') and
                  re-match(current(), concat('ManagedElement=', ../../../../../me3gpp:id, ',.*')) and
                  re-match(current(), concat('.*GNBCUCPFunction=', ../../../../gnbcucp3gpp:id, ',.*')) and
                  count(../../../../mcpc:Mcpc[re-match(current(), concat('.*Mcpc=', mcpc:id, ',.*'))]/mcpcpcellnrfreqrelprofile:McpcPCellNrFreqRelProfile[re-match(current(), concat('.*McpcPCellNrFreqRelProfile=', mcpcpcellnrfreqrelprofile:id))]) > 0" {
                error-message
                    "mcpcPCellNrFreqRelProfileRef must refer to an McpcPCellNrFreqRelProfile under the same GNBCUCPFunction.";
            }
            yexte:dependencies
                "Referenced McpcPCellNrFreqRelProfile must be under Mcpc MO under "+
                "same GNBCUCPFunction as NRCellCU.";
            yexte:takes-effect
                "Next usage";
            tailf:info 'Takes effect: Next usage, Dependencies: Referenced McpcPCellNrFreqRelProfile must be under Mcpc MO under same GNBCUCPFunction as NRCellCU, Reference to instance of McpcPCellNrFreqRelProfile MO. If non-empty, attributes from referenced MO instance are used. If empty, attribute default values according to MO class definition are used.';
        }

        leaf mcpcPSCellNrFreqRelProfileRef {
            description
              "Reference to McpcPSCellNrFreqRelProfile MO instance.

              If non-empty, attributes from referenced MO instance are used.
              If empty, attribute default values according to "+
              "McpcPSCellNrFreqRelProfile and McpcPSCellNrFreqRelProfileUeCfg MO "+
              "class definitions are used.";
            type types3gpp:DistinguishedName;
            must "re-match(current(), 'ManagedElement=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,GNBCUCPFunction=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,Mcpc=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,McpcPSCellNrFreqRelProfile=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?') and
                  re-match(current(), concat('ManagedElement=', ../../../../../me3gpp:id, ',.*')) and
                  re-match(current(), concat('.*GNBCUCPFunction=', ../../../../gnbcucp3gpp:id, ',.*')) and
                  count(../../../../mcpc:Mcpc[re-match(current(), concat('.*Mcpc=', mcpc:id, ',.*'))]/mcpcpscellnrfreqrelprofile:McpcPSCellNrFreqRelProfile[re-match(current(), concat('.*McpcPSCellNrFreqRelProfile=', mcpcpscellnrfreqrelprofile:id))]) > 0" {
                error-message
                    "mcpcPSCellNrFreqRelProfileRef must refer to an McpcPSCellNrFreqRelProfile under the same GNBCUCPFunction.";
            }
            yexte:dependencies
              "Referenced McpcPSCellNrFreqRelProfile must be under Mcpc MO under "+
              "same GNBCUCPFunction as NRCellCU.";
            yexte:takes-effect
              "Next usage";
            tailf:info 'Takes effect: Next usage, Dependencies: Referenced McpcPSCellNrFreqRelProfile must be under Mcpc MO under same GNBCUCPFunction as NRCellCU, Reference to McpcPSCellNrFreqRelProfile MO instance. If non-empty, attributes from referenced MO instance are used. If empty, attribute default values according to McpcPSCellNrFreqRelProfile and McpcPSCellNrFreqRelProfileUeCfg MO class definitions are used.';
        }

        list plmnIdList {
            key "mcc mnc";
            max-elements 15;
            description
                "List of all PLMN IDs allowed for this frequency relation.

                Only applied if attribute plmnRestriction is true.

                UE that does not support any of the PLMN(s) according to UE Mobility "+
                "Restriction List is not allowed to use this frequency.
                Empty list means that no PLMN is allowed to use the frequency.

                PLMN ID consists of the following:
                - Mobile Country Code, 3 digits.
                - Mobile Network Code, 2 or 3 digits.";
            uses types3gpp:PLMNId;
            yexte:disturbances "Changing this attribute can cause loss of traffic.";
            yexte:takes-effect "New connection";
            tailf:info 'Takes effect: New connection, Traffic Disturbance: Changing this attribute can cause loss of traffic, List of all PLMN IDs allowed for this frequency relation. Only applied if attribute plmnRestriction is true. UE that does not support any of the PLMN(s) according to UE Mobility Restriction List is not allowed to use this frequency. Empty list means that no PLMN is allowed to use the frequency. PLMN ID consists of the following: - Mobile Country Code, 3 digits. - Mobile Network Code, 2 or 3 digits.';
        }

        leaf plmnRestriction {
            description
              "Whether PLMN restriction is defined for frequency relation.

               PLMN restriction is defined by attribute plmnIdList.";
            type boolean;
            default false;
            yexte:disturbances "Changing this attribute can cause loss of traffic.";
            yexte:takes-effect "New connection";
            tailf:info 'Takes effect: New connection, Traffic Disturbance: Changing this attribute can cause loss of traffic, Whether PLMN restriction is defined for frequency relation. PLMN restriction is defined by attribute plmnIdList.';
        }

        leaf sIntraSearchP {
            description
              "Srxlev threshold indicating when intra-frequency measurements are "
            + "required.";
            type int32 {
                range "0..62";
            }
            default 62;
            units dB;
            must ". mod 2 = 0" {
                error-message
                  "The value must set with resolution/step of 2";
            }
            reference
              "3GPP TS 38.304";
            yexte:takes-effect "Next cell unlock";
            tailf:info 'Takes effect: Next cell unlock, Srxlev threshold indicating when intra-frequency measurements are required.';
        }

        leaf sIntraSearchQ {
            description
              "Squal threshold indicating when intra-frequency measurements are "
            + "required.

               If empty, the value is not broadcast in SIB2.";
            type int32 {
                range "0..31";
            }
            units dB;
            reference
              "3GPP TS 38.304";
            yexte:takes-effect "Next cell unlock";
            tailf:info 'Takes effect: Next cell unlock, Squal threshold indicating when intra-frequency measurements are required. If empty, the value is not broadcast in SIB2.';
        }

        leaf trStSaNrFreqRelProfileRef {
            description
                "Reference to instance of TrStSaNrFreqRelProfile MO.

                If non-empty, attributes from referenced MO instance are used.
                If empty, attribute default values according to "+
                "TrStSaNrFreqRelProfile and TrStSaNrFreqRelProfileUeCfg MO class "+
                "definitions are used.";
            type types3gpp:DistinguishedName;
            must "re-match(current(), 'ManagedElement=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,GNBCUCPFunction=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,TrafficSteering=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,TrStSaNrFreqRelProfile=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?') and
                    re-match(current(), concat('ManagedElement=', ../../../../../me3gpp:id, ',.*')) and
                    re-match(current(), concat('.*GNBCUCPFunction=', ../../../../gnbcucp3gpp:id, ',.*')) and
                    count(../../../../trafficsteering:TrafficSteering[re-match(current(), concat('.*TrafficSteering=', trafficsteering:id, ',.*'))]/trstsanrfreqrelprofile:TrStSaNrFreqRelProfile[re-match(current(), concat('.*TrStSaNrFreqRelProfile=', trstsanrfreqrelprofile:id))]) > 0" {
                description
                    "The instance identifier must point at a TrStSaNrFreqRelProfile MO.

                    Example of a valid value is
                    ManagedElement=1,GNBCUCPFunction=1,"+
                    "TrafficSteering=1,TrStSaNrFreqRelProfile=Default";
                error-message
                    "trStSaNrFreqRelProfileRef must refer to an TrStSaNrFreqRelProfile under the same GNBCUCPFunction.";
            }
            yexte:dependencies
                "Referenced TrStSaNrFreqRelProfile must be under TrafficSteering MO "+
                "under same GNBCUCPFunction as NRCellCU.
                Only one NRFreqRelation MO instance under NRCellCU can refer to a "+
                "TrStSaNrFreqRelProfile with attribute "+
                "TrStSaNrFreqRelationUeCfg::pCellAllowed set to true.";
            yexte:takes-effect
                "Next usage";
            tailf:info 'Takes effect: Next usage, Dependencies: Referenced TrStSaNrFreqRelProfile must be under TrafficSteering MO under same GNBCUCPFunction as NRCellCU.
                Only one NRFreqRelation MO instance under NRCellCU can refer to a TrStSaNrFreqRelProfile with attribute TrStSaNrFreqRelationUeCfg::pCellAllowed set to true, Reference to instance of TrStSaNrFreqRelProfile MO. If non-empty, attributes from referenced MO instance are used. If empty, attribute default values according to TrStSaNrFreqRelProfile and TrStSaNrFreqRelProfileUeCfg MO class definitions are used.';
        }

        leaf ueMCNrFreqRelProfileRef {
            description
              "Reference to an instance of UeMCNrFreqRelProfile MO.

              If non-empty, attributes from referenced MO instance are used.
              If empty, attribute default values according to UeMCNrFreqRelProfile "+
              "and UeMCNrFreqRelProfileUeCfg MO class definitions are used.";
            type types3gpp:DistinguishedName;
            must "re-match(current(), 'ManagedElement=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,GNBCUCPFunction=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,UeMC=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,UeMCNrFreqRelProfile=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?') and
                    re-match(current(), concat('ManagedElement=', ../../../../../me3gpp:id, ',.*')) and
                    re-match(current(), concat('.*GNBCUCPFunction=', ../../../../gnbcucp3gpp:id, ',.*')) and
                    count(../../../../uemcvcucp:UeMC[re-match(current(), concat('.*UeMC=', uemcvcucp:id, ',.*'))]/uemcnrfreqrelprofilevcucp:UeMCNrFreqRelProfile[re-match(current(), concat('.*UeMCNrFreqRelProfile=', uemcnrfreqrelprofilevcucp:id))]) > 0" {
                error-message
                    "ueMCNrFreqRelProfileRef must refer to an UeMCNrFreqRelProfileRef under the same GNBCUCPFunction.";
            }
            yexte:dependencies
              "Referenced UeMCNrFreqRelProfile must be under UeMC MO under same "+
              "GNBCUCPFunction as NRCellCU.";
            yexte:takes-effect "Next usage.";
            tailf:info 'Takes effect: Next usage, Dependencies: Referenced UeMCNrFreqRelProfile must be under UeMC MO under same GNBCUCPFunction as NRCellCU, Reference to an instance of UeMCNrFreqRelProfile MO. If non-empty, attributes from referenced MO instance are used. If empty, attribute default values according to UeMCNrFreqRelProfile and UeMCNrFreqRelProfileUeCfg MO class definitions are used.';
        }
    }

    augment "/me3gpp:ManagedElement/gnbcucp3gpp:GNBCUCPFunction/nrcellcu3gpp:NRCellCU/nrfreqrel3gpp:NRFreqRelation/nrfreqrel3gpp:attributes" {
        description
          "Adds Ericsson attributes to 3gpp NRFreqRelation.";
        uses NRFreqRelationVCUCPGrp;
    }
}
