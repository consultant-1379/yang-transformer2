// Generated by eyang-preprocessor (1.22.0-48 2022-01-20 09:10:06 CET) on Jun 30, 2022, 8:31:44 AM
module ericsson-trstpscellprofileuecfg-vcucp {
    yang-version 1.1;
    namespace "urn:rdns:com:ericsson:oammodel:ericsson-trstpscellprofileuecfg-vcucp";
    prefix trstpscellprofileuecfg;

    import tailf-common {
        prefix tailf;
    }
    import _3gpp-common-managed-element {
        prefix "me3gpp";
    }
    import _3gpp-nr-nrm-gnbcucpfunction {
        prefix "gnbcucp3gpp";
    }
    import _3gpp-common-top {
        prefix "top3gpp";
    }
    import ericsson-yang-extensions {
        prefix "yexte";
    }
    import ericsson-common-types-vcucp {
        prefix "commontypes";
    }
    import ericsson-trafficsteering-vcucp {
        prefix "trafficsteering";
    }
    import ericsson-trstpscellprofile-vcucp {
        prefix "trstpscellprofile";
    }

    organization
      "Ericsson AB";
    contact
      "Ericsson first line support via email";
    description
      "The module defines the TrStPSCellProfileUeCfg data model for the Ericsson vCU-CP.

       Copyright (c) 2021-2022 Ericsson AB. All rights reserved.";

    revision 2022-06-28 {
        description
            "Removed module-status preliminary.";
        yexte:version 0;
        yexte:release 3;
        yexte:correction 0;
        reference
            "RFC 7950: The YANG 1.1 Data Modeling Language";
    }

    revision 2022-03-14 {
        description
            "Updated description of TrStPSCellProfileUeCfg.
             Added the userLabel attribute.";
        yexte:version 0;
        yexte:release 2;
        yexte:correction 0;
        reference
            "RFC 7950: The YANG 1.1 Data Modeling Language";
    }

    revision 2021-11-05 {
        description
          "Initial version of the TrStPSCellProfileUeCfg list.";
        yexte:version 0;
        yexte:release 1;
        yexte:correction 1;
        reference
          "RFC 7950: The YANG 1.1 Data Modeling Language";
    }

    revision 2021-09-16 {
        description
          "Initial version of the TrStPSCellProfileUeCfg model.";
        yexte:version 0;
        yexte:release 1;
        yexte:correction 0;
        reference
          "RFC 7950: The YANG 1.1 Data Modeling Language";
    }

    grouping TrStPSCellProfileUeCfgGrp {
        description
            "Represents the TrStPSCellProfileUeCfg IOC.";

        leaf hiPrioDetInactiveTime {
            description
                "Time period between periods of active measurements on higher "+
                "priority cells.";
            type int32 {
                range "500..300000";
            }
            default 30000;
            units ms;
            yexte:takes-effect
                "Next usage.";
            tailf:info 'Takes effect: Next usage, Time period between periods of active measurements on higher priority cells.';
        }

        leaf hiPrioDetMeasurementTime {
            description
              "Time period when measurements on higher priority cells are active.";
            type int32 {
                range "500..120000";
            }
            default 5000;
            units ms;
            yexte:takes-effect
                "Next usage.";
            tailf:info 'Takes effect: Next usage, Time period when measurements on higher priority cells are active.';
        }

        leaf hiPrioDetStartTime {
            description
                "Initial delay before starting A5 measurements for higher priority "+
                "cells.";
            type int32 {
                range "10..10000";
            }
            default 2000;
            units ms;
            yexte:takes-effect
                "Next usage.";
            tailf:info 'Takes effect: Next usage, Initial delay before starting A5 measurements for higher priority cells.';
        }

        container rsrpCandidateA5 {
            description
                "RSRP A5 measurement report criteria when searching for higher "+
                "priority PSCell candidate.";
            uses commontypes:ReportConfigA5NoThr1Rsrp;
            reference
                "3GPP TS 38.331";
            yexte:takes-effect
                "Next usage.";
            tailf:info 'Takes effect: Next usage, RSRP A5 measurement report criteria when searching for higher priority PSCell candidate.';
        }
    }

    augment "/me3gpp:ManagedElement/gnbcucp3gpp:GNBCUCPFunction/trafficsteering:TrafficSteering/trstpscellprofile:TrStPSCellProfile" {
        list TrStPSCellProfileUeCfg {
            description
                "Traffic steering function for PSCell in EN-DC, UE "+
                "configuration group.

                Applicable to UEs using this cell as PSCell in EN-DC. "+
                "Attributes are used on cell level.

                TrStPSCellProfileUeCfg=Base MO instance is created "+
                "automatically when parent MO is created, unless created "+
                "manually in the same transaction as parent MO.

                The RDN of this MO must always be TrStPSCellProfileUeCfg=Base.";
            key id;
            max-elements 1;
            uses top3gpp:Top_Grp {
                refine id {
                    must '. = "Base"' {
                        error-message
                            "The RDN of this MO must always be TrStPSCellProfileUeCfg=Base";
                    }
                }
            }
            container attributes {
                uses TrStPSCellProfileUeCfgGrp;
                uses commontypes:UserLabelGrp;
            }
            yexte:precondition
                "TrStPSCellProfileUeCfg=Base MO must not be deleted unless "+
                "parent MO is deleted.";
            tailf:info 'Precondition: TrStPSCellProfileUeCfg=Base MO must not be deleted unless parent MO is deleted, Traffic steering function for PSCell in EN-DC, UE configuration group. Applicable to UEs using this cell as PSCell in EN-DC. Attributes are used on cell level. TrStPSCellProfileUeCfg=Base MO instance is created automatically when parent MO is created, unless created manually in the same transaction as parent MO. The RDN of this MO must always be TrStPSCellProfileUeCfg=Base.';
        }
    }
}
