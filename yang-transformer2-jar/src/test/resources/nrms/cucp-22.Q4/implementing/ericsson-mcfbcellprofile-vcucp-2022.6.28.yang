// Generated by eyang-preprocessor (1.22.0-48 2022-01-20 09:10:06 CET) on Jun 30, 2022, 8:31:38 AM
module ericsson-mcfbcellprofile-vcucp {
    yang-version 1.1;
    namespace urn:rdns:com:ericsson:oammodel:ericsson-mcfbcellprofile-vcucp;
    prefix mcfbcellprofile;

    import tailf-common {
        prefix tailf;
    }
    import _3gpp-common-managed-element {
        prefix me3gpp;
    }
    import _3gpp-nr-nrm-gnbcucpfunction {
        prefix gnbcucp3gpp;
    }
    import _3gpp-common-top {
        prefix top3gpp;
    }
    import ericsson-mcfb-vcucp {
        prefix mcfb;
    }
    import ericsson-yang-extensions {
        prefix yexte;
    }
    import ericsson-common-types-vcucp {
        prefix commontypes;
    }

    organization
      "Ericsson AB";
    contact
      "Ericsson first line support via email";
    description
      "The module defines the McfbCellProfile data model for the Ericsson vCU-CP.

        Copyright (c) 2021-2022 Ericsson AB. All rights reserved.";

    revision 2022-06-28 {
        description
            "Removed module-status preliminary.
             Removed preliminary status from epsFbAtSessionSetup and ueConfGroupType.";
        yexte:version 1;
        yexte:release 1;
        yexte:correction 0;
        reference
            "RFC 7950: The YANG 1.1 Data Modeling Language";
    }

    revision 2022-03-14 {
        description
          "Updated description for the McfbCellProfile MO list.
           Marked epsFallbackOperation, epsFallbackOperationEm, epsFbTargetSearchTimer,
            rsrpCellCandidate, rsrpCriticalCoverage, rsrqCellCandidate, rsrqCriticalCoverage and
            triggerQuantity as obsolete.
           Added the attributes epsFbAtSessionSetup and ueConfGroupType.
           Moved groupings ReportConfigB1Rsrp and ReportConfigB1Rsrq to ericsson-common-types-vcucp.
           Moved enums EpsFallbackOperationType and EpsFbOperationTypeEm to ericsson-common-types-vcucp.";
        yexte:version 1;
        yexte:release 0;
        yexte:correction 0;
        reference
          "RFC 7950: The YANG 1.1 Data Modeling Language";
    }

    revision 2021-11-05 {
        description
          "Update McfbCellProfile description and precondition.";
        yexte:version 0;
        yexte:release 1;
        yexte:correction 1;
        reference
          "RFC 7950: The YANG 1.1 Data Modeling Language";
    }

    revision 2021-04-25 {
        description
          "Initial version of the McfbCellProfile model.";
        yexte:version 0;
        yexte:release 1;
        yexte:correction 0;
        reference
          "RFC 7950: The YANG 1.1 Data Modeling Language";
    }

    grouping ReportConfigB1RsrpObsolete {
        description
            "Report configuration settings for E-UTRA B1 measurement event when " +
            "trigger quantity is RSRP.";

        leaf hysteresis {
            description
                "Hysteresis value for eventB1.";
            type int32 {
                range "0..150";
            }
            units "0.1 dB";
            reference
                "3GPP TS 38.331";
            status obsolete {
                yexte:status-information
                    "Since 22.Q1. Replaced by McfbCellProfileUeCfg::rsrpCellCandidate::hysteresis. "+
                    "Planned to be removed.";
            }
            tailf:info 'Status Info: Since 22.Q1. Replaced by McfbCellProfileUeCfg::rsrpCellCandidate::hysteresis. Planned to be removed, Obsolete, Hysteresis value for eventB1.';
        }

        leaf threshold {
            description
                "RSRP threshold value for eventB1.";
            type int32 {
                range "-140..-44";
            }
            units dBm;
            reference
                "3GPP TS 36.331";
            status obsolete {
                yexte:status-information
                    "Since 22.Q1. Replaced by McfbCellProfileUeCfg::rsrpCellCandidate::threshold. "+
                    "Planned to be removed.";
            }
            tailf:info 'Status Info: Since 22.Q1. Replaced by McfbCellProfileUeCfg::rsrpCellCandidate::threshold. Planned to be removed, Obsolete, RSRP threshold value for eventB1.';
        }

        leaf timeToTrigger {
            description
                "Time-to-trigger value for eventB1 measurement.";
            type int32 {
                range "0|40|64|80|100|128|160|256|320|480|512|640|1024|1280|2560|5120";
            }
            units ms;
            reference
                "3GPP TS 38.331";
            status obsolete {
                yexte:status-information
                    "Since 22.Q1. Replaced by McfbCellProfileUeCfg::rsrpCellCandidate::timeToTrigger. "+
                    "Planned to be removed.";
            }
            tailf:info 'Status Info: Since 22.Q1. Replaced by McfbCellProfileUeCfg::rsrpCellCandidate::timeToTrigger. Planned to be removed, Obsolete, Time-to-trigger value for eventB1 measurement.';
        }
    }

    grouping ReportConfigA1A2RsrpObsolete {
        description
            "Report configuration settings for UE DL A1, A2, or both measurements with trigger quantity RSRP.";

        leaf hysteresis {
            description
                "Hysteresis value for RSRP in UE DL event A1, A2, or both measurements.";
            type int32 {
                range "0..150";
            }
            units "0.1 dB";
            reference
                "3GPP TS 38.331";
            status obsolete {
                yexte:status-information
                    "Since 22.Q1. Replaced by "+
                    "McfbCellProfileUeCfg::rsrpCriticalCoverage::hysteresis. Planned to be removed.";
            }
            tailf:info 'Status Info: Since 22.Q1. Replaced by McfbCellProfileUeCfg::rsrpCriticalCoverage::hysteresis. Planned to be removed, Obsolete, Hysteresis value for RSRP in UE DL event A1, A2, or both measurements.';
        }

        leaf threshold {
            description
                "RSRP threshold value for UE DL event A1, A2, or both measurements.";
            type int32 {
                range "-156..-29";
            }
            units dBm;
            reference
                "3GPP TS 38.331";
            status obsolete {
                yexte:status-information
                    "Since 22.Q1. Replaced by "+
                    "McfbCellProfileUeCfg::rsrpCriticalCoverage::threshold. Planned to be removed.";
            }
            tailf:info 'Status Info: Since 22.Q1. Replaced by McfbCellProfileUeCfg::rsrpCriticalCoverage::threshold. Planned to be removed, Obsolete, RSRP threshold value for UE DL event A1, A2, or both measurements.';
        }

        leaf timeToTrigger {
            description
                "Time-to-trigger value for RSRP in UE DL event A1, A2, or both measurements.";
            type int32 {
                range "0 | 40 | 64 | 80 | 100 | 128 | 160 | 256 | 320 | 480 | 512 | 640 | 1024 | 1280 | 2560 | 5120";
            }
            units ms;
            reference
                "3GPP TS 38.331";
            status obsolete {
                yexte:status-information
                    "Since 22.Q1. Replaced by "+
                    "McfbCellProfileUeCfg::rsrpCriticalCoverage::timeToTrigger. Planned to be removed.";
            }
            tailf:info 'Status Info: Since 22.Q1. Replaced by McfbCellProfileUeCfg::rsrpCriticalCoverage::timeToTrigger. Planned to be removed, Obsolete, Time-to-trigger value for RSRP in UE DL event A1, A2, or both measurements.';
        }

        leaf timeToTriggerA1 {
            description
                "Time-to-trigger value for event A1.

                 If set to -1, time-to-trigger value from struct member timeToTrigger is used.";
            type int32 {
                range "-1 | 0 | 40 | 64 | 80 | 100 | 128 | 160 | 256 | 320 | 480 | 512 | 640 | 1024 | 1280 | 2560 | 5120";
            }
            units ms;
            reference
                "3GPP TS 38.331";
            status obsolete {
                yexte:status-information
                    "Since 22.Q1. Replaced by "+
                    "McfbCellProfileUeCfg::rsrpCriticalCoverage::timeToTriggerA1. Planned to be removed.";
            }
            tailf:info 'Status Info: Since 22.Q1. Replaced by McfbCellProfileUeCfg::rsrpCriticalCoverage::timeToTriggerA1. Planned to be removed, Obsolete, Time-to-trigger value for event A1. If set to -1, time-to-trigger value from struct member timeToTrigger is used.';
        }
    }

    grouping ReportConfigB1RsrqObsolete {
        description
            "Report configuration settings for E-UTRA B1 measurement event when " +
            "trigger quantity is RSRQ.";

        leaf hysteresis {
            description
                "Hysteresis value for eventB1.";
            type int32 {
                range "0..150";
            }
            units "0.1 dB";
            reference
                "3GPP TS 38.331";
            status obsolete {
                yexte:status-information
                    "Since 22.Q1. Replaced by McfbCellProfileUeCfg::rsrqCellCandidate::hysteresis. "+
                    "Planned to be removed.";
            }
            tailf:info 'Status Info: Since 22.Q1. Replaced by McfbCellProfileUeCfg::rsrqCellCandidate::hysteresis. Planned to be removed, Obsolete, Hysteresis value for eventB1.';
        }

        leaf threshold {
            description
                "RSRQ threshold value for eventB1.";
            type int32 {
                range "-195..-30";
            }
            units "0.1 dB";
            reference
                "3GPP TS 36.331";
            status obsolete {
                yexte:status-information
                    "Since 22.Q1. Replaced by McfbCellProfileUeCfg::rsrqCellCandidate::threshold. "+
                    "Planned to be removed.";
            }
            tailf:info 'Status Info: Since 22.Q1. Replaced by McfbCellProfileUeCfg::rsrqCellCandidate::threshold. Planned to be removed, Obsolete, RSRQ threshold value for eventB1.';
        }

        leaf timeToTrigger {
            description
                "Time-to-trigger value for eventB1 measurement.";
            type int32 {
                range "0|40|64|80|100|128|160|256|320|480|512|640|1024|1280|2560|5120";
            }
            units ms;
            reference
                "3GPP TS 38.331";
            status obsolete {
                yexte:status-information
                    "Since 22.Q1. Replaced by McfbCellProfileUeCfg::rsrqCellCandidate::timeToTrigger. "+
                    "Planned to be removed.";
            }
            tailf:info 'Status Info: Since 22.Q1. Replaced by McfbCellProfileUeCfg::rsrqCellCandidate::timeToTrigger. Planned to be removed, Obsolete, Time-to-trigger value for eventB1 measurement.';
        }
    }

    grouping ReportConfigA1A2RsrqObsolete {
        description
            "Report configuration settings for A1 and A2 measurements when trigger quantity is RSRQ.";

        leaf hysteresis {
            description
                "Hysteresis value for RSRQ in event A1 and A2 measurements.";
            type int32 {
                range "0..150";
            }
            units "0.1 dB";
            reference
                "3GPP TS 38.331";
            status obsolete {
                yexte:status-information
                    "Since 22.Q1. Replaced by "+
                    "McfbCellProfileUeCfg::rsrqCriticalCoverage::hysteresis. Planned to be removed.";
            }
            tailf:info 'Status Info: Since 22.Q1. Replaced by McfbCellProfileUeCfg::rsrqCriticalCoverage::hysteresis. Planned to be removed, Obsolete, Hysteresis value for RSRQ in event A1 and A2 measurements.';
        }

        leaf threshold {
            description
                "RSRQ threshold value for event A1 and A2 measurements.";
            type int32 {
                range "-435..200";
            }
            units "0.1 dB";
            reference
                "3GPP TS 38.331";
            status obsolete {
                yexte:status-information
                    "Since 22.Q1. Replaced by "+
                    "McfbCellProfileUeCfg::rsrqCriticalCoverage::threshold. Planned to be removed.";
            }
            tailf:info 'Status Info: Since 22.Q1. Replaced by McfbCellProfileUeCfg::rsrqCriticalCoverage::threshold. Planned to be removed, Obsolete, RSRQ threshold value for event A1 and A2 measurements.';
        }

        leaf timeToTrigger {
            description
                "Time-to-trigger value for RSRQ in event A1 and A2 measurements.";
            type int32 {
                range "0 | 40 | 64 | 80 | 100 | 128 | 160 | 256 | 320 | 480 | 512 | 640 | 1024 | 1280 | 2560 | 5120";
            }
            units ms;
            reference
                "3GPP TS 38.331";
            status obsolete {
                yexte:status-information
                    "Since 22.Q1. Replaced by "+
                    "McfbCellProfileUeCfg::rsrqCriticalCoverage::timeToTrigger. Planned to be removed.";
            }
            tailf:info 'Status Info: Since 22.Q1. Replaced by McfbCellProfileUeCfg::rsrqCriticalCoverage::timeToTrigger. Planned to be removed, Obsolete, Time-to-trigger value for RSRQ in event A1 and A2 measurements.';
        }

        leaf timeToTriggerA1 {
            description
                "The time-to-trigger value for eventA1.

                 If set to -1, time-to-trigger value from struct member timeToTrigger is used.";
            type int32 {
                range "-1 | 0 | 40 | 64 | 80 | 100 | 128 | 160 | 256 | 320 | 480 | 512 | 640 | 1024 | 1280 | 2560 | 5120";
            }
            units ms;
            reference
                "3GPP TS 38.331";
            status obsolete {
                yexte:status-information
                    "Since 22.Q1. Replaced by "+
                    "McfbCellProfileUeCfg::rsrqCriticalCoverage::timeToTriggerA1. Planned to be removed.";
            }
            tailf:info 'Status Info: Since 22.Q1. Replaced by McfbCellProfileUeCfg::rsrqCriticalCoverage::timeToTriggerA1. Planned to be removed, Obsolete, The time-to-trigger value for eventA1. If set to -1, time-to-trigger value from struct member timeToTrigger is used.';
        }
    }

    typedef EpsFbAtSessionSetupType {
        description
            "EPS fallback operation can be done at session setup.";

        type enumeration {
            enum INACTIVE {
                value 0;
                description
                    "Always use Voice over NR (VoNR).";
            }

            enum ACTIVE {
                value 1;
                description
                    "For voice call at session setup, policy defined by "+
                    "epsFallbackOperation is used.

                     For emergency call at session setup, policy defined by "+
                    "epsFallbackOperationEm is used.
                     For EPS fallback, entire IMS PDU Session establishment is rejected.";
            }
        }
    }

    grouping McfbCellProfileGrp {
        description
          "Represents the McfbCellProfile IOC.";

        leaf epsFallbackOperation {
            description
              "Policy for EPS fallback or Voice over NR (VoNR) for voice calls.";
            type commontypes:EpsFallbackOperationType;
            status obsolete {
                yexte:status-information
                "Since 22.Q1. Replaced by "+
                "McfbCellProfileUeCfg::epsFallbackOperation. Planned to be removed.";
            }
            yexte:takes-effect
              "Next usage.";
            tailf:info 'Takes effect: Next usage, Status Info: Since 22.Q1. Replaced by McfbCellProfileUeCfg::epsFallbackOperation. Planned to be removed, Obsolete, Policy for EPS fallback or Voice over NR (VoNR) for voice calls.';
        }

        leaf epsFallbackOperationEm {
            description
              "Policy for EPS fallback or Voice over NR (VoNR) for emergency calls.";
            type commontypes:EpsFbOperationTypeEm;
            status obsolete {
                yexte:status-information
                "Since 22.Q1. Replaced by "+
                "McfbCellProfileUeCfg::epsFallbackOperationEm. Planned to be "+
                "removed.";
            }
            yexte:takes-effect
              "Next usage.";
            tailf:info 'Takes effect: Next usage, Status Info: Since 22.Q1. Replaced by McfbCellProfileUeCfg::epsFallbackOperationEm. Planned to be removed, Obsolete, Policy for EPS fallback or Voice over NR (VoNR) for emergency calls.';
        }

        leaf epsFbAtSessionSetup {
            description
              "Policy for voice and emergency call handling when voice flow is "+
              "included in PDU session setup.";
            type EpsFbAtSessionSetupType;
            default INACTIVE;
            yexte:disturbances
              "Changing this attribute can cause loss of traffic.";
            tailf:info 'Traffic Disturbance: Changing this attribute can cause loss of traffic, Policy for voice and emergency call handling when voice flow is included in PDU session setup.';
        }

        leaf epsFbTargetSearchTimer {
            description
              "Length of time the gNodeB waits for reports from B1 measurement for " +
              "EPS Fallback reasons.";
            type int32 {
                range "1..12000";
            }
            units ms;
            status obsolete {
                yexte:status-information
                "Since 22.Q1. Replaced by "+
                "McfbCellProfileUeCfg::epsFbTargetSearchTimer. Planned to be "+
                "removed.";
            }
            yexte:takes-effect
              "Next usage.";
            tailf:info 'Takes effect: Next usage, Status Info: Since 22.Q1. Replaced by McfbCellProfileUeCfg::epsFbTargetSearchTimer. Planned to be removed, Obsolete, Length of time the gNodeB waits for reports from B1 measurement for EPS Fallback reasons.';
        }

        leaf rejectVoiceIncHoAtEpsFb {
            description
              "Whether policy for EPS fallback is considered for rejecting incoming " +
              "handover with voice service.

               If true, handover preparation will fail if voice service is not " +
              "allowed when epsFallbackOperation is set to one of below values:
               - FORCED
               - FORCED_MEAS_RWR
               - FORCED_MEAS_IRAT_HO

               If false, voice service is always allowed at incoming handover " +
              "procedure.

               For initial call setup procedure, EPS fallback operation policy is " +
              "applied, rejectVoiceIncHoAtEpsFb has no impact.";
            type boolean;
            status obsolete {
                yexte:status-information
                "Since 22.Q1. Replaced by "+
                "McfbCellProfileUeCfg::rejectVoiceIncHoAtEpsFb. Planned to be "+
                "removed.";
            }
            yexte:takes-effect
              "New connection";
            tailf:info 'Takes effect: New connection, Status Info: Since 22.Q1. Replaced by McfbCellProfileUeCfg::rejectVoiceIncHoAtEpsFb. Planned to be removed, Obsolete, Whether policy for EPS fallback is considered for rejecting incoming handover with voice service. If true, handover preparation will fail if voice service is not allowed when epsFallbackOperation is set to one of below values: - FORCED - FORCED_MEAS_RWR - FORCED_MEAS_IRAT_HO If false, voice service is always allowed at incoming handover procedure. For initial call setup procedure, EPS fallback operation policy is applied, rejectVoiceIncHoAtEpsFb has no impact.';
        }

        container rsrpCellCandidate {
            description
              "RSRP B1 measurement report criteria when searching for E-UTRAN cell " +
              "candidate.";
            uses ReportConfigB1RsrpObsolete {
                status obsolete;
            }
            status obsolete {
                yexte:status-information
                "Since 22.Q1. Replaced by McfbCellProfileUeCfg::rsrpCellCandidate. "+
                "Planned to be removed.";
            }
            yexte:takes-effect
              "Next usage.";
            tailf:info 'Takes effect: Next usage, Status Info: Since 22.Q1. Replaced by McfbCellProfileUeCfg::rsrpCellCandidate. Planned to be removed, Obsolete, RSRP B1 measurement report criteria when searching for E-UTRAN cell candidate.';
        }

        container rsrpCriticalCoverage {
            description
              "RSRP A2 measurement report criteria for detecting critical coverage.";
            uses ReportConfigA1A2RsrpObsolete {
                status obsolete;
            }
            status obsolete {
                yexte:status-information
                "Since 22.Q1. Replaced by "+
                "McfbCellProfileUeCfg::rsrpCriticalCoverage. Planned to be removed.";
            }
            yexte:takes-effect
              "Next usage.";
            tailf:info 'Takes effect: Next usage, Status Info: Since 22.Q1. Replaced by McfbCellProfileUeCfg::rsrpCriticalCoverage. Planned to be removed, Obsolete, RSRP A2 measurement report criteria for detecting critical coverage.';
        }

        container rsrqCellCandidate {
            description
              "RSRQ B1 measurement report criteria when searching for E-UTRAN cell " +
              "candidate.";
            uses ReportConfigB1RsrqObsolete {
                status obsolete;
            }
            status obsolete {
                yexte:status-information
                "Since 22.Q1. Replaced by McfbCellProfileUeCfg::rsrqCellCandidate. "+
                "Planned to be removed.";
            }
            yexte:takes-effect
              "Next usage.";
            tailf:info 'Takes effect: Next usage, Status Info: Since 22.Q1. Replaced by McfbCellProfileUeCfg::rsrqCellCandidate. Planned to be removed, Obsolete, RSRQ B1 measurement report criteria when searching for E-UTRAN cell candidate.';
        }

        container rsrqCriticalCoverage {
            description
              "RSRQ A2 measurement report criteria for detecting critical coverage.";
            uses ReportConfigA1A2RsrqObsolete {
                status obsolete;
            }
            status obsolete {
                yexte:status-information
                "Since 22.Q1. Replaced by "+
                "McfbCellProfileUeCfg::rsrqCriticalCoverage. Planned to be removed.";
            }
            yexte:takes-effect
              "Next usage.";
            tailf:info 'Takes effect: Next usage, Status Info: Since 22.Q1. Replaced by McfbCellProfileUeCfg::rsrqCriticalCoverage. Planned to be removed, Obsolete, RSRQ A2 measurement report criteria for detecting critical coverage.';
        }

        leaf triggerQuantity {
            description
              "Quantity that triggers the event B1 and A2.";
            type commontypes:TriggerQuantity;
            status obsolete {
                yexte:status-information
                "Since 22.Q1. Replaced by McfbCellProfileUeCfg::triggerQuantity. "+
                "Planned to be removed.";
            }
            yexte:takes-effect
              "Next usage.";
            tailf:info 'Takes effect: Next usage, Status Info: Since 22.Q1. Replaced by McfbCellProfileUeCfg::triggerQuantity. Planned to be removed, Obsolete, Quantity that triggers the event B1 and A2.';
        }

        leaf ueConfGroupType {
            description
              "UE configuration Group Type.

              Defines which UE configuration group type that is applied in the "+
              "contained MO class McfbCellProfileUeCfg.";
            type commontypes:UeConfGroupType;
            default UE_MOBILITY_GROUP;
            yexte:disturbances
              "Changing this attribute can cause loss of traffic.";
            yexte:takes-effect
              "Next usage.";
            tailf:info 'Takes effect: Next usage, Traffic Disturbance: Changing this attribute can cause loss of traffic, UE configuration Group Type. Defines which UE configuration group type that is applied in the contained MO class McfbCellProfileUeCfg.';
        }
    }

    augment "/me3gpp:ManagedElement/gnbcucp3gpp:GNBCUCPFunction/mcfb:Mcfb" {

        list McfbCellProfile {
            description
              "Profile of mobility control fallback for cell.

              Applies to UEs which use the cell as PCell. Attributes are used "+
              "on cell level.

              MO instance McfbCellProfile=Default is created automatically "+
              "when parent MO is created, unless created manually in the same "+
              "transaction as parent MO.

              If NRCellCU::McfbCellProfileRef is non-empty, attributes from "+
              "referred MO instance are used.
              If NRCellCU::McfbCellProfileRef is empty, attribute default "+
              "values according to McfbCellProfile and McfbCellProfileUeCfg MO "+
              "class definitions are used.";
            yexte:precondition
              "McfbCellProfile=Default MO instance can only be created in same "+
              "transaction as parent MO and must not be deleted unless parent MO "+
              "is deleted.";
            key id;
            uses top3gpp:Top_Grp;
            container attributes {
                uses McfbCellProfileGrp;
            }
            tailf:info 'Precondition: McfbCellProfile=Default MO instance can only be created in same transaction as parent MO and must not be deleted unless parent MO is deleted, Profile of mobility control fallback for cell. Applies to UEs which use the cell as PCell. Attributes are used on cell level. MO instance McfbCellProfile=Default is created automatically when parent MO is created, unless created manually in the same transaction as parent MO. If NRCellCU::McfbCellProfileRef is non-empty, attributes from referred MO instance are used. If NRCellCU::McfbCellProfileRef is empty, attribute default values according to McfbCellProfile and McfbCellProfileUeCfg MO class definitions are used.';
        }
    }
}
