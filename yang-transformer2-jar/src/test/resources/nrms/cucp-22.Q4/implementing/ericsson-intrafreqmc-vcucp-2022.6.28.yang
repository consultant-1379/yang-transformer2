// Generated by eyang-preprocessor (1.22.0-48 2022-01-20 09:10:06 CET) on Jun 30, 2022, 8:31:38 AM
module ericsson-intrafreqmc-vcucp {
    yang-version 1.1;
    namespace "urn:rdns:com:ericsson:oammodel:ericsson-intrafreqmc-vcucp";
    prefix "intrafreqmc";

    import tailf-common {
        prefix tailf;
    }
    import _3gpp-common-managed-element {
        prefix "me3gpp";
    }
    import _3gpp-nr-nrm-gnbcucpfunction {
        prefix "gnbcucp3gpp";
    }
    import _3gpp-common-top {
        prefix "top3gpp";
    }
    import ericsson-yang-extensions {
        prefix "yexte";
    }

    organization
      "Ericsson AB";
    contact
      "Ericsson first line support via email";
    description
      "The module defines the IntraFreqMC data model for the Ericsson vCU-CP.

       Copyright (c) 2021-2022 Ericsson AB. All rights reserved.";

    revision 2022-06-28 {
        description
            "Removed module-status preliminary.";
        yexte:version 1;
        yexte:release 1;
        yexte:correction 0;
        reference
            "RFC 7950: The YANG 1.1 Data Modeling Language";
    }

    revision 2022-03-14 {
        description
            "Update description for IntraFreqMC.";
        yexte:version 1;
        yexte:release 0;
        yexte:correction 1;
        reference
            "RFC 7950: The YANG 1.1 Data Modeling Language";
    }

    revision 2021-11-17 {
        description
            "Updated description and precondition for the IntraFreqMC MO list.
            Marked intraFreqMCCellProfileUsage as obsolete.";
        yexte:version 1;
        yexte:release 0;
        yexte:correction 0;
        reference
            "RFC 7950: The YANG 1.1 Data Modeling Language";
    }

    revision 2021-06-08 {
        description
            "Changed error message for a must statement.";
        yexte:version 0;
        yexte:release 1;
        yexte:correction 1;
        reference
            "RFC 7950: The YANG 1.1 Data Modeling Language";
    }

    revision 2021-04-12 {
        description
          "Initial version of the IntraFreqMC model.";
        yexte:version 0;
        yexte:release 1;
        yexte:correction 0;
        reference
          "RFC 7950: The YANG 1.1 Data Modeling Language";
    }

    typedef IntraFreqMCCellProfileUsage {
        description
          "IntraFreqMCCellProfile MO class usage in relation to the deprecated MO class ReportConfigA3.";
        type enumeration {
            enum LIMITED_USAGE {
                value 0;
                description
                  "Limited usage of IntraFreqMCCellProfile MO class.

                   Following attributes are not used:
                   - rsrpBetterSpCell
                   - rsrqBetterSpCell
                   - betterSpCellTriggerQuantity
                   - endcActionEvalFail
                   Instead attributes from deprecated MO class ReportConfigA3 are used.";
            }
            enum COMPLETE_USAGE {
                value 1;
                description
                  "Complete usage of IntraFreqMCCellProfile MO class.

                   Deprecated MO class ReportConfigA3 is not used.";
            }
        }
    }

    grouping IntraFreqMCGrp {
        description
          "Represents the IntraFreqMC IOC.";

        leaf intraFreqMCCellProfileUsage {
            description
              "IntraFreqMCCellProfile MO class usage in relation to the deprecated MO class ReportConfigA3.";
            type IntraFreqMCCellProfileUsage;
            status obsolete {
                yexte:status-information
                    "Since 21.Q4. IntraFreqMCCellProfile MO class is now always used.";
            }
            tailf:info 'Status Info: Since 21.Q4. IntraFreqMCCellProfile MO class is now always used, Obsolete, IntraFreqMCCellProfile MO class usage in relation to the deprecated MO class ReportConfigA3.';
        }
    }

    augment "/me3gpp:ManagedElement/gnbcucp3gpp:GNBCUCPFunction" {
        list IntraFreqMC {
            description
                "This is a container for Intra-frequency mobility control profiles.

                MO instance IntraFreqMC=1 is created automatically when parent MO "+
                "is created, unless created manually in the same transaction as parent "+
                "MO.

                The RDN of this MO must always be IntraFreqMC=1.";
            key id;
            max-elements 1;
            uses top3gpp:Top_Grp {
                refine id {
                    must '. = "1"' {
                        error-message
                          "The RDN of this MO must always be IntraFreqMC=1";
                    }
                }
            }
            container attributes {
                uses IntraFreqMCGrp;
            }
            yexte:precondition
                "IntraFreqMC=1 MO instance must not be deleted unless parent MO is deleted.";
            tailf:info 'Precondition: IntraFreqMC=1 MO instance must not be deleted unless parent MO is deleted, This is a container for Intra-frequency mobility control profiles. MO instance IntraFreqMC=1 is created automatically when parent MO is created, unless created manually in the same transaction as parent MO. The RDN of this MO must always be IntraFreqMC=1.';
        }
    }
}
