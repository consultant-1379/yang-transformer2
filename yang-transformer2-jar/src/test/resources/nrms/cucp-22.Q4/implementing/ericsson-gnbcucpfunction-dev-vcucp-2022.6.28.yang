// Generated by eyang-preprocessor (1.22.0-48 2022-01-20 09:10:06 CET) on Jun 30, 2022, 8:31:38 AM
module ericsson-gnbcucpfunction-dev-vcucp {
    yang-version 1.1;
    namespace urn:rdns:com:ericsson:oammodel:ericsson-gnbcucpfunction-dev-vcucp;
    prefix gnbcucp3gppdev;

    import _3gpp-common-managed-element {
        prefix me3gpp;
    }
    import _3gpp-nr-nrm-gnbcucpfunction {
        prefix gnbcucp3gpp;
    }
    import ericsson-yang-extensions {
        prefix yexte;
    }

    organization
        "Ericsson AB";
    contact
        "Ericsson first line support via email";
    description
        "The module defines the GNBCUCPFunction data model deviations for the Ericsson vCU-CP.

        Copyright (c) 2020-2022 Ericsson AB. All rights reserved.";

    revision 2022-06-28 {
        description
            "Removed module-status preliminary.";
        yexte:version 0;
        yexte:release 2;
        yexte:correction 0;
        reference
            "RFC 7950: The YANG 1.1 Data Modeling Language";
    }

    revision 2020-11-18 {
        description
            "Deviations on _3gpp-nr-nrm-gnbcucpfunction.";
        yexte:version 0;
        yexte:release 1;
        yexte:correction 0;
        reference
            "RFC 7950: The YANG 1.1 Data Modeling Language";
    }

    deviation /me3gpp:ManagedElement/gnbcucp3gpp:GNBCUCPFunction/gnbcucp3gpp:ManagedNFService {
        description
        "Managed Network Function Service is not supported for GNBCUCPFunction.";
        deviate not-supported;
    }

    deviation /me3gpp:ManagedElement/gnbcucp3gpp:GNBCUCPFunction/gnbcucp3gpp:PerfMetricJob {
        description
        "Performance Metric Job is not supported for GNBCUCPFunction.";
        deviate not-supported;
    }

    deviation /me3gpp:ManagedElement/gnbcucp3gpp:GNBCUCPFunction/gnbcucp3gpp:ThresholdMonitor {
        description
        "Threshold Monitor is not supported for GNBCUCPFunction.";
        deviate not-supported;
    }

    deviation /me3gpp:ManagedElement/gnbcucp3gpp:GNBCUCPFunction/gnbcucp3gpp:TraceJob {
        description
        "Trace Job is not supported for GNBCUCPFunction.";
        deviate not-supported;
    }

    deviation /me3gpp:ManagedElement/gnbcucp3gpp:GNBCUCPFunction/gnbcucp3gpp:attributes/gnbcucp3gpp:SupportedPerfMetricGroup {
        description
        "Supported Performance Metrics is not supported for GNBCUCPFunction.";
        deviate not-supported;
    }

    deviation /me3gpp:ManagedElement/gnbcucp3gpp:GNBCUCPFunction/gnbcucp3gpp:attributes/gnbcucp3gpp:vnfParametersList {
        description
        "GNBCUCPFunction::vnfParametersList is not supported.";
        deviate not-supported;
    }

    deviation /me3gpp:ManagedElement/gnbcucp3gpp:GNBCUCPFunction/gnbcucp3gpp:attributes/gnbcucp3gpp:peeParametersList {
        description
        "GNBCUCPFunction::peeParametersList is not supported.";
        deviate not-supported;
    }

    deviation /me3gpp:ManagedElement/gnbcucp3gpp:GNBCUCPFunction/gnbcucp3gpp:attributes/gnbcucp3gpp:priorityLabel {
        description
        "GNBCUCPFunction::priorityLabel is not supported.";
        deviate not-supported;
    }

    deviation /me3gpp:ManagedElement/gnbcucp3gpp:GNBCUCPFunction/gnbcucp3gpp:attributes/gnbcucp3gpp:resourceType {
        description
        "GNBCUCPFunction::resourceType is not supported.";
        deviate not-supported;
    }

    deviation /me3gpp:ManagedElement/gnbcucp3gpp:GNBCUCPFunction/gnbcucp3gpp:attributes/gnbcucp3gpp:rRMPolicyMemberList {
        description
        "GNBCUCPFunction::rRMPolicyMemberList is not supported.";
        deviate not-supported;
    }

    deviation /me3gpp:ManagedElement/gnbcucp3gpp:GNBCUCPFunction/gnbcucp3gpp:attributes/gnbcucp3gpp:x2BlackList {
        description
        "GNBCUCPFunction::x2BlackList is not supported.";
        deviate not-supported;
    }

    deviation /me3gpp:ManagedElement/gnbcucp3gpp:GNBCUCPFunction/gnbcucp3gpp:attributes/gnbcucp3gpp:x2WhiteList {
        description
        "GNBCUCPFunction::x2WhiteList is not supported.";
        deviate not-supported;
    }

    deviation /me3gpp:ManagedElement/gnbcucp3gpp:GNBCUCPFunction/gnbcucp3gpp:attributes/gnbcucp3gpp:xnBlackList {
        description
        "GNBCUCPFunction::xnBlackList is not supported.";
        deviate not-supported;
    }

    deviation /me3gpp:ManagedElement/gnbcucp3gpp:GNBCUCPFunction/gnbcucp3gpp:attributes/gnbcucp3gpp:xnWhiteList {
        description
        "GNBCUCPFunction::xnWhiteList is not supported.";
        deviate not-supported;
    }

    deviation /me3gpp:ManagedElement/gnbcucp3gpp:GNBCUCPFunction/gnbcucp3gpp:attributes/gnbcucp3gpp:xnHOBlackList {
        description
        "GNBCUCPFunction::xnHOBlackList is not supported.";
        deviate not-supported;
    }

    deviation /me3gpp:ManagedElement/gnbcucp3gpp:GNBCUCPFunction/gnbcucp3gpp:attributes/gnbcucp3gpp:configurable5QISetRef {
        description
        "GNBCUCPFunction::configurable5QISetRef is not supported.";
        deviate not-supported;
    }

    deviation /me3gpp:ManagedElement/gnbcucp3gpp:GNBCUCPFunction/gnbcucp3gpp:attributes/gnbcucp3gpp:x2HOBlackList {
        description
        "GNBCUCPFunction::x2HOBlackList is not supported.";
        deviate not-supported;
    }

    deviation /me3gpp:ManagedElement/gnbcucp3gpp:GNBCUCPFunction/gnbcucp3gpp:attributes/gnbcucp3gpp:dynamic5QISetRef {
        description
        "GNBCUCPFunction::dynamic5QISetRef is not supported.";
        deviate not-supported;
    }
}
