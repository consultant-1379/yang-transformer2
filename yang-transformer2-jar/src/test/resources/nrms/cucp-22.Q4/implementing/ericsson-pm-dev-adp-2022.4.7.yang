// Generated by eyang-preprocessor (1.22.0-48 2022-01-20 09:10:06 CET) on Apr 8, 2022, 6:40:07 PM
module ericsson-pm-dev-adp {
    yang-version 1.1;
    namespace urn:rdns:com:ericsson:oammodel:ericsson-pm-dev-adp;
    prefix pmdevadp;
    import tailf-common {
        prefix tailf;
    }
    import ericsson-pm {
        prefix pme;
    }
    import ericsson-yang-extensions {
        prefix yexte;
    }
    organization 'Ericsson AB';
    contact 'Ericsson first line support via email';
    description "The module deviates ericsson-pm model.
    Copyright (c) 2021 Ericsson AB. All rights reserved.";
    revision 2022-04-07 {
        description 'Aligned to use ericsson-pm@2022-03-31.
      Remove threshold-high and threshold-low comparison check.';
        yexte:version 1;
        yexte:release 0;
        yexte:correction 3;
    }
    revision 2021-07-18 {
        description 'Added extra checks in measurement-job-checks and threshold-job-checks containers';
        yexte:version 1;
        yexte:release 0;
        yexte:correction 1;
    }
    revision 2021-07-07 {
        description 'Initial revision';
        yexte:version 1;
        yexte:release 0;
        yexte:correction 0;
    }
    deviation "/pme:pm/pme:job/pme:measurement-job-checks" {
        description "Added stricter GP-RP validation";
        deviate add {
            must "enum-value(../pme:reporting-period) >=
          enum-value(../pme:granularity-period) and
          (../../pme:measurement-capabilities/pme:measurement-jobs/
          pme:file-rp-supported = 'true' or
          (../pme:reporting-period = ../pme:granularity-period ))" {
                error-message "The value of granularity-period must be equal
          to the value of reporting-period if file-rp-supported in
          measurement-capabilities is 'false', or may be equal to a
          multiple of the value of reporting-period if
          file-rp-supported is set to 'true'.";
            }
        }
    }
    deviation "/pme:pm/pme:job/pme:measurement-reader/"
    + "pme:threshold-rate-of-variation" {
        description "Supports only 'per-gp' based threshold-rate-of-variation";
        deviate replace {
            default per-gp;
            config false;
        }
    }
    deviation "/pme:pm/pme:job/pme:measurement-reader/pme:target" {
        description "Supports only the first element of the target list.";
        deviate add {
            max-elements 1;
            yexte:updated-description "Selects resource instance(s)
      as the target of the measurement. If not set, the job is applied to all
      resource instances relevant to the selected group or measurement-type.
      If set, target is extracted based on configured pattern";
        }
    }
}
