// Generated by eyang-preprocessor (1.23.0-54 2022-02-22 23:30:06 CET) on Jun 17, 2022, 11:33:58 AM
module ericsson-cu-cp-rc-diagnostics-esi {
    yang-version 1.1;
    namespace urn:rdns:com:ericsson:oammodel:ericsson-cu-cp-rc-diagnostics-esi;
    prefix rcdiagesi;
    import ericsson-yang-extensions {
        prefix yexte;
    }
    import ericsson-common-types-diagnostics {
        prefix commontypesdiag;
    }
    import ericsson-cu-cp-rc-diagnostics {
        prefix rcdiag;
    }
    organization
      'Ericsson AB';
    contact
      'Ericsson first line support via email';
    description
      'Diagnostics action prepare esi for RC Service

       Copyright (c) 2022 Ericsson AB. All rights reserved';
    revision 2022-06-17 {
        description
        'Initial revision';
        yexte:version 1;
        yexte:release 0;
        yexte:correction 0;
    }

    yexte:module-status preliminary;

    augment "/rcdiag:rc-diagnostics" {
        uses commontypesdiag:esi;
    }
}
