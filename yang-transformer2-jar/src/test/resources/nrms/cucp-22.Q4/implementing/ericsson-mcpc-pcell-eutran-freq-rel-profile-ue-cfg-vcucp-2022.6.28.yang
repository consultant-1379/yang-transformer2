// Generated by eyang-preprocessor (1.22.0-48 2022-01-20 09:10:06 CET) on Jun 30, 2022, 8:31:39 AM
module ericsson-mcpc-pcell-eutran-freq-rel-profile-ue-cfg-vcucp {
    yang-version 1.1;
    namespace "urn:rdns:com:ericsson:oammodel:ericsson-mcpc-pcell-eutran-freq-rel-profile-ue-cfg-vcucp";
    prefix "mcpcpcelleutranfreqrelprofileuecfg";

    import tailf-common {
        prefix tailf;
    }
    import _3gpp-common-managed-element {
        prefix "me3gpp";
    }
    import _3gpp-nr-nrm-gnbcucpfunction {
        prefix "gnbcucp3gpp";
    }
    import _3gpp-common-top {
        prefix "top3gpp";
    }
    import ericsson-yang-extensions {
        prefix "yexte";
    }
    import ericsson-mcpc-vcucp {
        prefix "mcpc";
    }
    import ericsson-mcpc-pcell-eutran-freq-rel-profile-vcucp {
        prefix "mcpcpcelleutranfreqrelprofile";
    }
    import ericsson-common-types-vcucp {
        prefix "commontypes";
    }

    organization
        "Ericsson AB";
    contact
        "Ericsson first line support via email";
    description
        "The module defines the McpcPCellEUtranFreqRelProfileUeCfg data model for the Ericsson vCU-CP.

        Copyright (c) 2022 Ericsson AB. All rights reserved.";

    revision 2022-06-28 {
        description
            "Removed module-status preliminary.
             Removed preliminary status from McpcPCellEUtranFreqRelProfileUeCfg.";
        yexte:version 0;
        yexte:release 2;
        yexte:correction 0;
        reference
            "RFC 7950: The YANG 1.1 Data Modeling Language";
    }

    revision 2022-03-14 {
        description
            "Initial version of the McpcPCellEUtranFreqRelProfileUeCfg model";
        yexte:version 0;
        yexte:release 1;
        yexte:correction 0;
        reference
            "RFC 7950: The YANG 1.1 Data Modeling Language";
    }

    grouping ReportConfigB2RsrpOffsets {
        description
            "Threshold offsets for report configuration setting for B2 measurement event.

            Applied when trigger quantity is RSRP.";
        leaf threshold1Offset {
            description
                "RSRP threshold1 offset value for Event B2.";
            type int32 {
                range "-100..100";
            }
            units dB;
            default 0;
        }

        leaf threshold2EUtraOffset {
            description
                "RSRP threshold2 offset value for Event B2.";
            type int32 {
                range "-100..100";
            }
            units dB;
            default 0;
        }
    }

    grouping McpcPCellEUtranFreqRelProfileUeCfgGrp {
        description
            "Represents the McpcPCellEUtranFreqRelProfileUeCfg IOC.";
        leaf inhibitMeasForCellCandidate {
            description
                "Whether UE measurement searching for PCell candidate on this "+
                "frequency is inhibited.";
            type boolean;
            default false;
            yexte:takes-effect
                "Next usage";
            tailf:info 'Takes effect: Next usage, Whether UE measurement searching for PCell candidate on this frequency is inhibited.';
        }

        leaf-list prefUeGroupList {
            max-elements 8;
            ordered-by user;
            description
                "Preference UE group list.

                List of preference UE group identifiers.

                If empty, the MO instance matches preference UE group identifiers "+
                "not defined in prefUeGroupList of any other MO instances under "+
                "parent MO instance.";
            type int32 {
                range "1..255";
            }
            yexte:dependencies
                "Combinations of pair of preference UE group Identifier in "+
                "prefUeGroupList and UE group identifier in ueGroupList must be "+
                "unique among McpcPCellEUtranFreqRelProfileUeCfg instances under same "+
                "parent McpcPCellEUtranFreqRelProfile instance.

                For all preference UE group identifiers in prefUeGroupList "+
                "attributes under same parent McpcPCellEUtranFreqRelProfile MO "+
                "instance, exactly one McpcPCellEUtranFreqRelProfileUeCfg MO instance "+
                "must exist that combines the given preference UE group identifier "+
                "with an empty ueGroupList.";
            yexte:disturbances
                "Changing this attribute can cause loss of traffic.";
            yexte:takes-effect
                "Next usage.";
            must "count(../../../McpcPCellEUtranFreqRelProfileUeCfg/attributes[prefUeGroupList = current()
                    and count(ueGroupList) = 0] ) = 1" {
                error-message
                    "Exactly one McpcPCellEUtranFreqRelProfileUeCfg instance under an "+
                    "McpcPCellEUtranFreqRelProfile must combine a specific preference UE "+
                    "group identifier in attribute prefUeGroupList with an empty ueGroupList.";
            }
            tailf:info 'Takes effect: Next usage, Traffic Disturbance: Changing this attribute can cause loss of traffic, Dependencies: Combinations of pair of preference UE group Identifier in prefUeGroupList and UE group identifier in ueGroupList must be unique among McpcPCellEUtranFreqRelProfileUeCfg instances under same parent McpcPCellEUtranFreqRelProfile instance.

                For all preference UE group identifiers in prefUeGroupList attributes under same parent McpcPCellEUtranFreqRelProfile MO instance, exactly one McpcPCellEUtranFreqRelProfileUeCfg MO instance must exist that combines the given preference UE group identifier with an empty ueGroupList, Preference UE group list. List of preference UE group identifiers. If empty, the MO instance matches preference UE group identifiers not defined in prefUeGroupList of any other MO instances under parent MO instance.';
        }

        container rsrpCandidateB2Offsets {
            description
                "Downlink RSRP B2 measurement offsets when searching for PCell candidate.";
            uses ReportConfigB2RsrpOffsets;
            yexte:takes-effect
                "Next usage";
            tailf:info 'Takes effect: Next usage, Downlink RSRP B2 measurement offsets when searching for PCell candidate.';
        }

        leaf-list ueConfGroupList {
            max-elements 32;
            ordered-by user;
            description
                "UE configuration group list.

                List of UE configuration group identifiers.

                If empty, the MO instance matches all UE configuration group "+
                "identifiers.

                Which UE configuration group type that is applied is defined by "+
                "attribute ueConfGroupType in parent MO class instance.";
            type int32 {
                range "1..255";
            }
            yexte:dependencies
                "A given UE configuration group identifier can be defined in only one "+
                "ueConfGroupList among McpcPCellEUtranFreqRelProfileUeCfg instances "+
                "under same parent McpcPCellEUtranFreqRelProfile instance.";
            yexte:disturbances
                "Changing this attribute can cause loss of traffic.";
            yexte:takes-effect
                "Next usage.";
            must "count(../../../McpcPCellEUtranFreqRelProfileUeCfg/attributes[ueConfGroupList = current() ]) &lt;= 1" {
                error-message
                    "Only one McpcPCellEUtranFreqRelProfileUeCfg instance under an "+
                    "McpcPCellEUtranFreqRelProfile can include a specific UE configuration "+
                    "group identifier in attribute ueConfGroupList.";
            }
            tailf:info 'Takes effect: Next usage, Traffic Disturbance: Changing this attribute can cause loss of traffic, Dependencies: A given UE configuration group identifier can be defined in only one ueConfGroupList among McpcPCellEUtranFreqRelProfileUeCfg instances under same parent McpcPCellEUtranFreqRelProfile instance, UE configuration group list. List of UE configuration group identifiers. If empty, the MO instance matches all UE configuration group identifiers. Which UE configuration group type that is applied is defined by attribute ueConfGroupType in parent MO class instance.';
        }

        leaf-list ueGroupList {
            max-elements 16;
            ordered-by user;
            description
                "UE group list.

                List of UE group identifiers.

                If empty, the MO instance matches all UE group identifiers.";
            type int32 {
                range "1..255";
            }
            yexte:dependencies
                "Combinations of pair of preference UE group Identifier in "+
                "prefUeGroupList and UE group identifier in ueGroupList must be "+
                "unique among McpcPCellEUtranFreqRelProfileUeCfg instances under same "+
                "parent McpcPCellEUtranFreqRelProfile instance.

                Combination of a UE group identifier in UeGroupList and empty "+
                "prefUeGroupList must be unique among "+
                "McpcPCellEUtranFreqRelProfileUeCfg instances under same parent "+
                "McpcPCellEUtranFreqRelProfile instance.";
            yexte:disturbances
                "Changing this attribute can cause loss of traffic.";
            yexte:takes-effect
                "Next usage.";
            must "count(../prefUeGroupList) &gt; 0 or
                  count(../../../McpcPCellEUtranFreqRelProfileUeCfg/attributes[ueGroupList = current()
                    and count(prefUeGroupList) = 0] ) &lt;= 1" {
                error-message
                    "Only one McpcPCellEUtranFreqRelProfileUeCfg instance under an "+
                    "McpcPCellEUtranFreqRelProfile can combine a specific UE group "+
                    "identifier in attribute ueGroupList with an empty prefUeGroupList.";
            }
            tailf:info 'Takes effect: Next usage, Traffic Disturbance: Changing this attribute can cause loss of traffic, Dependencies: Combinations of pair of preference UE group Identifier in prefUeGroupList and UE group identifier in ueGroupList must be unique among McpcPCellEUtranFreqRelProfileUeCfg instances under same parent McpcPCellEUtranFreqRelProfile instance.

                Combination of a UE group identifier in UeGroupList and empty prefUeGroupList must be unique among McpcPCellEUtranFreqRelProfileUeCfg instances under same parent McpcPCellEUtranFreqRelProfile instance, UE group list. List of UE group identifiers. If empty, the MO instance matches all UE group identifiers.';
        }
    }

    augment "/me3gpp:ManagedElement/gnbcucp3gpp:GNBCUCPFunction/mcpc:Mcpc/mcpcpcelleutranfreqrelprofile:McpcPCellEUtranFreqRelProfile" {

        list McpcPCellEUtranFreqRelProfileUeCfg {
            description
                "Mobility control at poor coverage (MCPC) for PCell, UE "+
                "configuration group.

                Applies to UEs which use the cell as PCell. Attributes are "+
                "used on E-UTRAN frequency relation level.

                MO instance McpcPCellEUtranFreqRelProfileUeCfg=Base is created "+
                "automatically when parent MO is created, unless created "+
                "manually in the same transaction as parent MO.

                Attributes prefUeGroupList, ueGroupList and ueConfGroupList "+
                "must be empty in instance "+
                "McpcPCellEUtranFreqRelProfileUeCfg=Base but cannot all be "+
                "empty in other instances of McpcPCellEUtranFreqRelProfileUeCfg "+
                "under same parent McpcPCellEUtranFreqRelProfile.";
            yexte:precondition
                "McpcPCellEutranFreqRelProfileUeCfg=Base MO instance can only "+
                "be created in the same transaction as parent MO and must not be "+
                "deleted unless parent MO is deleted. Other instances can be "+
                "created and deleted manually.

                Maximum 31 McpcPCellEutranFreqRelProfileUeCfg instances, with "+
                "RDN different from Base, can be created.";
            key id;
            max-elements 32;
            uses top3gpp:Top_Grp;
            container attributes {
                uses McpcPCellEUtranFreqRelProfileUeCfgGrp;
                uses commontypes:UserLabelGrp;
            }
            must "count(../McpcPCellEUtranFreqRelProfileUeCfg) &lt; 32 or
                  count(../McpcPCellEUtranFreqRelProfileUeCfg/id[. = 'Base']) = 1" {
                error-message
                    "Maximum 31 McpcPCellEUtranFreqRelProfileUeCfg instances under an "+
                    "McpcPCellEUtranFreqRelProfile can be created with RDN different from Base.";
            }
            must "count(../McpcPCellEUtranFreqRelProfileUeCfg/attributes[prefUeGroupList = current()/attributes/prefUeGroupList
                  and ueGroupList = current()/attributes/ueGroupList] ) &lt;= 1" {
                error-message
                    "The combinations of a pair of UE group identifier in ueGroupList "+
                    "and preference UE group identifier in prefUeGroupList must be "+
                    "unique among McpcPCellEUtranFreqRelProfileUeCfg under an "+
                    "McpcPCellEUtranFreqRelProfile";
            }
            must "./id != 'Base'
                  or ( count(./attributes/ueConfGroupList) = 0
                       and count(./attributes/ueGroupList) = 0
                       and count(./attributes/prefUeGroupList) = 0 )" {
                error-message
                    "McpcPCellEUtranFreqRelProfileUeCfg::prefUeGroupList, ueGroupList and "+
                    "ueConfGroupList must be empty in the "+
                    "McpcPCellEUtranFreqRelProfileUeCfg=Base instance.";
            }
            must "./id = 'Base'
                  or not ( count(./attributes/ueConfGroupList) = 0
                           and count(./attributes/ueGroupList) = 0
                           and count(./attributes/prefUeGroupList) = 0 )" {
                error-message
                    "McpcPCellEUtranFreqRelProfileUeCfg::prefUeGroupList, ueGroupList and "+
                    "ueConfGroupList can only be empty in the "+
                    "McpcPCellEUtranFreqRelProfileUeCfg=Base instance";
            }
            tailf:info 'Precondition: McpcPCellEutranFreqRelProfileUeCfg=Base MO instance can only be created in the same transaction as parent MO and must not be deleted unless parent MO is deleted. Other instances can be created and deleted manually.

                Maximum 31 McpcPCellEutranFreqRelProfileUeCfg instances, with RDN different from Base, can be created, Mobility control at poor coverage (MCPC) for PCell, UE configuration group. Applies to UEs which use the cell as PCell. Attributes are used on E-UTRAN frequency relation level. MO instance McpcPCellEUtranFreqRelProfileUeCfg=Base is created automatically when parent MO is created, unless created manually in the same transaction as parent MO. Attributes prefUeGroupList, ueGroupList and ueConfGroupList must be empty in instance McpcPCellEUtranFreqRelProfileUeCfg=Base but cannot all be empty in other instances of McpcPCellEUtranFreqRelProfileUeCfg under same parent McpcPCellEUtranFreqRelProfile.';
        }
    }
}
