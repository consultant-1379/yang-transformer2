// Generated by eyang-preprocessor (1.22.0-48 2022-01-20 09:10:06 CET) on Sep 4, 2022, 12:23:55 PM
module ericsson-nrcellcu-ext-vcucp {
    yang-version 1.1;
    namespace urn:rdns:com:ericsson:oammodel:ericsson-nrcellcu-ext-vcucp;
    prefix nrcellcu3gppext;

    import tailf-common {
        prefix tailf;
    }
    import _3gpp-common-managed-element {
        prefix me3gpp;
    }
    import _3gpp-nr-nrm-gnbcucpfunction {
        prefix gnbcucp3gpp;
    }
    import _3gpp-nr-nrm-nrcellcu {
        prefix nrcellcu3gpp;
    }
    import _3gpp-common-yang-types {
        prefix types3gpp;
    }
    import ericsson-mcpc-vcucp {
        prefix mcpc;
    }
    import ericsson-mcpc-pscell-profile-vcucp {
        prefix mcpcpscellprofile;
    }
    import ericsson-mcpc-pcell-profile-vcucp {
        prefix mcpcpcellprofile;
    }
    import ericsson-nrcellcu-types-vcucp {
        prefix nrcellcutypes;
    }
    import ericsson-nrfrequency-vcucp {
        prefix nrfrequency;
    }
    import ericsson-nrnetwork-vcucp {
        prefix nrnetwork;
    }
    import ericsson-intrafreqmc-vcucp {
        prefix intrafreqmc;
    }
    import ericsson-intrafreqmccellprofile-vcucp {
        prefix intrafreqmccellprofile;
    }
    import ericsson-uemc-vcucp {
        prefix uemcvcucp;
    }
    import ericsson-uemccellprofile-vcucp {
        prefix uemccellprofile;
    }
    import ericsson-pmuemeas-vcucp {
        prefix pmuemeasvcucp;
    }
    import ericsson-pmueintrafreqcellprofile-vcucp {
        prefix pmueintrafreqcellprofilevcucp;
    }
    import ericsson-mcfb-vcucp {
        prefix mcfb;
    }
    import ericsson-mcfbcellprofile-vcucp {
        prefix mcfbcellprofile;
    }
    import ericsson-trafficsteering-vcucp {
        prefix trafficsteering;
    }
    import ericsson-trstpscellprofile-vcucp {
        prefix trstpscellprofile;
    }
    import ericsson-trstsacellprofile-vcucp {
        prefix trstsacellprofile;
    }
    import ericsson-nrdc-control-vcucp {
        prefix nrdccontrol;
    }
    import ericsson-nrdc-mn-cell-profile-vcucp {
        prefix nrdcmncellprofile;
    }
    import ericsson-yang-extensions {
        prefix yexte;
    }
    import ericsson-common-types-vcucp {
        prefix commontypes;
    }
    import ericsson-notifications {
        prefix notife;
    }

    organization
      "Ericsson AB";
    contact
      "Ericsson first line support via email";
    description
      "The module defines the NRCellCU data model extensions for the Ericsson vCU-CP.

       Copyright (c) 2021-2022 Ericsson AB. All rights reserved.";

    revision 2022-08-10 {
        description
            "Updated dependencies description for transmitSib2 and transmitSib4.";
        yexte:version 5;
        yexte:release 1;
        yexte:correction 1;
        reference
            "RFC 7950: The YANG 1.1 Data Modeling Language";
    }

    revision 2022-06-28 {
        description
            "Removed module-status preliminary.
             Removed preliminary status from lwNeighborRel, nrdcMnCellProfileRef
              and trStSaCellProfileRef.";
        yexte:version 5;
        yexte:release 1;
        yexte:correction 0;
        reference
            "RFC 7950: The YANG 1.1 Data Modeling Language";
    }

    revision 2022-03-14 {
        description
          "Add attribute nrdcMnCellProfileRef.
          Remove leftover 3gpp pLMNInfoList deviation.
          Updated dependencies for transmitSib2, and transmitSib5.
          Updated description and dependencies for transmitSib4.";
        yexte:version 5;
        yexte:release 0;
        yexte:correction 0;
        reference
          "RFC 7950: The YANG 1.1 Data Modeling Language";
    }

    revision 2021-11-26 {
        description
          "Replace pLMNInfoList type.";
        yexte:version 4;
        yexte:release 0;
        yexte:correction 0;
        reference
          "RFC 7950: The YANG 1.1 Data Modeling Language";
    }

    revision 2021-11-17 {
        description
          "Add trStSaCellProfileRef attribute.
          Remove endcDlNrRetProhibTimer and endcUlNrRetProhibTimer.
          Marked mcpcPCellEnabled as obsolete.
          Update takes effect for nRFrequencyRef.
          Update description and fix dependencies tag for multiple attributes.";
        yexte:version 3;
        yexte:release 0;
        yexte:correction 0;
        reference
          "RFC 7950: The YANG 1.1 Data Modeling Language";
    }

    revision 2021-09-16 {
        description
          "Add the trStPSCellProfileRef and hiPrioDetEnabled attributes.
           Update description for mcpcPSCellProfileRef.";
        yexte:version 2;
        yexte:release 3;
        yexte:correction 0;
        reference
          "RFC 7950: The YANG 1.1 Data Modeling Language";
    }

    revision 2021-06-09 {
        description
          "Remove an incorrect must statement from threshServingLowQ.
           Changed error messages for must statements.";
        yexte:version 2;
        yexte:release 2;
        yexte:correction 4;
        reference
          "RFC 7950: The YANG 1.1 Data Modeling Language";
    }

    revision 2021-06-08 {
        description
          "Remove max-elements from NRCellCU";
        yexte:version 2;
        yexte:release 2;
        yexte:correction 3;
        reference
          "RFC 7950: The YANG 1.1 Data Modeling Language";
    }

    revision 2021-06-03 {
        description
          "Disable notifications for lwNeighborRel.";
        yexte:version 2;
        yexte:release 2;
        yexte:correction 2;
        reference
          "RFC 7950: The YANG 1.1 Data Modeling Language";
    }

    revision 2021-05-28 {
        description
          "Remove duplicate config false from deviation of pLMNInfoList.";
        yexte:version 2;
        yexte:release 2;
        yexte:correction 1;
        reference
          "RFC 7950: The YANG 1.1 Data Modeling Language";
    }

    revision 2021-05-06 {
        description
          "Remove is-system-created and restricted extensions.
           Add config false to attribute pLMNInfoList.
           Remove attribute absFrameStartOffset and remove when statement from augment.";
        yexte:version 2;
        yexte:release 2;
        yexte:correction 0;
        reference
          "RFC 7950: The YANG 1.1 Data Modeling Language";
    }

    revision 2021-05-05 {
        description
            "Update must statements for mcpcPSCellProfileRef, mcpcPCellProfileRef,
             mcfbCellProfileRef and pmUeIntraFreqCellProfileRef.";
        yexte:version 2;
        yexte:release 1;
        yexte:correction 1;
        reference
            "RFC 7950: The YANG 1.1 Data Modeling Language";
    }

    revision 2021-04-29 {
        description
            "Add MOM attributes for ENDC leg switch.
            Update must statement for intraFreqMCCellRef and ueMCCellProfileRef.";
        yexte:version 2;
        yexte:release 1;
        yexte:correction 0;
        reference
            "RFC 7950: The YANG 1.1 Data Modeling Language";
    }

    revision 2021-03-31 {
        description
            "Add Ericsson descriptions and tags to attributes.";
        yexte:version 2;
        yexte:release 0;
        yexte:correction 2;
        reference
            "RFC 7950: The YANG 1.1 Data Modeling Language";
    }

    revision 2021-03-24 {
        description
            "Correct must statement for MO references.";
        yexte:version 2;
        yexte:release 0;
        yexte:correction 1;
        reference
            "RFC 7950: The YANG 1.1 Data Modeling Language";
    }

    revision 2021-03-10 {
        description
          "Parity with ECIM R1A79.";
        yexte:version 2;
        yexte:release 0;
        yexte:correction 0;
        reference
          "RFC 7950: The YANG 1.1 Data Modeling Language";
    }

    revision 2021-01-20 {
        description
          "Add extensions is-system-created and restricted.";
        yexte:version 1;
        yexte:release 0;
        yexte:correction 0;
        reference
          "RFC 7950: The YANG 1.1 Data Modeling Language";
    }

    revision 2021-01-11 {
        description
          "Add attributes on _3gpp-nr-nrm-nrcellcu";
        yexte:version 0;
        yexte:release 1;
        yexte:correction 0;
        reference
          "RFC 7950: The YANG 1.1 Data Modeling Language";
    }

    deviation /me3gpp:ManagedElement/gnbcucp3gpp:GNBCUCPFunction/nrcellcu3gpp:NRCellCU {
        deviate add {
            yexte:updated-description
              "Representation of an NR cell in gNodeB-CU.

              Manages inter-cell mobility and neighbor relations through the NR "+
              "Automated Neighbor Relations feature.

              This MO is created automatically. Can also be created and deleted "+
              "manually.

              Created automatically when a configuration message over F1 "+
              "interface is received.

              When created automatically, the RDN of this MO is NRCellCU=<NCI>, "+
              "where NCI = <gNBId>*2^(36-<gNBIdLength>) + <cellLocalId>.";
        }
    }

    deviation /me3gpp:ManagedElement/gnbcucp3gpp:GNBCUCPFunction/nrcellcu3gpp:NRCellCU/nrcellcu3gpp:attributes/nrcellcu3gpp:cellLocalId {
        deviate add {
            must 'count(../../../nrcellcu3gpp:NRCellCU/nrcellcu3gpp:attributes/nrcellcu3gpp:cellLocalId[current() = .]) = 1' {
                error-message
                  "All NRCellCUs under the same GNBCUCPFunction must have a unique cellLocalId.";
            }
            must '(../../../gnbcucp3gpp:attributes/gnbcucp3gpp:gNBIdLength = 32 and current() <= 15) or (../../../gnbcucp3gpp:attributes/gnbcucp3gpp:gNBIdLength = 31 and current() <= 31) or (../../../gnbcucp3gpp:attributes/gnbcucp3gpp:gNBIdLength = 30 and current() <= 63) or (../../../gnbcucp3gpp:attributes/gnbcucp3gpp:gNBIdLength = 29 and current() <= 127) or (../../../gnbcucp3gpp:attributes/gnbcucp3gpp:gNBIdLength = 28 and current() <= 255) or (../../../gnbcucp3gpp:attributes/gnbcucp3gpp:gNBIdLength = 27 and current() <= 511) or (../../../gnbcucp3gpp:attributes/gnbcucp3gpp:gNBIdLength = 26 and current() <= 1023) or (../../../gnbcucp3gpp:attributes/gnbcucp3gpp:gNBIdLength = 25 and current() <= 2047) or (../../../gnbcucp3gpp:attributes/gnbcucp3gpp:gNBIdLength = 24 and current() <= 4095) or (../../../gnbcucp3gpp:attributes/gnbcucp3gpp:gNBIdLength = 23 and current() <= 8191) or ../../../gnbcucp3gpp:attributes/gnbcucp3gpp:gNBIdLength = 22' {
                error-message
                  "cellLocalId must be equal or less than 2^(36-gNBIdLength) - 1.";
            }
            yexte:updated-description
              "Used together with gNodeB identifier to identify NR cell in PLMN.

              Used together with gNBId to form NCI.";
            yexte:dependencies
              "Must be unique among all NRCellCU MO instances within a "+
              "GNBCUCPFunction MO instance.

              cellLocalId < 2^(36 - GNBCUCPFunction::gNBIdLength)";
            yexte:takes-effect
              "Node restart";
        }
    }

    deviation /me3gpp:ManagedElement/gnbcucp3gpp:GNBCUCPFunction/nrcellcu3gpp:NRCellCU/nrcellcu3gpp:attributes/nrcellcu3gpp:nRFrequencyRef {
        deviate add {
            must "re-match(current(), 'ManagedElement=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,GNBCUCPFunction=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,NRNetwork=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,NRFrequency=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?') and
                  re-match(current(), concat('ManagedElement=', ../../../../me3gpp:id, ',.*')) and
                  re-match(current(), concat('.*GNBCUCPFunction=', ../../../gnbcucp3gpp:id, ',.*')) and
                  count(../../../nrnetwork:NRNetwork[re-match(current(), concat('.*NRNetwork=', nrnetwork:id, ',.*'))]/nrfrequency:NRFrequency[re-match(current(), concat('.*NRFrequency=', nrfrequency:id))]) > 0" {
                description
                  "The instance identifier must point at an NRFrequency entry.

                  Examples of valid value are
                  ManagedElement=1,GNBCUCPFunction=1,NRNetwork=1,NRFrequency=1";
                error-message
                  "nRFrquencyRef must refer to an NRFrequency under the same GNBCUCPFunction.";
            }
            yexte:updated-description
              "Reference to an instance of NRFrequency MO corresponding to cell SSB "+
              "configuration.";
            yexte:takes-effect
              "Next NRCellDU unlock";
        }
    }

    grouping NRCellCUVCUCPGrp {
        description
          "Ericsson extensions to the 3gpp NRCellCU.";
        reference
          "Ericsson documentation";

        leaf cellState {
            description
              "Current cellState.";
            config false;
            type nrcellcutypes:NRCellState;
            reference
              "3GPP TS 28.541";
        }

        leaf hiPrioDetEnabled {
            description
              "Whether traffic steering function PSCell change to higher priority "+
              "is enabled for NRCellCU.";
            type boolean;
            default false;
            yexte:takes-effect
              "New connection";
            tailf:info 'Takes effect: New connection, Whether traffic steering function PSCell change to higher priority is enabled for NRCellCU.';
        }

        leaf intraFreqMCCellProfileRef {
            description
              "Reference to instance of IntraFreqMCCellProfile MO.

              If non-empty, attributes from referenced MO instance are used.
              If empty, attribute default values according to MO class definition "+
              "are used.";
            type types3gpp:DistinguishedName;
            must "re-match(current(), 'ManagedElement=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,GNBCUCPFunction=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,IntraFreqMC=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,IntraFreqMCCellProfile=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?') and
                  re-match(current(), concat('ManagedElement=', ../../../../me3gpp:id, ',.*')) and
                  re-match(current(), concat('.*GNBCUCPFunction=', ../../../gnbcucp3gpp:id,',.*')) and
                  count( ../../../intrafreqmc:IntraFreqMC[re-match(current(), concat('.*IntraFreqMC=', intrafreqmc:id, ',.*'))]/intrafreqmccellprofile:IntraFreqMCCellProfile[re-match(current(), concat('.*IntraFreqMCCellProfile=', intrafreqmccellprofile:id))]) > 0" {
                description
                  "The instance identifier must point at a IntraFreqMCCellProfile entry.

                  Examples of valid value are
                  ManagedElement=1,GNBCUCPFunction=1,IntraFreqMC=1,IntraFreqMCCellProfile=1";
                error-message
                  "intraFreqMCCellProfileRef must refer to a IntraFreqMCCellProfile under the same GNBCUCPFunction.";
            }
            yexte:takes-effect
              "New connection";
            yexte:dependencies
              "Referenced IntraFreqMCCellProfile must be under IntraFreqMC MO under "+
              "same GNBCUCPFunction as NRCellCU.";
            tailf:info 'Dependencies: Referenced IntraFreqMCCellProfile must be under IntraFreqMC MO under same GNBCUCPFunction as NRCellCU, Takes effect: New connection, Reference to instance of IntraFreqMCCellProfile MO. If non-empty, attributes from referenced MO instance are used. If empty, attribute default values according to MO class definition are used.';
        }

        list lwNeighborRel {
            description
              "List of lightweight NR neighbor relations.
               These lightweight relations complement the set of relations "
            + "represented by NRCellRelation MO instances.";
            config false;
            uses nrcellcutypes:LwNeighborRelInfo;
            notife:notifiable-state-data false;
            tailf:meta-data notife:notifiable-state-data {
                tailf:meta-value false;
            }
        }

        leaf mcfbCellProfileRef {
            description
              "Reference to instance of McfbCellProfile MO.

              If non-empty, attributes from referenced MO instance are used.
              If empty, attribute default values according to MO class definition "+
              "are used.";
            type types3gpp:DistinguishedName;
            must "re-match(current(), 'ManagedElement=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,GNBCUCPFunction=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,Mcfb=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,McfbCellProfile=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?') and
                  re-match(current(), concat('ManagedElement=', ../../../../me3gpp:id, ',.*')) and
                  re-match(current(), concat('.*GNBCUCPFunction=', ../../../gnbcucp3gpp:id, ',.*')) and
                  count(../../../mcfb:Mcfb[re-match(current(), concat('.*Mcfb=', mcfb:id, ',.*'))]/mcfbcellprofile:McfbCellProfile[re-match(current(), concat('.*McfbCellProfile=', mcfbcellprofile:id))]) > 0" {
                description
                  "The instance identifier must point at a McfbCellProfile entry.

                  Examples of valid value are
                  ManagedElement=1,GNBCUCPFunction=1,Mcfb=1,McfbCellProfile=1";
                error-message
                  "mcfbCellProfileRef must refer to a McfbCellProfile under the same GNBCUCPFunction.";
            }
            yexte:dependencies
              "Referenced McfbCellProfile must be under Mcfb MO under the same "+
              "GNBCUCPFunction as NRCellCU.";
            yexte:takes-effect
              "Next usage.";
            tailf:info 'Takes effect: Next usage, Dependencies: Referenced McfbCellProfile must be under Mcfb MO under the same GNBCUCPFunction as NRCellCU, Reference to instance of McfbCellProfile MO. If non-empty, attributes from referenced MO instance are used. If empty, attribute default values according to MO class definition are used.';
        }

        leaf mcpcNrdcPSCellEnabled {
            description
              "Whether Mobility Control at Poor Coverage (MCPC) for PSCell in NR-DC "
            + "is enabled for NRCellCU.";
            type boolean;
            default false;
            status current {
                yexte:preliminary;
            }
            yexte:takes-effect
              "New connection";
            tailf:info 'Takes effect: New connection, Preliminary, Whether Mobility Control at Poor Coverage (MCPC) for PSCell in NR-DC is enabled for NRCellCU.';
        }

        leaf mcpcNrdcPSCellProfileRef {
            description
              "Reference to instance of McpcNrdcPSCellProfile MO.

              If non-empty, attributes from referenced MO instance are used.
              If empty, attribute default values from MO class definition are used.";
            type types3gpp:DistinguishedName;
            must "re-match(current(), 'ManagedElement=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,GNBCUCPFunction=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,Mcpc=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,McpcNrdcPSCellProfile=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?') and
                  re-match(current(), concat('ManagedElement=', ../../../../me3gpp:id, ',.*')) and
                  re-match(current(), concat('.*GNBCUCPFunction=', ../../../gnbcucp3gpp:id, ',.*'))" {
                // TODO: Add a count() to check that the referred MO actually exists when the MO class has been added to the external model.
                description
              "The instance identifier must point at a McpcNrdcPSCellProfile entry.

              Examples of valid value are
              ManagedElement=1,GNBCUCPFunction=1,Mcpc=1,McpcNrdcPSCellProfile=1";
                error-message
                  "mcpcNrdcPSCellProfileRef must refer to a McpcNrdcPSCellProfile under the same GNBCUCPFunction.";
            }
            yexte:dependencies
              "Referenced McpcNrdcPSCellProfile must be under Mcpc MO under same "+
              "GNBCUCPFunction as NRCellCU.";
            status current {
                yexte:preliminary;
            }
            yexte:takes-effect
              "Next usage.";
            tailf:info 'Takes effect: Next usage, Preliminary, Dependencies: Referenced McpcNrdcPSCellProfile must be under Mcpc MO under same GNBCUCPFunction as NRCellCU, Reference to instance of McpcNrdcPSCellProfile MO. If non-empty, attributes from referenced MO instance are used. If empty, attribute default values from MO class definition are used.';
        }

        leaf mcpcPCellEnabled {
            description
              "Whether Mobility Control at Poor Coverage (MCPC) for PCell is "
            + "enabled for NRCellCU.

               If set to false, function defined in ReportConfigA2 MO is applied.
               If set to true, function defined in ReportConfigA2 MO is turned off "
            + "and replaced by the enabled PCell MCPC functionality.";
            type boolean;
            status obsolete {
                yexte:status-information
                    "Since 21.Q4. MCPC PCell functionality is now always used.";
            }
            tailf:info 'Status Info: Since 21.Q4. MCPC PCell functionality is now always used, Obsolete, Whether Mobility Control at Poor Coverage (MCPC) for PCell is enabled for NRCellCU. If set to false, function defined in ReportConfigA2 MO is applied. If set to true, function defined in ReportConfigA2 MO is turned off and replaced by the enabled PCell MCPC functionality.';
        }

        leaf mcpcPCellProfileRef {
            description
              "Reference to instance of McpcPCellProfile MO.

              If non-empty, attributes from referenced MO instance are used.
              If empty, attribute default values according to MO class definition "+
              "are used.";
            type types3gpp:DistinguishedName;
            must "re-match(current(), 'ManagedElement=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,GNBCUCPFunction=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,Mcpc=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,McpcPCellProfile=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?') and
                  re-match(current(), concat('ManagedElement=', ../../../../me3gpp:id, ',.*')) and
                  re-match(current(), concat('.*GNBCUCPFunction=', ../../../gnbcucp3gpp:id, ',.*')) and
                  count(../../../mcpc:Mcpc[re-match(current(), concat('.*Mcpc=', mcpc:id, ',.*'))]/mcpcpcellprofile:McpcPCellProfile[re-match(current(), concat('.*McpcPCellProfile=', mcpcpcellprofile:id))]) > 0" {
                description
                  "The instance identifier must point at a McpcPCellProfile entry.

                  Examples of valid value are
                  ManagedElement=1,GNBCUCPFunction=1,Mcpc=1,McpcPCellProfile=1";
                error-message
                  "mcpcPCellProfileRef must refer to a McpcPCellProfile under the same GNBCUCPFunction.";
            }
            yexte:dependencies
              "Referenced McpcPCellProfile must be under Mcpc MO under same "+
              "GNBCUCPFunction as NRCellCU.";
            yexte:takes-effect
              "Next usage.";
            tailf:info 'Takes effect: Next usage, Dependencies: Referenced McpcPCellProfile must be under Mcpc MO under same GNBCUCPFunction as NRCellCU, Reference to instance of McpcPCellProfile MO. If non-empty, attributes from referenced MO instance are used. If empty, attribute default values according to MO class definition are used.';
        }

        leaf mcpcPSCellEnabled {
            description
              "Whether Mobility Control at Poor Coverage (MCPC) for PSCell is "
            + "enabled for NRCellCU.";
            type boolean;
            default false;
            yexte:takes-effect
              "Next usage.";
            tailf:info 'Takes effect: Next usage, Whether Mobility Control at Poor Coverage (MCPC) for PSCell is enabled for NRCellCU.';
        }

        leaf mcpcPSCellProfileRef {
            description
              "Reference to instance of McpcPSCellProfile MO.

              If non-empty, attributes from referenced MO instance are used.
              If empty, attribute default values according to McpcPSCellProfile "+
              "and McpcPSCellProfileUeCfg MO class definitions are used.

              Referenced McpcPSCellProfile must be under Mcpc MO under same "+
              "GNBCUCPFunction as NRCellCU.";
            type types3gpp:DistinguishedName;
            must "re-match(current(), 'ManagedElement=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,GNBCUCPFunction=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,Mcpc=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,McpcPSCellProfile=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?') and
                  re-match(current(), concat('ManagedElement=', ../../../../me3gpp:id, ',.*')) and
                  re-match(current(), concat('.*GNBCUCPFunction=', ../../../gnbcucp3gpp:id, ',.*')) and
                  count(../../../mcpc:Mcpc[re-match(current(), concat('.*Mcpc=', mcpc:id, ',.*'))]/mcpcpscellprofile:McpcPSCellProfile[re-match(current(), concat('.*McpcPSCellProfile=', mcpcpscellprofile:id))]) > 0" {
                error-message
                  "mcpcPSCellProfileRef must refer to a McpcPSCellProfile under the same GNBCUCPFunction.";
            }
            yexte:takes-effect
              "Next usage.";
            tailf:info 'Takes effect: Next usage, Reference to instance of McpcPSCellProfile MO. If non-empty, attributes from referenced MO instance are used. If empty, attribute default values according to McpcPSCellProfile and McpcPSCellProfileUeCfg MO class definitions are used. Referenced McpcPSCellProfile must be under Mcpc MO under same GNBCUCPFunction as NRCellCU.';
        }

        leaf nCellChangeHigh {
            description
              "Maximum number of cell reselections to enter high mobility state.

               If empty, no mobility state parameters will be broadcast in SIB2.";
            type uint32 {
                range "1..16";
            }
            reference
              "3GPP TS 38.331, 3GPP TS 38.304";
            yexte:takes-effect
              "New connection";
            tailf:info 'Takes effect: New connection, Maximum number of cell reselections to enter high mobility state. If empty, no mobility state parameters will be broadcast in SIB2.';
        }

        leaf nCellChangeMedium {
            description
              "Maximum number of cell reselections to enter medium mobility state.

               If empty, no mobility state parameters will be broadcast in SIB2.";
            type uint32 {
                range "1..16";
            }
            reference
              "3GPP TS 38.331, 3GPP TS 38.304";
            yexte:takes-effect
              "New connection";
            tailf:info 'Takes effect: New connection, Maximum number of cell reselections to enter medium mobility state. If empty, no mobility state parameters will be broadcast in SIB2.';
        }

        leaf nCI {
            description
              "NR Cell Identity.";
            config false;
            type int64 {
                range "0..68719476735";
            }
        }

        leaf nrdcMnCellProfileRef {
            description
                "Reference to an instance of NrdcMnCellProfile MO.

                If reference is non-empty, attributes from referred MO instance are "+
                "used.
                If reference is empty, attribute default values according to MO "+
                "class definition are used.";
            type types3gpp:DistinguishedName;
            must "re-match(current(), 'ManagedElement=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,GNBCUCPFunction=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,NrdcControl=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,NrdcMnCellProfile=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?') and
                  re-match(current(), concat('ManagedElement=', ../../../../me3gpp:id, ',.*')) and
                  re-match(current(), concat('.*GNBCUCPFunction=', ../../../gnbcucp3gpp:id, ',.*')) and
                  count(../../../nrdccontrol:NrdcControl[re-match(current(), concat('.*NrdcControl=', nrdccontrol:id, ',.*'))]/nrdcmncellprofile:NrdcMnCellProfile[re-match(current(), concat('.*NrdcMnCellProfile=', nrdcmncellprofile:id))]) > 0" {
                description
                    "The instance identifier must point at an NrdcMnCellProfile entry.

                    Examples of valid value are
                    ManagedElement1,GNBCUCPFunction=1,NrdcControl=1,NrdcMnCellProfile=1";
                error-message
                    "The instance identifier must point at an NrdcMnCellProfile MO "+
                    "entry.";
            }
            yexte:dependencies
                "Referenced NrdcMnCellProfile must be under NrdcControl MO under same "+
                "GNBCUCPFunction as NRCellCU.";
            yexte:takes-effect
                "New connection";
            tailf:info 'Takes effect: New connection, Dependencies: Referenced NrdcMnCellProfile must be under NrdcControl MO under same GNBCUCPFunction as NRCellCU, Reference to an instance of NrdcMnCellProfile MO. If reference is non-empty, attributes from referred MO instance are used. If reference is empty, attribute default values according to MO class definition are used.';
        }

        leaf nRTAC {
            description
              "NR Tracking Area Code (TAC).";
            config false;
            type int32;
            reference
              "3GPP TS 28.651";
        }

        leaf pmUeIntraFreqCellProfileRef {
            description
              "Reference to instance of PmUeIntraFreqCellProfile MO.

              If non-empty, attributes from referenced MO instance are used.
              If empty, attribute default values according to MO class definition "+
              "are used.";
            type types3gpp:DistinguishedName;
            must "re-match(current(), 'ManagedElement=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,GNBCUCPFunction=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,PmUeMeas=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,PmUeIntraFreqCellProfile=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?') and
                  re-match(current(), concat('ManagedElement=', ../../../../me3gpp:id, ',.*')) and
                  re-match(current(), concat('.*GNBCUCPFunction=', ../../../gnbcucp3gpp:id, ',.*')) and
                  count(../../../pmuemeasvcucp:PmUeMeas[re-match(current(), concat('.*PmUeMeas=', pmuemeasvcucp:id, ',.*'))]/pmueintrafreqcellprofilevcucp:PmUeIntraFreqCellProfile[re-match(current(), concat('.*PmUeIntraFreqCellProfile=', pmueintrafreqcellprofilevcucp:id))]) > 0" {
                description
                  "The instance identifier must point at a PmUeIntraFreqCellProfile "+
                  "entry.

                  Examples of valid value are
                  ManagedElement1,GNBCUCPFunction=1,PmUeMeas=1,PmUeIntraFreqCellProfile=1";
                error-message
                  "pmUeIntraFreqCellProfileRef must refer to a PmUeIntraFreqCellProfile under the same GNBCUCPFunction.";
            }
            yexte:dependencies
              "Referenced PmUeIntraFreqCellProfile must be under PmUeMeas MO under "+
              "same GNBCUCPFunction as NRCellCU.";
            yexte:takes-effect
              "Next usage.";
            tailf:info 'Takes effect: Next usage, Dependencies: Referenced PmUeIntraFreqCellProfile must be under PmUeMeas MO under same GNBCUCPFunction as NRCellCU, Reference to instance of PmUeIntraFreqCellProfile MO. If non-empty, attributes from referenced MO instance are used. If empty, attribute default values according to MO class definition are used.';
        }

        leaf pmUeIntraFreqEnabled {
            description
              "Whether PM intra-frequency UE Measurements are enabled for NR cell.";
            type boolean;
            default false;
            yexte:takes-effect
              "Next usage.";
            tailf:info 'Takes effect: Next usage, Whether PM intra-frequency UE Measurements are enabled for NR cell.';
        }

        list primaryPLMNId {
            key "mcc mnc";
            max-elements 1;
            description
              "PLMN ID for NR CGI.

               If empty, GNBCUCPFunction::pLMNId is used for PLMN ID in NR CGI.";
            uses types3gpp:PLMNId;
            yexte:takes-effect
              "Node restart";
            tailf:info 'Takes effect: Node restart, PLMN ID for NR CGI. If empty, GNBCUCPFunction::pLMNId is used for PLMN ID in NR CGI.';
        }

        leaf pSCellCapable {
            description
              "Whether cell is Primary Secondary Cell (PSCell) capable in EN-DC.

               If false, cell is not shared over X2AP.
               If empty, the value is unknown.";
            config false;
            type boolean;
        }

        leaf-list pwsEmergencyAreaIdList {
            max-elements 15;
            description
              "List of emergency areas that cell belongs to.

               A cell that supports broadcast of warning messages can belong to 1 to "
            + "15 emergency areas. Emergency area is identified by an Emergency "
            + "Area ID, set by the operator.";
            type int32 {
                range "0..16777215";
            }
            reference
              "3GPP TS 38.413";
            yexte:takes-effect
              "Next cell unlock";
            yexte:precondition
              "Value can only be changed when NRCellDU with matching cellLocalId "+
              "does not exist or has administrativeState LOCKED.";
            tailf:info 'Precondition: Value can only be changed when NRCellDU with matching cellLocalId does not exist or has administrativeState LOCKED, Takes effect: Next cell unlock, List of emergency areas that cell belongs to. A cell that supports broadcast of warning messages can belong to 1 to 15 emergency areas. Emergency area is identified by an Emergency Area ID, set by the operator.';
        }

        leaf qHyst {
            description
              "Hysteresis value for ranking criteria at cell reselection.";
            type int32 {
                range "0|1|2|3|4|5|6|8|10|12|14|16|18|20|22|24";
            }
            default 4;
            units dB;
            reference
              "3GPP TS 38.304";
            yexte:takes-effect
              "Next cell unlock";
            yexte:precondition
              "Value can only be changed when NRCellDU with matching cellLocalId "+
              "does not exist or has administrativeState LOCKED.";
            tailf:info 'Precondition: Value can only be changed when NRCellDU with matching cellLocalId does not exist or has administrativeState LOCKED, Takes effect: Next cell unlock, Hysteresis value for ranking criteria at cell reselection.';
        }

        leaf qHystSfHigh {
            description
              "Speed-dependent scaling factor for Qhyst parameter in sf-High for "
            + "high mobility state.

               If empty, no q-HystSF will be broadcast in SIB2.";
            type int32 {
                range "-6|-4|-2|0";
            }
            units dB;
            reference
              "3GPP TS 38.331, 3GPP TS 38.304";
            yexte:takes-effect
              "New connection";
            tailf:info 'Takes effect: New connection, Speed-dependent scaling factor for Qhyst parameter in sf-High for high mobility state. If empty, no q-HystSF will be broadcast in SIB2.';
        }

        leaf qHystSfMedium {
            description
              "Speed-dependent scaling factor for Qhyst parameter in sf-Medium for "
            + "medium mobility state.

               If empty, no q-HystSF will be broadcast in SIB2.";
            type int32 {
                range "-6|-4|-2|0";
            }
            units dB;
            reference
              "3GPP TS 38.331, 3GPP TS 38.304";
            yexte:takes-effect
              "New connection";
            tailf:info 'Takes effect: New connection, Speed-dependent scaling factor for Qhyst parameter in sf-Medium for medium mobility state. If empty, no q-HystSF will be broadcast in SIB2.';
        }

        leaf rrcReconfMsgSizeRed {
            description
              "Size reduction options in one single RRCReconfiguration message in "
            + "NR SA deployment.";
            type nrcellcutypes:MsgRedOptions;
            default HO_ESS_MSG_RED_LEVEL1;
            status current {
                yexte:preliminary;
            }
            yexte:takes-effect
              "New connection";
            tailf:info 'Takes effect: New connection, Preliminary, Size reduction options in one single RRCReconfiguration message in NR SA deployment.';
        }

        leaf serviceState {
            description
              "Current service state.";
            config false;
            type nrcellcutypes:NRCellServiceState;
            reference
              "3GPP TS 38.473";
        }

        leaf smtcDuration {
            description
              "Duration of SSB.

               Represents value received in RRC encoded "
            + "MeasurementTimingInformation (SMTC) information element at F1 Setup "
            + "or at GNB-DU Configuration Update.";
            config false;
            type int32 {
                range "1..5";
            }
            units ms;
            status current {
                yexte:preliminary;
            }
            reference
              "3GPP TS 38.331";
            tailf:info 'Preliminary, Duration of SSB. Represents value received in RRC encoded MeasurementTimingInformation (SMTC) information element at F1 Setup or at GNB-DU Configuration Update.';
        }

        leaf smtcOffset {
            description
              "Offset of SSB.

               Represents value received in RRC encoded "
            + "MeasurementTimingInformation (SMTC) information element at F1 Setup "
            + "or at GNB-DU Configuration Update.";
            config false;
            type int32 {
                range "0..159";
            }
            units ms;
            status current {
                yexte:preliminary;
            }
            reference
              "3GPP TS 38.331";
            tailf:info 'Preliminary, Offset of SSB. Represents value received in RRC encoded MeasurementTimingInformation (SMTC) information element at F1 Setup or at GNB-DU Configuration Update.';
        }

        leaf smtcPeriodicity {
            description
              "Periodicity of SSB.

               Represents value received in RRC encoded "
            + "MeasurementTimingInformation (SMTC) information element at F1 Setup "
            + "or at GNB-DU Configuration Update.";
            config false;
            type int32 {
                range "5|10|20|40|80|160";
            }
            units ms;
            status current {
                yexte:preliminary;
            }
            reference
              "3GPP TS 38.331";
            tailf:info 'Preliminary, Periodicity of SSB. Represents value received in RRC encoded MeasurementTimingInformation (SMTC) information element at F1 Setup or at GNB-DU Configuration Update.';
        }

        leaf sNonIntraSearchP {
            description
              "Threshold when inter-frequency and inter-RAT measurements are "
            + "required.

               If the attribute is set to empty, value is not broadcast in SIB2 and "
            + "the UE applies the default value of infinity for sNonIntraSearchP.";
            type int32 {
                range "0..62";
            }
            yexte:initial-value 0;
            units dB;
            must ". mod 2 = 0" {
                error-message
                  "The value must set with resolution/step of 2";
            }
            reference
              "3GPP TS 38.304";
            yexte:takes-effect
              "Next cell unlock";
            yexte:precondition
              "Value can only be changed when NRCellDU with matching cellLocalId "+
              "does not exist or has administrativeState LOCKED.";
            tailf:info 'Precondition: Value can only be changed when NRCellDU with matching cellLocalId does not exist or has administrativeState LOCKED, Takes effect: Next cell unlock, Threshold when inter-frequency and inter-RAT measurements are required. If the attribute is set to empty, value is not broadcast in SIB2 and the UE applies the default value of infinity for sNonIntraSearchP.';
        }

        leaf sNonIntraSearchQ {
            description
              "Threshold when inter-frequency and inter-RAT measurements are "
            + "required.

               If the attribute is set to empty, the value is not broadcast in SIB2, "
            + "and the UE applies the default value of 0 dB for sNonIntraSearch.";
            type int32 {
                range "0..31";
            }
            units dB;
            must "../threshServingLowQ" {
                error-message
                  "sNonIntraSearchQ must be empty if threshServingLowQ is empty.";
            }
            yexte:dependencies
              "Must be set to empty if threshServingLowQ is set to empty.";
            reference
              "3GPP TS 38.304";
            yexte:takes-effect
              "Next cell unlock";
            yexte:precondition
              "Value can only be changed when NRCellDU with matching cellLocalId "+
              "does not exist or has administrativeState LOCKED.";
            tailf:info 'Precondition: Value can only be changed when NRCellDU with matching cellLocalId does not exist or has administrativeState LOCKED, Takes effect: Next cell unlock, Dependencies: Must be set to empty if threshServingLowQ is set to empty, Threshold when inter-frequency and inter-RAT measurements are required. If the attribute is set to empty, the value is not broadcast in SIB2, and the UE applies the default value of 0 dB for sNonIntraSearch.';
        }

        list sNSSAIList {
            key "sd sst";
            max-elements 1024;
            description
              "List of supported network slices.

              If empty, cell can be used for all UEs regardless of their S-NSSAI.";
            config false;
            // TODO: Change to the types3gpp:SNssai once they have fixed that type in a newer
            // release. It is invalid in version 16.0.
            uses commontypes:SliceSelectionAssistInfo;
        }

        leaf tEvaluation {
            description
              "Duration for evaluating criteria to enter mobility states.

               If empty, no mobility state parameters will be broadcast in SIB2.";
            type uint32 {
                range "30|60|120|180|240";
            }
            units s;
            reference
              "3GPP TS 38.331, 3GPP TS 38.304";
            yexte:takes-effect
              "New connection";
            tailf:info 'Takes effect: New connection, Duration for evaluating criteria to enter mobility states. If empty, no mobility state parameters will be broadcast in SIB2.';
        }

        leaf threshServingLowP {
            description
              "Srxlev used for cell reselection to lower priority RAT frequencies.";
            type int32 {
                range "0..62";
            }
            default 0;
            units dB;
            must ". mod 2 = 0" {
                error-message
                  "The value must set with resolution/step of 2";
            }
            reference
              "3GPP TS 38.304";
            yexte:takes-effect
              "Next cell unlock";
            yexte:precondition
              "Value can only be changed when NRCellDU with matching cellLocalId "+
              "does not exist or has administrativeState LOCKED.";
            tailf:info 'Precondition: Value can only be changed when NRCellDU with matching cellLocalId does not exist or has administrativeState LOCKED, Takes effect: Next cell unlock, Srxlev used for cell reselection to lower priority RAT frequencies.';
        }

        leaf threshServingLowQ {
            description
              "Squal used for cell reselection to lower priority RAT frequencies.

               If the attribute is set to empty, value is not broadcast in SIB.";
            type int32 {
                range "0..31";
            }
            units dB;
            reference
              "3GPP TS 38.304";
            yexte:takes-effect
              "Next cell unlock";
            yexte:precondition
              "Value can only be changed when NRCellDU with matching cellLocalId "+
              "does not exist or has administrativeState LOCKED.";
            tailf:info 'Precondition: Value can only be changed when NRCellDU with matching cellLocalId does not exist or has administrativeState LOCKED, Takes effect: Next cell unlock, Squal used for cell reselection to lower priority RAT frequencies. If the attribute is set to empty, value is not broadcast in SIB.';
        }

        leaf tHystNormal {
            description
              "Additional duration for evaluating criteria to enter normal mobility "
            + "state.

               If empty, no mobility state parameters will be broadcast in SIB2.";
            type uint32 {
                range "30|60|120|180|240";
            }
            units s;
            reference
              "3GPP TS 38.331, 3GPP TS 38.304";
            yexte:takes-effect
              "New connection";
            tailf:info 'Takes effect: New connection, Additional duration for evaluating criteria to enter normal mobility state. If empty, no mobility state parameters will be broadcast in SIB2.';
        }

        leaf transmitSib2 {
            description
              "Broadcast status of SIB2.";
            type boolean;
            default false;
            yexte:dependencies
              "Can only be true if number of intra-frequency NRFreqRelations under cell is "+
              "greater than 0. Can only be false if transmitSib4 and transmitSib5 are false";
            reference
              "3GPP TS 38.331";
            yexte:takes-effect
              "Next cell unlock";
            yexte:precondition
              "Value can only be changed when NRCellDU with matching cellLocalId "+
              "does not exist or has administrativeState LOCKED.";
            tailf:info 'Precondition: Value can only be changed when NRCellDU with matching cellLocalId does not exist or has administrativeState LOCKED, Takes effect: Next cell unlock, Dependencies: Can only be true if number of intra-frequency NRFreqRelations under cell is greater than 0. Can only be false if transmitSib4 and transmitSib5 are false, Broadcast status of SIB2.';
        }

        leaf transmitSib4 {
            description
              "Broadcast status of SIB4.

              If number of inter-frequency NrFreqRelations exceeds 8, only the 8 "+
              "NrFreqRelations with higher priority according to "+
              "cellReselectionPriority value are included in SIB4.";
            type boolean;
            default false;
            yexte:dependencies
              "Can only be true if transmitSib2 is true. "+
              "Can only be true if number of inter-frequency NRFreqRelations under cell is "+
              "greater than 0";
            reference
              "3GPP TS 38.331";
            yexte:takes-effect
              "Next cell unlock";
            yexte:precondition
              "Value can only be changed when NRCellDU with matching cellLocalId "+
              "does not exist or has administrativeState LOCKED.";
            tailf:info 'Precondition: Value can only be changed when NRCellDU with matching cellLocalId does not exist or has administrativeState LOCKED, Takes effect: Next cell unlock, Dependencies: Can only be true if transmitSib2 is true. Can only be true if number of inter-frequency NRFreqRelations under cell is greater than 0, Broadcast status of SIB4. If number of inter-frequency NrFreqRelations exceeds 8, only the 8 NrFreqRelations with higher priority according to cellReselectionPriority value are included in SIB4.';
        }

        leaf transmitSib5 {
            description
              "Broadcast status of SIB5.";
            type boolean;
            default false;
            yexte:dependencies
              "Can only be true if transmitSib2 is true and number of "+
              "EUtranFreqRelations under cell is between 1 and 8.";
            reference
              "3GPP TS 38.331";
            yexte:takes-effect
              "Next cell unlock";
            yexte:precondition
              "Value can only be changed when NRCellDU with matching cellLocalId "+
              "does not exist or has administrativeState LOCKED.";
            tailf:info 'Precondition: Value can only be changed when NRCellDU with matching cellLocalId does not exist or has administrativeState LOCKED, Takes effect: Next cell unlock, Dependencies: Can only be true if transmitSib2 is true and number of EUtranFreqRelations under cell is between 1 and 8, Broadcast status of SIB5.';
        }

        leaf trStPSCellProfileRef {
            description
              "Reference to instance of TrStPSCellProfile MO.

              If non-empty, attributes from referenced MO instance are used.
              If empty, attribute default values according to TrStPSCellProfile and "+
              "TrStPSCellProfileUeCfg MO class definitions are used.";
            type types3gpp:DistinguishedName;
            must "re-match(current(), 'ManagedElement=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,GNBCUCPFunction=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,TrafficSteering=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,TrStPSCellProfile=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?') and
                  re-match(current(), concat('ManagedElement=', ../../../../me3gpp:id, ',.*')) and
                  re-match(current(), concat('.*GNBCUCPFunction=', ../../../gnbcucp3gpp:id, ',.*')) and
                  count( ../../../trafficsteering:TrafficSteering[re-match(current(), concat('.*TrafficSteering=', trafficsteering:id, ',.*'))]/trstpscellprofile:TrStPSCellProfile[re-match(current(), concat('.*TrStPSCellProfile=', trstpscellprofile:id))]) > 0" {
                description
              "The instance identifier must point at a TrStPSCellProfile entry.

              Examples of valid value are
              ManagedElement=1,GNBCUCPFunction=1,TrafficSteering=1,TrStPSCellProfile=Default";
                error-message
                  "trStPSCellProfileRef must refer to a TrStPSCellProfile under the same GNBCUCPFunction.";
            }
            yexte:dependencies
              "Referenced TrStPSCellProfile MO instance must be under "+
              "TrafficSteering MO under same GNBCUCPFunction as NRCellCU.";
            yexte:takes-effect
              "Next usage.";
            tailf:info 'Takes effect: Next usage, Dependencies: Referenced TrStPSCellProfile MO instance must be under TrafficSteering MO under same GNBCUCPFunction as NRCellCU, Reference to instance of TrStPSCellProfile MO. If non-empty, attributes from referenced MO instance are used. If empty, attribute default values according to TrStPSCellProfile and TrStPSCellProfileUeCfg MO class definitions are used.';
        }

        leaf trStSaCellProfileRef {
            description
              "Reference to instance of TrStSaCellProfile MO.

              If non-empty, attributes from referenced MO instance are used.
              If empty, attribute default values according to TrStSaCellProfile "+
              "and TrStSaCellProfileUeCfg MO class definitions are used.";
            type types3gpp:DistinguishedName;
            must "re-match(current(), 'ManagedElement=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,GNBCUCPFunction=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,TrafficSteering=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,TrStSaCellProfile=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?') and
                    re-match(current(), concat('ManagedElement=', ../../../../me3gpp:id, ',.*')) and
                    re-match(current(), concat('.*GNBCUCPFunction=', ../../../gnbcucp3gpp:id, ',.*')) and
                    count( ../../../trafficsteering:TrafficSteering[re-match(current(), concat('.*TrafficSteering=', trafficsteering:id, ',.*'))]/trstsacellprofile:TrStSaCellProfile[re-match(current(), concat('.*TrStSaCellProfile=', trstsacellprofile:id))]) > 0" {
                description
                "The instance identifier must point at a TrStSaCellProfile entry.

                Examples of valid value are
                ManagedElement=1,GNBCUCPFunction=1,TrafficSteering=1,TrStSaCellProfile=Default";
                error-message
                "The instance identifier must point at a TrStSaCellProfile MO entry";
            }
            yexte:dependencies
              "Referenced TrStSaCellProfile must be under TrafficSteering MO under "+
              "same GNBCUCPFunction as NRCellCU.";
            yexte:takes-effect
              "Next usage";
            tailf:info 'Takes effect: Next usage, Dependencies: Referenced TrStSaCellProfile must be under TrafficSteering MO under same GNBCUCPFunction as NRCellCU, Reference to instance of TrStSaCellProfile MO. If non-empty, attributes from referenced MO instance are used. If empty, attribute default values according to TrStSaCellProfile and TrStSaCellProfileUeCfg MO class definitions are used.';
        }

        leaf ueMCCellProfileRef {
            description
              "Reference to instance of UeMCCellProfile MO.

              If non-empty, attributes from referenced MO instance are used.
              If empty, attribute default values according to MO class definition "+
              "are used.";
            type types3gpp:DistinguishedName;
            must "re-match(current(), 'ManagedElement=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,GNBCUCPFunction=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,UeMC=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?,UeMCCellProfile=(\\\\( |#|\\\\|>|<|;|\"|\\+|,|[a-fA-F0-9]{2})|[^\\\\><;\"+,# ])((\\\\( |#|\\\\|>|<|;|\"|\\+|,|[a-fA-F0-9]{2})|[^\\\\><;\"+,])*(\\\\( |#|\\\\|>|<|;|\"|\\+|,|[a-fA-F0-9]{2})|[^\\\\><;\"+, ]))?') and
                  re-match(current(), concat('ManagedElement=', ../../../../me3gpp:id, ',.*')) and
                  re-match(current(), concat('.*GNBCUCPFunction=', ../../../gnbcucp3gpp:id, ',.*')) and
                  count( ../../../uemcvcucp:UeMC[re-match(current(), concat('.*UeMC=', uemcvcucp:id, ',.*'))]/uemccellprofile:UeMCCellProfile[re-match(current(), concat('.*UeMCCellProfile=', uemccellprofile:id))]) > 0" {
                description
                  "The instance identifier must point at a UeMCCellProfile entry.

                  Examples of valid value are
                  ManagedElement=1,GNBCUCPFunction=1,UeMC=1,UeMCCellProfile=1";
                error-message
                  "ueMCCellProfileRef must refer to a UeMCCellProfile under the same GNBCUCPFunction.";
            }
            yexte:dependencies
              "Referenced UeMCCellProfile must be under UeMC MO under same "+
              "GNBCUCPFunction as NRCellCU.";
            yexte:takes-effect
              "Next usage.";
            tailf:info 'Takes effect: Next usage, Dependencies: Referenced UeMCCellProfile must be under UeMC MO under same GNBCUCPFunction as NRCellCU, Reference to instance of UeMCCellProfile MO. If non-empty, attributes from referenced MO instance are used. If empty, attribute default values according to MO class definition are used.';
        }
    }

    grouping PLMNInfoListGrp {
        list pLMNInfoList {
            description
              "List of supported PLMNs.

              PLMN ID consists of MobileCountryCode (MCC, 3 digits) and "+
              "MobileNetworkCode (MNC, 2 or 3 digits).";
            key "mcc mnc";
            min-elements 0;
            max-elements 12;
            config false;
            uses types3gpp:PLMNId;
        }
    }

    augment "/me3gpp:ManagedElement/gnbcucp3gpp:GNBCUCPFunction/nrcellcu3gpp:NRCellCU/nrcellcu3gpp:attributes" {
        description
          "Adds Ericsson attributes to 3gpp NRCellCU.";
        uses NRCellCUVCUCPGrp;
        uses PLMNInfoListGrp;
    }
}
