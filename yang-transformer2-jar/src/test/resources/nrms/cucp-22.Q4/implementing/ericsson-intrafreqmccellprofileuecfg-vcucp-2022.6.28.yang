// Generated by eyang-preprocessor (1.22.0-48 2022-01-20 09:10:06 CET) on Jun 30, 2022, 8:31:38 AM
module ericsson-intrafreqmccellprofileuecfg-vcucp {
    yang-version 1.1;
    namespace "urn:rdns:com:ericsson:oammodel:ericsson-intrafreqmccellprofileuecfg-vcucp";
    prefix intrafreqmccellprofileuecfg;

    import tailf-common {
        prefix tailf;
    }
    import _3gpp-common-managed-element {
        prefix "me3gpp";
    }
    import _3gpp-nr-nrm-gnbcucpfunction {
        prefix "gnbcucp3gpp";
    }
    import _3gpp-common-top {
        prefix "top3gpp";
    }
    import ericsson-intrafreqmc-vcucp {
        prefix "intrafreqmc";
    }
    import ericsson-intrafreqmccellprofile-vcucp {
        prefix "intrafreqmccellprofile";
    }
    import ericsson-yang-extensions {
        prefix "yexte";
    }
    import ericsson-common-types-vcucp {
        prefix "commontypes";
    }

    organization
      "Ericsson AB";
    contact
      "Ericsson first line support via email";
    description
      "The module defines the IntraFreqMCCellProfileUeCfg data model for the Ericsson vCU-CP.

       Copyright (c) 2022 Ericsson AB. All rights reserved.";

    revision 2022-06-28 {
        description
            "Removed module-status preliminary.
             Removed preliminary status from IntraFreqMCCellProfileUeCfg.";
        yexte:version 0;
        yexte:release 2;
        yexte:correction 0;
        reference
            "RFC 7950: The YANG 1.1 Data Modeling Language";
    }

    revision 2022-03-14 {
        description
          "Initial version of the IntraFreqMCCellProfileUeCfg model.";
        yexte:version 0;
        yexte:release 1;
        yexte:correction 0;
        reference
          "RFC 7950: The YANG 1.1 Data Modeling Language";
    }

    grouping IntraFreqMCCellProfileUeCfgGrp {
        description
            "Represents the IntraFreqMCCellProfileUeCfg IOC.";

        leaf betterSpCellTriggerQuantity {
            description
                "Measurement trigger quantity used when searching for better Special "+
                "Cell.

                 Special Cell is either PCell or PSCell.";
            type commontypes:TriggerQuantity;
            default RSRP;
            reference
                "3GPP TS 38.331";
            yexte:takes-effect
                "Next usage.";
            tailf:info 'Takes effect: Next usage, Measurement trigger quantity used when searching for better Special Cell. Special Cell is either PCell or PSCell.';
        }

        leaf endcActionEvalFail {
            description
                "Action taken when intra-frequency PSCell change evaluation or PSCell "+
                "change procedure fails.

                 Applies to UEs that use cell as PSCell in EN-DC.";
            type commontypes:EndcMobilityAction;
            default RELEASE;
            yexte:takes-effect
                "Next usage.";
            tailf:info 'Takes effect: Next usage, Action taken when intra-frequency PSCell change evaluation or PSCell change procedure fails. Applies to UEs that use cell as PSCell in EN-DC.';
        }

        leaf-list prefUeGroupList {
            description
                "Preference UE group list.

                 List of preference UE group identifiers.

                 If empty, the MO instance matches preference UE group identifiers "+
                "not defined in prefUeGroupList of any other MO instances under "+
                "parent MO instance.";
            type int32 {
                range "1..255";
            }
            max-elements 8;
            ordered-by user;
            yexte:dependencies
                "Combinations of pair of preference UE group Identifier in "+
                "prefUeGroupList and UE group identifier in ueGroupList must be "+
                "unique among IntraFreqMCCellProfileUeCfg instances under same parent "+
                "IntraFreqMCCellProfile instance.

                 For all preference UE group identifiers in prefUeGroupList "+
                "attributes under same parent IntraFreqMCCellProfile MO instance, "+
                "exactly one IntraFreqMCCellProfileUeCfg MO instance must exist that "+
                "combines the given preference UE group identifier with an empty "+
                "ueGroupList.";
            yexte:disturbances
                "Changing this attribute can cause loss of traffic.";
            yexte:takes-effect
                "Next usage.";
            must "count(../../../IntraFreqMCCellProfileUeCfg/attributes[prefUeGroupList = current() and count(ueGroupList) = 0]) = 1" {
                error-message
                   "Exactly one IntraFreqMCCellProfileUeCfg instance under an IntraFreqMCCellProfile must combine a specific preference UE group identifier in attribute prefUeGroupList with an empty ueGroupList.";
            }
            tailf:info 'Takes effect: Next usage, Traffic Disturbance: Changing this attribute can cause loss of traffic, Dependencies: Combinations of pair of preference UE group Identifier in prefUeGroupList and UE group identifier in ueGroupList must be unique among IntraFreqMCCellProfileUeCfg instances under same parent IntraFreqMCCellProfile instance.

                 For all preference UE group identifiers in prefUeGroupList attributes under same parent IntraFreqMCCellProfile MO instance, exactly one IntraFreqMCCellProfileUeCfg MO instance must exist that combines the given preference UE group identifier with an empty ueGroupList, Preference UE group list. List of preference UE group identifiers. If empty, the MO instance matches preference UE group identifiers not defined in prefUeGroupList of any other MO instances under parent MO instance.';
        }

        container rsrpBetterSpCell {
            description
                "Downlink RSRP measurement report criteria when searching for better "+
                "Special Cell.

                 Special Cell is either PCell or PSCell.
                 Used only when triggerQuantity is set to RSRP.";
            uses commontypes:ReportConfigA3Rsrp;
            reference
                "3GPP TS 38.331";
            yexte:takes-effect
                "Next usage.";
            tailf:info 'Takes effect: Next usage, Downlink RSRP measurement report criteria when searching for better Special Cell. Special Cell is either PCell or PSCell. Used only when triggerQuantity is set to RSRP.';
        }

        container rsrqBetterSpCell {
            description
                "Downlink RSRQ measurement report criteria when searching for better "+
                "Special Cell.

                 Special Cell is either PCell or PSCell.
                 Used only when triggerQuantity is set to RSRQ.";
            uses commontypes:ReportConfigA3Rsrq;
            reference
                "3GPP TS 38.331";
            yexte:takes-effect
                "Next usage.";
            tailf:info 'Takes effect: Next usage, Downlink RSRQ measurement report criteria when searching for better Special Cell. Special Cell is either PCell or PSCell. Used only when triggerQuantity is set to RSRQ.';
        }

        leaf-list ueConfGroupList {
            description
                "UE configuration group list.

                 List of UE configuration group identifiers.

                 If empty, the MO instance matches all UE configuration group "+
                "identifiers.

                 Which UE configuration group type that is applied is defined by "+
                "attribute ueConfGroupType in parent MO class instance.";
            type int32 {
                range "1..255";
            }
            max-elements 16;
            ordered-by user;
            yexte:dependencies
                "A given UE configuration group identifier can be defined in only one "+
                "ueConfGroupList among IntraFreqMCCellProfileUeCfg instances under "+
                "same parent IntraFreqMCCellProfile instance.";
            yexte:disturbances
                "Changing this attribute can cause loss of traffic.";
            yexte:takes-effect
                "Next usage.";
            must "count(../../../IntraFreqMCCellProfileUeCfg/attributes[ueConfGroupList = current()]) &lt;= 1" {
                error-message
                    "Only one IntraFreqMCCellProfileUeCfg instance under an IntraFreqMCCellProfile can include a specific ueConfGroupId in attribute ueConfGroupList.";
            }
            tailf:info 'Takes effect: Next usage, Traffic Disturbance: Changing this attribute can cause loss of traffic, Dependencies: A given UE configuration group identifier can be defined in only one ueConfGroupList among IntraFreqMCCellProfileUeCfg instances under same parent IntraFreqMCCellProfile instance, UE configuration group list. List of UE configuration group identifiers. If empty, the MO instance matches all UE configuration group identifiers. Which UE configuration group type that is applied is defined by attribute ueConfGroupType in parent MO class instance.';
        }

        leaf-list ueGroupList {
            description
                "UE group list.

                 List of UE group identifiers.

                 If empty, the MO instance matches all UE group identifiers.";
            type int32 {
                range "1..255";
            }
            max-elements 16;
            ordered-by user;
            yexte:dependencies
                "Combinations of pair of preference UE group Identifier in "+
                "prefUeGroupList and UE group identifier in ueGroupList must be "+
                "unique among IntraFreqMCCellProfileUeCfg instances under same parent "+
                "IntraFreqMCCellProfile instance.

                 Combination of a UE group identifier in UeGroupList and empty "+
                "prefUeGroupList must be unique among IntraFreqMCCellProfileUeCfg "+
                "instances under same parent IntraFreqMCCellProfile instance.";
            yexte:disturbances
                "Changing this attribute can cause loss of traffic.";
            yexte:takes-effect
                "Next usage.";
            must "count(../prefUeGroupList) &gt; 0 or
                  count(../../../IntraFreqMCCellProfileUeCfg/attributes[ueGroupList = current() and count(prefUeGroupList) = 0]) &lt;= 1" {
                error-message
                    "Only one IntraFreqMCCellProfileUeCfg instance under an IntraFreqMCCellProfile can combine a specific UE group identifier in attribute ueGroupList with an empty prefUeGroupList.";
            }
            tailf:info 'Takes effect: Next usage, Traffic Disturbance: Changing this attribute can cause loss of traffic, Dependencies: Combinations of pair of preference UE group Identifier in prefUeGroupList and UE group identifier in ueGroupList must be unique among IntraFreqMCCellProfileUeCfg instances under same parent IntraFreqMCCellProfile instance.

                 Combination of a UE group identifier in UeGroupList and empty prefUeGroupList must be unique among IntraFreqMCCellProfileUeCfg instances under same parent IntraFreqMCCellProfile instance, UE group list. List of UE group identifiers. If empty, the MO instance matches all UE group identifiers.';
        }
    }

    augment "/me3gpp:ManagedElement/gnbcucp3gpp:GNBCUCPFunction/intrafreqmc:IntraFreqMC/intrafreqmccellprofile:IntraFreqMCCellProfile" {
        list IntraFreqMCCellProfileUeCfg {
            description
                "Intra-frequency mobility control cell configuration profile, "+
                "UE configuration group.

                 Applies to UEs that use cell as SpCell. Attributes are used on "+
                "cell level.

                 MO instance IntraFreqMCCellProfileUeCfg=Base is created "+
                "automatically when parent MO is created, unless created "+
                "manually in the same transaction as parent MO.

                 Attributes prefUeGroupList, ueGroupList and ueConfGroupList "+
                "must be empty in instance IntraFreqMCCellProfileUeCfg=Base but "+
                "cannot all be empty in other instances of "+
                "IntraFreqMCCellProfileUeCfg under same parent "+
                "IntraFreqMCCellProfile.";
            key id;
            max-elements 32;
            uses top3gpp:Top_Grp;
            container attributes {
                uses IntraFreqMCCellProfileUeCfgGrp;
                uses commontypes:UserLabelGrp;
            }
            yexte:precondition
                "IntraFreqMCCellProfileUeCfg=Base MO instance must not be "+
                "deleted unless parent MO is deleted. Other instances can be "+
                "created and deleted manually.

                 Maximum 31 IntraFreqMCCellProfileUeCfg instances, with RDN "+
                "different from Base, can be created.";

            must "count(../IntraFreqMCCellProfileUeCfg) &lt; 32 or
                  count(../IntraFreqMCCellProfileUeCfg/id[. = 'Base']) = 1" {
                error-message
                    "Maximum 31 IntraFreqMCCellProfileUeCfg instances under an IntraFreqMCCellProfile can be created with RDN different from Base.";
            }

            must "id != 'Base' or
                  (count(attributes/prefUeGroupList) = 0 and count(attributes/ueGroupList) = 0 and count(attributes/ueConfGroupList) = 0)" {
                error-message
                    "prefUeGroupList, ueGroupList and ueConfGroupList must be empty in the IntraFreqMCCellProfileUeCfg=Base instance.";
            }

            must "id = 'Base' or not(count(attributes/prefUeGroupList) = 0 and count(attributes/ueGroupList) = 0 and count(attributes/ueConfGroupList) = 0)" {
                error-message
                    "prefUeGroupList, ueGroupList and ueConfGroupList can only be empty in the IntraFreqMCCellProfileUeCfg=Base instance.";
            }

            must "count(../IntraFreqMCCellProfileUeCfg/attributes[prefUeGroupList = current()/attributes/prefUeGroupList and ueGroupList = current()/attributes/ueGroupList] ) &lt;= 1" {
                error-message
                    "The combinations of a pair of UE group identifier in ueGroupList and preference UE group identifier in prefUeGroupList must be unique among IntraFreqMCCellProfileUeCfg under an IntraFreqMCCellProfile.";
            }
            tailf:info 'Precondition: IntraFreqMCCellProfileUeCfg=Base MO instance must not be deleted unless parent MO is deleted. Other instances can be created and deleted manually.

                 Maximum 31 IntraFreqMCCellProfileUeCfg instances, with RDN different from Base, can be created, Intra-frequency mobility control cell configuration profile, UE configuration group. Applies to UEs that use cell as SpCell. Attributes are used on cell level. MO instance IntraFreqMCCellProfileUeCfg=Base is created automatically when parent MO is created, unless created manually in the same transaction as parent MO. Attributes prefUeGroupList, ueGroupList and ueConfGroupList must be empty in instance IntraFreqMCCellProfileUeCfg=Base but cannot all be empty in other instances of IntraFreqMCCellProfileUeCfg under same parent IntraFreqMCCellProfile.';
        }
    }
}
