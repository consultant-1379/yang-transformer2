// Generated by eyang-preprocessor (1.22.0-48 2022-01-20 09:10:06 CET) on Jun 30, 2022, 8:31:39 AM
module ericsson-mcpc-pscell-nr-freq-rel-profile-vcucp {
    yang-version 1.1;
    namespace urn:rdns:com:ericsson:oammodel:ericsson-mcpc-pscell-nr-freq-rel-profile-vcucp;
    prefix mcpcpscellnrfreqrelprofile;

    import tailf-common {
        prefix tailf;
    }
    import _3gpp-common-managed-element {
        prefix me3gpp;
    }
    import _3gpp-nr-nrm-gnbcucpfunction {
        prefix gnbcucp3gpp;
    }
    import _3gpp-common-top {
        prefix top3gpp;
    }
    import ericsson-yang-extensions {
        prefix yexte;
    }
    import ericsson-mcpc-vcucp {
        prefix mcpc;
    }
    import ericsson-common-types-vcucp {
        prefix commontypes;
    }

    organization
        "Ericsson AB";
    contact
        "Ericsson first line support via email";
    description
        "The module defines the McpcPSCellNrFreqRelProfile data model for the Ericsson vCU-CP.

        Copyright (c) 2021-2022 Ericsson AB. All rights reserved.";

    revision 2022-06-28 {
        description
            "Removed module-status preliminary.";
        yexte:version 0;
        yexte:release 3;
        yexte:correction 0;
        reference
            "RFC 7950: The YANG 1.1 Data Modeling Language";
    }

    revision 2022-03-14 {
        description
            "Update description of McpcPSCellNrFreqRelProfile.
             Added the userLabel attribute.";
        yexte:version 0;
        yexte:release 2;
        yexte:correction 0;
        reference
            "RFC 7950: The YANG 1.1 Data Modeling Language";
    }

    revision 2021-11-05 {
        description
            "Update precondition for McpcPSCellNrFreqRelProfile.";
        yexte:version 0;
        yexte:release 1;
        yexte:correction 1;
        reference
            "RFC 7950: The YANG 1.1 Data Modeling Language";
    }

    revision 2021-09-20 {
        description
            "Initial version of the McpcPSCellNrFreqRelProfile model";
        yexte:version 0;
        yexte:release 1;
        yexte:correction 0;
        reference
            "RFC 7950: The YANG 1.1 Data Modeling Language";
    }

    augment "/me3gpp:ManagedElement/gnbcucp3gpp:GNBCUCPFunction/mcpc:Mcpc" {

        list McpcPSCellNrFreqRelProfile {
            description
                "Mobility control at poor coverage function for PSCell in EN-DC.

                Applies to UEs that use this cell as PSCell in EN-DC. Attributes "+
                "are used on NR frequency relation level.

                This function for PSCell in EN-DC can be enabled for each "+
                "NRCellCU MO with NRCellCU::mcpcPSCellEnabled.

                MO instance McpcPSCellNrFreqRelProfile=Default is created "+
                "automatically when parent MO is created, unless created manually "+
                "in the same transaction as parent MO.

                If NRFreqRelation::mcpcPSCellNrFreqRelProfileRef is non-empty, "+
                "attributes from referred MO instance are used.
                If NRFreqRelation::mcpcPSCellNrFreqRelProfileRef is empty, "+
                "attribute default values according to McpcPSCellNrFreqRelProfile "+
                "and McpcPSCellNrFreqRelProfileUeCfg MO class definitions are "+
                "used.";
            key id;
            uses top3gpp:Top_Grp;
            container attributes {
                uses commontypes:UserLabelGrp;
            }
            yexte:precondition
                "McpcPSCellNrFreqRelProfile=Default MO must not be deleted "+
                "unless parent MO is deleted. Other instances can be created and "+
                "deleted manually.";
            tailf:info 'Precondition: McpcPSCellNrFreqRelProfile=Default MO must not be deleted unless parent MO is deleted. Other instances can be created and deleted manually, Mobility control at poor coverage function for PSCell in EN-DC. Applies to UEs that use this cell as PSCell in EN-DC. Attributes are used on NR frequency relation level. This function for PSCell in EN-DC can be enabled for each NRCellCU MO with NRCellCU::mcpcPSCellEnabled. MO instance McpcPSCellNrFreqRelProfile=Default is created automatically when parent MO is created, unless created manually in the same transaction as parent MO. If NRFreqRelation::mcpcPSCellNrFreqRelProfileRef is non-empty, attributes from referred MO instance are used. If NRFreqRelation::mcpcPSCellNrFreqRelProfileRef is empty, attribute default values according to McpcPSCellNrFreqRelProfile and McpcPSCellNrFreqRelProfileUeCfg MO class definitions are used.';
        }
    }
}
