// Generated by eyang-preprocessor (1.22.0-48 2022-01-20 09:10:06 CET) on Jun 30, 2022, 8:31:44 AM
module ericsson-trafficsteering-vcucp {
    yang-version 1.1;
    namespace "urn:rdns:com:ericsson:oammodel:ericsson-trafficsteering-vcucp";
    prefix trafficsteering;

    import tailf-common {
        prefix tailf;
    }
    import _3gpp-common-managed-element {
        prefix "me3gpp";
    }
    import _3gpp-nr-nrm-gnbcucpfunction {
        prefix "gnbcucp3gpp";
    }
    import _3gpp-common-top {
        prefix "top3gpp";
    }
    import ericsson-yang-extensions {
        prefix "yexte";
    }
    import ericsson-common-types-vcucp {
        prefix "commontypes";
    }

    organization
      "Ericsson AB";
    contact
      "Ericsson first line support via email";
    description
      "The module defines the TrafficSteering data model for the Ericsson vCU-CP.

       Copyright (c) 2021-2022 Ericsson AB. All rights reserved.";

    revision 2022-06-28 {
        description
            "Removed module-status preliminary.";
        yexte:version 0;
        yexte:release 3;
        yexte:correction 0;
        reference
            "RFC 7950: The YANG 1.1 Data Modeling Language";
    }

    revision 2022-03-14 {
        description
            "Updated description of TrafficSteering.
             Added the userLabel attribute.";
        yexte:version 0;
        yexte:release 2;
        yexte:correction 0;
        reference
            "RFC 7950: The YANG 1.1 Data Modeling Language";
    }

    revision 2021-11-05 {
        description
          "Update precondition for TrafficSteering list.";
        yexte:version 0;
        yexte:release 1;
        yexte:correction 1;
        reference
          "RFC 7950: The YANG 1.1 Data Modeling Language";
    }

    revision 2021-09-16 {
        description
          "Initial version of the TrafficSteering model.";
        yexte:version 0;
        yexte:release 1;
        yexte:correction 0;
        reference
          "RFC 7950: The YANG 1.1 Data Modeling Language";
    }

    augment "/me3gpp:ManagedElement/gnbcucp3gpp:GNBCUCPFunction" {
        list TrafficSteering {
            description
                "Configuration of Traffic Steering (TrSt) and container for TrSt "+
                "profiles.

                TrafficSteering=1 MO instance is created automatically when parent "+
                "MO is created, unless created manually in the same transaction as "+
                "parent MO.

                The RDN of this MO must always be TrafficSteering=1.";
            key id;
            max-elements 1;
            uses top3gpp:Top_Grp {
                refine id {
                    must '. = "1"' {
                        error-message
                          "The RDN of this MO must always be TrafficSteering=1";
                    }
                }
            }
            container attributes {
                uses commontypes:UserLabelGrp;
            }
            yexte:precondition
                "TrafficSteering=1 MO instance must not be deleted unless parent MO is "+
                "deleted.";
            tailf:info 'Precondition: TrafficSteering=1 MO instance must not be deleted unless parent MO is deleted, Configuration of Traffic Steering (TrSt) and container for TrSt profiles. TrafficSteering=1 MO instance is created automatically when parent MO is created, unless created manually in the same transaction as parent MO. The RDN of this MO must always be TrafficSteering=1.';
        }
    }
}
