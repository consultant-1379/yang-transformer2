// Generated by eyang-preprocessor (1.22.0-48 2022-01-20 09:10:06 CET) on Jun 30, 2022, 8:31:35 AM
module ericsson-eutrancellrelation-dev-vcucp {
    yang-version 1.1;
    namespace urn:rdns:com:ericsson:oammodel:ericsson-eutrancellrelation-dev-vcucp;
    prefix eutrancellrel3gppdev;

    import _3gpp-common-managed-element {
        prefix me3gpp;
    }
    import _3gpp-nr-nrm-gnbcucpfunction {
        prefix gnbcucp3gpp;
    }
    import _3gpp-nr-nrm-nrcellcu {
        prefix nrcellcu3gpp;
    }
    import _3gpp-nr-nrm-eutrancellrelation {
        prefix eutrancellrel3gpp;
    }
    import ericsson-yang-extensions {
        prefix yexte;
    }

    organization
        "Ericsson AB";
    contact
        "Ericsson first line support via email";
    description
        "The module defines the EUtranCellRelation data model deviations for the Ericsson vCU-CP.

        Copyright (c) 2021-2022 Ericsson AB. All rights reserved.";

    revision 2022-06-28 {
        description
            "Removed module-status preliminary.";
        yexte:version 0;
        yexte:release 2;
        yexte:correction 0;
        reference
            "RFC 7950: The YANG 1.1 Data Modeling Language";
    }

    revision 2021-01-11 {
        description
            "Deviations on _3gpp-nr-nrm-eutrancellrelation.";
        yexte:version 0;
        yexte:release 1;
        yexte:correction 0;
        reference
            "RFC 7950: The YANG 1.1 Data Modeling Language";
    }

    deviation /me3gpp:ManagedElement/gnbcucp3gpp:GNBCUCPFunction/nrcellcu3gpp:NRCellCU/eutrancellrel3gpp:EUtranCellRelation/eutrancellrel3gpp:ManagedNFService {
        description "Managed Network Function Service is not supported for EUtranCellRelation.";
        deviate not-supported;
    }

    deviation /me3gpp:ManagedElement/gnbcucp3gpp:GNBCUCPFunction/nrcellcu3gpp:NRCellCU/eutrancellrel3gpp:EUtranCellRelation/eutrancellrel3gpp:PerfMetricJob {
        description "Performance Metric Job is not supported for EUtranCellRelation.";
        deviate not-supported;
    }

    deviation /me3gpp:ManagedElement/gnbcucp3gpp:GNBCUCPFunction/nrcellcu3gpp:NRCellCU/eutrancellrel3gpp:EUtranCellRelation/eutrancellrel3gpp:ThresholdMonitor {
        description "Threshold Monitor is not supported for EUtranCellRelation.";
        deviate not-supported;
    }

    deviation /me3gpp:ManagedElement/gnbcucp3gpp:GNBCUCPFunction/nrcellcu3gpp:NRCellCU/eutrancellrel3gpp:EUtranCellRelation/eutrancellrel3gpp:TraceJob {
        description "Trace Job is not supported for EUtranCellRelation.";
        deviate not-supported;
    }

    deviation /me3gpp:ManagedElement/gnbcucp3gpp:GNBCUCPFunction/nrcellcu3gpp:NRCellCU/eutrancellrel3gpp:EUtranCellRelation/eutrancellrel3gpp:attributes/eutrancellrel3gpp:SupportedPerfMetricGroup {
        description "Supported Performance Metrics is not supported for EUtranCellRelation.";
        deviate not-supported;
    }

    deviation /me3gpp:ManagedElement/gnbcucp3gpp:GNBCUCPFunction/nrcellcu3gpp:NRCellCU/eutrancellrel3gpp:EUtranCellRelation/eutrancellrel3gpp:attributes/eutrancellrel3gpp:vnfParametersList {
        description "EUtranCellRelation::vnfParametersList is not supported.";
        deviate not-supported;
    }

    deviation /me3gpp:ManagedElement/gnbcucp3gpp:GNBCUCPFunction/nrcellcu3gpp:NRCellCU/eutrancellrel3gpp:EUtranCellRelation/eutrancellrel3gpp:attributes/eutrancellrel3gpp:peeParametersList {
        description "EUtranCellRelation::peeParametersList is not supported.";
        deviate not-supported;
    }

    deviation /me3gpp:ManagedElement/gnbcucp3gpp:GNBCUCPFunction/nrcellcu3gpp:NRCellCU/eutrancellrel3gpp:EUtranCellRelation/eutrancellrel3gpp:attributes/eutrancellrel3gpp:priorityLabel {
        description "EUtranCellRelation::priorityLabel is not supported.";
        deviate not-supported;
    }

    deviation /me3gpp:ManagedElement/gnbcucp3gpp:GNBCUCPFunction/nrcellcu3gpp:NRCellCU/eutrancellrel3gpp:EUtranCellRelation/eutrancellrel3gpp:attributes/eutrancellrel3gpp:tCI {
        description "EUtranCellRelation::tCI is not supported.";
        deviate not-supported;
    }

    deviation /me3gpp:ManagedElement/gnbcucp3gpp:GNBCUCPFunction/nrcellcu3gpp:NRCellCU/eutrancellrel3gpp:EUtranCellRelation/eutrancellrel3gpp:attributes/eutrancellrel3gpp:isENDCAllowed {
        description "EUtranCellRelation::isENDCAllowed is not supported.";
        deviate not-supported;
    }

    deviation /me3gpp:ManagedElement/gnbcucp3gpp:GNBCUCPFunction/nrcellcu3gpp:NRCellCU/eutrancellrel3gpp:EUtranCellRelation/eutrancellrel3gpp:attributes/eutrancellrel3gpp:isICICInformationSendAllowed {
        description "EUtranCellRelation::isICICInformationSendAllowed is not supported.";
        deviate not-supported;
    }

    deviation /me3gpp:ManagedElement/gnbcucp3gpp:GNBCUCPFunction/nrcellcu3gpp:NRCellCU/eutrancellrel3gpp:EUtranCellRelation/eutrancellrel3gpp:attributes/eutrancellrel3gpp:isLBAllowed {
        description "EUtranCellRelation::isLBAllowed is not supported.";
        deviate not-supported;
    }

    deviation /me3gpp:ManagedElement/gnbcucp3gpp:GNBCUCPFunction/nrcellcu3gpp:NRCellCU/eutrancellrel3gpp:EUtranCellRelation/eutrancellrel3gpp:attributes/eutrancellrel3gpp:isESCoveredBy {
        description "EUtranCellRelation::isESCoveredBy is not supported.";
        deviate not-supported;
    }

    deviation /me3gpp:ManagedElement/gnbcucp3gpp:GNBCUCPFunction/nrcellcu3gpp:NRCellCU/eutrancellrel3gpp:EUtranCellRelation/eutrancellrel3gpp:attributes/eutrancellrel3gpp:qOffset {
        description "EUtranCellRelation::qOffset is not supported.";
        deviate not-supported;
    }

    deviation /me3gpp:ManagedElement/gnbcucp3gpp:GNBCUCPFunction/nrcellcu3gpp:NRCellCU/eutrancellrel3gpp:EUtranCellRelation/eutrancellrel3gpp:attributes/eutrancellrel3gpp:cellIndividualOffset {
        deviate replace {
            config true;
        }
    }
}
