// Generated by eyang-preprocessor (1.22.0-48 2022-01-20 09:10:06 CET) on Jun 30, 2022, 8:31:43 AM
module ericsson-qci-profile-endc-configext-vcucp {
    yang-version 1.1;
    namespace urn:rdns:com:ericsson:oammodel:ericsson-qci-profile-endc-configext-vcucp;
    prefix qciprofendcconfigextvcucp;

    import tailf-common {
        prefix tailf;
    }
    import _3gpp-common-managed-element {
        prefix me3gpp;
    }
    import _3gpp-nr-nrm-gnbcucpfunction {
        prefix gnbcucp3gpp;
    }
    import _3gpp-common-top {
        prefix top3gpp;
    }
    import ericsson-yang-extensions {
        prefix yexte;
    }

    organization
        "Ericsson AB";
    contact
        "Ericsson first line support via email";
    description
        "The module defines the QciProfileEndcConfigExt data model for the Ericsson vCU-CP.

        Copyright (c) 2021-2022 Ericsson AB. All rights reserved.";

    revision 2022-06-28 {
        description
            "Removed module-status preliminary.
             Removed preliminary status from ulDataSplitThresholdMcg.";
        yexte:version 0;
        yexte:release 4;
        yexte:correction 0;
        reference
            "RFC 7950: The YANG 1.1 Data Modeling Language";
    }

    revision 2022-03-14 {
        description
            "Updated description of ulDataSplitThreshold.
            Adding ulDataSplitThresholdMcg.";
        yexte:version 0;
        yexte:release 3;
        yexte:correction 0;
        reference
            "RFC 7950: The YANG 1.1 Data Modeling Language";
    }

    revision 2021-11-05 {
        description
            "Updated description for initialUplinkConf.
             Updated description, reference and disturbances for ulDataSplitThreshold.";
        yexte:version 0;
        yexte:release 2;
        yexte:correction 1;
        reference
            "RFC 7950: The YANG 1.1 Data Modeling Language";
    }

    revision 2021-05-06 {
        description
            "Remove restricted extensions from configurable attributes.";
        yexte:version 0;
        yexte:release 2;
        yexte:correction 0;
        reference
            "RFC 7950: The YANG 1.1 Data Modeling Language";
    }

    revision 2021-04-07 {
        description
            "Initial version of the QciProfileEndcConfigExt model";
        yexte:version 0;
        yexte:release 1;
        yexte:correction 0;
        reference
            "RFC 7950: The YANG 1.1 Data Modeling Language";
    }

    typedef UplinkTarget {
        type enumeration {
            enum MCG {
                value 0;
                description "PDCP uplink PDU to the configured RLC entity in master cell group at initial state.";
            }

            enum SCG {
                value 1;
                description "PDCP uplink PDU to the configured RLC entity in secondary cell group at initial state.";
            }
        }
        description "Uplink configuration enums.";
    }

    grouping QciProfileEndcConfigExtGrp {
        description
            "Managing quality of service related parameters for Data Radio Bearers in EN-DC.
            Extension of the configuration in MO class QciProfileEndcConfig.";

        leaf initialUplinkConf {
            description
                "Initial uplink configuration for EN-DC and NR-DC.

                Whether to use MCG or SCG leg for UL at initial state. Set when dual "+
                "connectivity is configured.";
            type UplinkTarget;
            default MCG;
            yexte:takes-effect
                "New connection";
            tailf:info 'Takes effect: New connection, Initial uplink configuration for EN-DC and NR-DC. Whether to use MCG or SCG leg for UL at initial state. Set when dual connectivity is configured.';
        }

        leaf ulDataSplitThreshold {
            description
                "Buffer threshold for uplink PDCP split for capable UE instances.

                Specifies buffer level where capable UE instances can split data on "+
                "both main and secondary leg when primary path is SCG.
                A capable UE is a UE with dual connectivity supporting split DRB with "+
                "uplink on both MCG and SCG. This UE can submit uplink PDCP PDUs to "+
                "both primary RLC entity and secondary RLC entity if total amount of "+
                "PDCP and RLC data volume for initial transmission in the two "+
                "associated RLC entities is equal or larger than the used threshold.
                If set to 0, uplink PDCP split is always active for capable UE "+
                "instances.
                If set to -1, used threshold is infinity meaning that PDCP split is "+
                "not allowed even for capable UE instances.
                The attribute is common for EN-DC and NR-DC.
                If empty, used threshold will be automatically controlled for EN-DC "+
                "users and set to infinity for NR-DC users.

                Without license for LTE-NR Uplink Aggregation a value of infinity is "+
                "used for EN-DC and NR-DC users.";
            type int32 {
                range "-1 | 0 | 100 | 200 | 400 | 800 | 1600 | 3200 | 6400 | 12800 | 25600 | 51200 | 102400 | 204800 | 409600 | 819200 | 1228800 | 1638400 | 2457600 | 3276800 | 4096000 | 4915200 | 5734400 | 6553600";
            }
            units bytes;
            reference
                "3GPP TS 38.463, 3GPP TS 38.331, 3GPP TS 38.323";
            yexte:disturbances
                "Changing this attribute can cause loss of traffic.";
            yexte:takes-effect
                "New connection";
            tailf:info 'Takes effect: New connection, Traffic Disturbance: Changing this attribute can cause loss of traffic, Buffer threshold for uplink PDCP split for capable UE instances. Specifies buffer level where capable UE instances can split data on both main and secondary leg when primary path is SCG. A capable UE is a UE with dual connectivity supporting split DRB with uplink on both MCG and SCG. This UE can submit uplink PDCP PDUs to both primary RLC entity and secondary RLC entity if total amount of PDCP and RLC data volume for initial transmission in the two associated RLC entities is equal or larger than the used threshold. If set to 0, uplink PDCP split is always active for capable UE instances. If set to -1, used threshold is infinity meaning that PDCP split is not allowed even for capable UE instances. The attribute is common for EN-DC and NR-DC. If empty, used threshold will be automatically controlled for EN-DC users and set to infinity for NR-DC users. Without license for LTE-NR Uplink Aggregation a value of infinity is used for EN-DC and NR-DC users.';
        }

        leaf ulDataSplitThresholdMcg {
            description
                "Buffer threshold for uplink PDCP split for capable UE instances when "+
                "primary path is MCG.

                This attribute is only applicable for EN-DC UEs. For NR-DC UEs used "+
                "threshold is infinity meaning that PDCP split is not allowed when "+
                "primary path is MCG.
                Only applicable if license for LTE-NR Uplink Aggregation is present "+
                "and feature is active.

                Following settings are possible:
                - If empty and value for ulDataSplitThreshold is also empty, "+
                "threshold is 51200.
                - If empty and value for ulDataSplitThreshold is non-empty, value "+
                "according to ulDataSplitThreshold is used.
                - If set to -1, threshold is infinity meaning that PDCP split is not "+
                "allowed.
                - If set to 0, UL PDCP split is always active.
                - Value -1 is recommended when NRCellDU::endcUlLegSwitchEnabled is "+
                "true and a low value is set for NRCellDU::endcUlNrLowQualThresh.
                - Values 0 to 1600 are only recommended for operators for temporary "+
                "testing purposes.";
            type int32 {
                range "-1|0|100|200|400|800|1600|3200|6400|12800|25600|51200|102400|"+
                    "204800|409600|819200|1228800|1638400|2457600|3276800|4096000|"+
                    "4915200|5734400|6553600";
            }
            units byte;
            reference
                "3GPP TS 38.463, 3GPP TS 38.331, 3GPP TS 38.323";
            yexte:disturbances
                "Changing this attribute can cause loss of traffic.";
            yexte:takes-effect
                "New connection";
            tailf:info 'Takes effect: New connection, Traffic Disturbance: Changing this attribute can cause loss of traffic, Buffer threshold for uplink PDCP split for capable UE instances when primary path is MCG. This attribute is only applicable for EN-DC UEs. For NR-DC UEs used threshold is infinity meaning that PDCP split is not allowed when primary path is MCG. Only applicable if license for LTE-NR Uplink Aggregation is present and feature is active. Following settings are possible: - If empty and value for ulDataSplitThreshold is also empty, threshold is 51200. - If empty and value for ulDataSplitThreshold is non-empty, value according to ulDataSplitThreshold is used. - If set to -1, threshold is infinity meaning that PDCP split is not allowed. - If set to 0, UL PDCP split is always active. - Value -1 is recommended when NRCellDU::endcUlLegSwitchEnabled is true and a low value is set for NRCellDU::endcUlNrLowQualThresh. - Values 0 to 1600 are only recommended for operators for temporary testing purposes.';
        }
    }

    augment "/me3gpp:ManagedElement/gnbcucp3gpp:GNBCUCPFunction" {

        list QciProfileEndcConfigExt {
            description
                "Reference to QciProfileEndcConfigExt MO instance.
                The system will automatically create QciProfileEndcConfigExt when GNBCUCPFunction is created";
            key id;
            uses top3gpp:Top_Grp;
            max-elements 1;
            // min-elements 1; // is not working with YANG implementation. The system will automatically create QciProfileEndcConfigExt when GNBCUCPFunction is created.
            container attributes {
                uses QciProfileEndcConfigExtGrp;
            }
            yexte:system-supplied-entries "id=1 initialUplinkConf=MCG";
        }
    }
}
