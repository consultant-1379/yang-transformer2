// Generated by eyang-preprocessor (1.22.0-48 2022-01-20 09:10:06 CET) on Jun 30, 2022, 8:31:35 AM
module ericsson-anrfunction-eutran-ue-cfg-vcucp {
    yang-version 1.1;
    namespace "urn:rdns:com:ericsson:oammodel:ericsson-anrfunction-eutran-ue-cfg-vcucp";
    prefix anrfunctioneutranuecfg;

    import _3gpp-common-managed-element {
        prefix "me3gpp";
    }
    import _3gpp-nr-nrm-gnbcucpfunction {
        prefix "gnbcucp3gpp";
    }
    import _3gpp-common-top {
        prefix "top3gpp";
    }
    import ericsson-yang-extensions {
        prefix "yexte";
    }
    import ericsson-anrfunction-vcucp {
        prefix "anrfunction";
    }
    import ericsson-anrfunction-eutran-vcucp {
        prefix "anrfunctioneutran";
    }

    organization
        "Ericsson AB";
    contact
        "Ericsson first line support via email";
    description
        "The module defines the AnrFunctionEUtranUeCfg data model for the Ericsson vCU-CP.

        Copyright (c) 2022 Ericsson AB. All rights reserved.";

    revision 2022-06-28 {
        description
            "Removed module-status preliminary.
             Removed preliminary status from AnrFunctionEUtranUeCfg.";
        yexte:version 0;
        yexte:release 2;
        yexte:correction 0;
        reference
            "RFC 7950: The YANG 1.1 Data Modeling Language";
    }

    revision 2022-03-14 {
        description
            "Initial version of the AnrFunctionEUtranUeCfg model.";
        yexte:version 0;
        yexte:release 1;
        yexte:correction 0;
        reference
            "RFC 7950: The YANG 1.1 Data Modeling Language";
    }

    grouping AnrFunctionEUtranUeCfgGrp {
        description
            "Represents the AnrFunctionEUtranUeCfg IOC.";

        leaf ecgiDuringEpsFbEnabled {
            description
              "Whether ECGI measurement during EPS fallback is enabled.

              ECGI measurement is triggered when B1 measurement report is received "+
              "and E-UTRAN cell PCI is not known.

              Only applicable for EPS fallback of non-emergency voice call.";
            type boolean;
            default true;
        }
    }

    augment "/me3gpp:ManagedElement/gnbcucp3gpp:GNBCUCPFunction/anrfunction:AnrFunction/anrfunctioneutran:AnrFunctionEUtran" {
        list AnrFunctionEUtranUeCfg {
            description
              "UE configuration of E-UTRAN ANR functions.

              The RDN of this MO must always be AnrFunctionEUtranUeCfg=Base.";
            key id;
            max-elements 1;
            uses top3gpp:Top_Grp {
                refine id {
                    must '. = "Base"' {
                        error-message
                          "The RDN of this MO must always be AnrFunctionEUtranUeCfg=Base";
                    }
                }
            }
            container attributes {
                uses AnrFunctionEUtranUeCfgGrp;
            }
        }
    }
}
