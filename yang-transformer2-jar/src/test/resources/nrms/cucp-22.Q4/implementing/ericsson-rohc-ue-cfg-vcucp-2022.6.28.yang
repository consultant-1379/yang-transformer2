// Generated by eyang-preprocessor (1.22.0-48 2022-01-20 09:10:06 CET) on Jun 30, 2022, 8:31:43 AM
module ericsson-rohc-ue-cfg-vcucp {
    yang-version 1.1;
    namespace urn:rdns:com:ericsson:oammodel:ericsson-rohc-ue-cfg-vcucp;
    prefix rohcuecfgvcucp;

    import tailf-common {
        prefix tailf;
    }
    import _3gpp-common-managed-element {
        prefix "me3gpp";
    }
    import _3gpp-nr-nrm-gnbcucpfunction {
        prefix "gnbcucp3gpp";
    }
    import ericsson-uecc-vcucp {
        prefix "ueccvcucp";
    }
    import ericsson-rohc-vcucp {
        prefix "rohcvcucp";
    }
    import _3gpp-common-top {
        prefix "top3gpp";
    }
    import ericsson-yang-extensions {
        prefix "yexte";
    }
    import ericsson-common-types-vcucp {
        prefix commontypes;
    }

    organization
      "Ericsson AB";
    contact
      "Ericsson first line support via email";
    description
      "The module defines the RohcUeCfg data model for the Ericsson vCU-CP.

       Copyright (c) 2022 Ericsson AB. All rights reserved.";

    revision 2022-06-28 {
        description
            "Removed module-status preliminary.
             Removed preliminary status from RohcUeCfg.";
        yexte:version 0;
        yexte:release 2;
        yexte:correction 0;
        reference
            "RFC 7950: The YANG 1.1 Data Modeling Language";
    }

    revision 2022-03-14 {
        description
            "Initial version of the RohcUeCfg model.";
        yexte:version 0;
        yexte:release 1;
        yexte:correction 0;
        reference
            "RFC 7950: The YANG 1.1 Data Modeling Language";
    }

    grouping RohcUeCfgGrp {
        description
          "Represents the RohcUeCfg IOC.";

        leaf-list prefUeGroupList {
            max-elements 8;
            ordered-by user;
            description
                "Preference UE group list.

                List of preference UE group identifiers.";
            type int32 {
                range "1..255";
            }
            yexte:dependencies
                "Combinations of pair of preference UE group identifier in "+
                "prefUeGroupList and UE group identifier in ueGroupList must be "+
                "unique among RohcUeCfg instances.

                Combination of a UE group identifier in ueGroupList and empty "+
                "prefUeGroupList must be unique among RohcUeCfg instances.

                Combination of a preference UE group identifier in prefUeGroupList "+
                "and empty ueGroupList must be unique among RohcUeCfg instances.";
            yexte:takes-effect
                "New connection";

            must "count(../../../RohcUeCfg/attributes[prefUeGroupList = current() and
                    count(ueGroupList) = 0]) = 1" {
                error-message
                    "Exactly one RohcUeCfg instance under an Rohc must combine a "+
                    "specific preference UE group identifier in attribute "+
                    "prefUeGroupList with an empty ueGroupList.";
            }
            tailf:info 'Takes effect: New connection, Dependencies: Combinations of pair of preference UE group identifier in prefUeGroupList and UE group identifier in ueGroupList must be unique among RohcUeCfg instances.

                Combination of a UE group identifier in ueGroupList and empty prefUeGroupList must be unique among RohcUeCfg instances.

                Combination of a preference UE group identifier in prefUeGroupList and empty ueGroupList must be unique among RohcUeCfg instances, Preference UE group list. List of preference UE group identifiers.';
        }

        leaf-list rohc5qiList {
            max-elements 16;
            ordered-by user;
            description
                "Rohc5qi list.

                List of 5QIs for which Robust Header Compression is enabled.";
            type int32 {
                range "1|65|66";
            }
            default 1;
            yexte:takes-effect
                "New connection";
            tailf:info 'Takes effect: New connection, Rohc5qi list. List of 5QIs for which Robust Header Compression is enabled.';
        }

        leaf-list ueConfGroupList {
            max-elements 32;
            ordered-by user;
            description
                "UE configuration group list.

                List of UE configuration group identifiers.

                Which UE configuration group type that is applied is defined by "
                + "attribute ueConfGroupType in parent MO class instance.";
            type int32 {
                range "1..255";
            }
            yexte:dependencies
                "A given UE configuration group identifier can be defined in only one "+
                "ueConfGroupList among RohcUeCfg instances.";
            yexte:takes-effect
                "New connection";

            must "count(../../../RohcUeCfg/attributes[ueConfGroupList = current()]) = 1" {
                error-message
                    "Only one RohcUeCfg instance under an Rohc can include a specific "+
                    "ueConfGroupId in attribute ueConfGroupList.";
            }
            tailf:info 'Takes effect: New connection, Dependencies: A given UE configuration group identifier can be defined in only one ueConfGroupList among RohcUeCfg instances, UE configuration group list. List of UE configuration group identifiers. Which UE configuration group type that is applied is defined by attribute ueConfGroupType in parent MO class instance.';
        }

        leaf-list ueGroupList {
            max-elements 16;
            ordered-by user;
            description
                "UE group list.

                List of UE group identifiers.";
            type int32 {
                range "1..255";
            }
            yexte:dependencies
                "Combinations of pair of preference UE group identifier in "+
                "prefUeGroupList and UE group identifier in ueGroupList must be "+
                "unique among RohcUeCfg instances.

                Combination of a UE group identifier in ueGroupList and empty "+
                "prefUeGroupList must be unique among RohcUeCfg instances.

                Combination of a preference UE group identifier in prefUeGroupList "+
                "and empty ueGroupList must be unique among RohcUeCfg instances.";
            yexte:takes-effect
                "New connection";

            must "count(../prefUeGroupList) &gt; 0 or
                  count(../../../RohcUeCfg/attributes[ueGroupList = current() and
                    count(prefUeGroupList) = 0]) &lt;= 1" {
                error-message
                    "Only one RohcUeCfg instance under an Rohc can combine a specific "+
                    "UE group identifier in attribute ueGroupList with an "+
                    "empty prefUeGroupList.";
            }
            tailf:info 'Takes effect: New connection, Dependencies: Combinations of pair of preference UE group identifier in prefUeGroupList and UE group identifier in ueGroupList must be unique among RohcUeCfg instances.

                Combination of a UE group identifier in ueGroupList and empty prefUeGroupList must be unique among RohcUeCfg instances.

                Combination of a preference UE group identifier in prefUeGroupList and empty ueGroupList must be unique among RohcUeCfg instances, UE group list. List of UE group identifiers.';
        }
    }

    augment "/me3gpp:ManagedElement/gnbcucp3gpp:GNBCUCPFunction/ueccvcucp:UeCC/rohcvcucp:Rohc" {
        list RohcUeCfg {
            key id;
            max-elements 8;
            description
                "Configuration of Robust Header Compression feature for UE "+
                "groups.

                MO instance RohcUeCfg=Base is created automatically when "+
                "parent MO is created, unless created manually in the same "+
                "transaction as parent MO.

                Each UE configuration group identifier can only be defined in "+
                "one ueConfigGroupList attribute among RohcUeCfg MOs contained "+
                "under the parent Rohc MO instance.

                Any combination of one UE group identifier in ueGroupList "+
                "attribute and one preference UE group identifier in "+
                "prefUeGroupList attribute must be unique among RohcUeCfg MOs "+
                "contained under parent Rohc MO instance.

                Attributes prefUeGroupList, ueGroupList, and ueConfGroupList "+
                "must be empty in instance RohcUeCfg=Base but cannot all be "+
                "empty in other instances of RohcUeCfg.";
            yexte:precondition
                "RohcUeCfg=Base instance can only be created in the same "+
                "transaction as parent MO and must not be deleted unless parent "+
                "MO is deleted. Other instances can be created and deleted "+
                "manually.
                Maximum 7 RohcUeCfg instances, with RDN different from Base, "+
                "can be created.";
            uses top3gpp:Top_Grp;
            container attributes {
                uses RohcUeCfgGrp;
                uses commontypes:UserLabelGrp;
            }

            must "count(../RohcUeCfg) &lt; 8 or
                    count(../RohcUeCfg[id = 'Base']) = 1" {
                error-message
                    "Maximum 7 RohcUeCfg instances under an Rohc can be created "+
                    "with RDN different from Base.";
            }

            must "count(../RohcUeCfg/attributes
                    [ueGroupList = current()/attributes/ueGroupList and
                    prefUeGroupList = current()/attributes/prefUeGroupList]) &lt;= 1" {
                error-message
                    "The combinations of pair of UE group identifier in ueGroupList "+
                    "and preference UE group identifier in prefUeGroupList must be "+
                    "unique among RohcUeCfg under an Rohc.";
            }

            must "id != 'Base' or (count(attributes/prefUeGroupList) = 0 and
                    count(attributes/ueGroupList) = 0 and
                    count(attributes/ueConfGroupList) = 0)" {
                error-message
                    "prefUeGroupList, ueGroupList and ueConfGroupList "+
                    "must be empty in the RohcUeCfg=Base instance.";
            }

            must "id = 'Base' or not(count(attributes/prefUeGroupList) = 0 and
                    count(attributes/ueGroupList) = 0 and
                    count(attributes/ueConfGroupList) = 0)" {
                error-message
                    "prefUeGroupList, ueGroupList and ueConfGroupList "+
                    "can only be empty in the RohcUeCfg=Base instance.";
            }
            tailf:info 'Precondition: RohcUeCfg=Base instance can only be created in the same transaction as parent MO and must not be deleted unless parent MO is deleted. Other instances can be created and deleted manually.
                Maximum 7 RohcUeCfg instances, with RDN different from Base, can be created, Configuration of Robust Header Compression feature for UE groups. MO instance RohcUeCfg=Base is created automatically when parent MO is created, unless created manually in the same transaction as parent MO. Each UE configuration group identifier can only be defined in one ueConfigGroupList attribute among RohcUeCfg MOs contained under the parent Rohc MO instance. Any combination of one UE group identifier in ueGroupList attribute and one preference UE group identifier in prefUeGroupList attribute must be unique among RohcUeCfg MOs contained under parent Rohc MO instance. Attributes prefUeGroupList, ueGroupList, and ueConfGroupList must be empty in instance RohcUeCfg=Base but cannot all be empty in other instances of RohcUeCfg.';
        }
    }
}
