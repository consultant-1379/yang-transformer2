// Generated by eyang-preprocessor (1.22.0-48 2022-01-20 09:10:06 CET) on Jun 30, 2022, 8:31:44 AM
module ericsson-sctp-profile-vcu {
    yang-version 1.1;
    namespace urn:rdns:com:ericsson:oammodel:ericsson-sctp-profile-vcu;
    prefix sctpprofile;

    import tailf-common {
        prefix tailf;
    }
    import ericsson-transport-types-vcu {
        prefix transtypes;
    }
    import ericsson-yang-extensions {
        prefix yexte;
    }

    organization
        "Ericsson AB";
    contact
        "Ericsson first line support via email";
    description
        "The module defines the abstract SctpProfile data model for the Ericsson vCU.

         Copyright (c) 2021-2022 Ericsson AB. All rights reserved.";

    revision 2022-06-28 {
        description
            "Removed module-status preliminary.";
        yexte:version 1;
        yexte:release 1;
        yexte:correction 0;
        reference
            "RFC 7950: The YANG 1.1 Data Modeling Language";
    }

    revision 2021-01-26 {
        description
            "Removed attribute maxSctpPduSize.";
        yexte:version 1;
        yexte:release 0;
        yexte:correction 0;
        reference
            "RFC 7950: The YANG 1.1 Data Modeling Language";
    }

    revision 2021-01-07 {
        description
            "Initial revision.";
        yexte:version 0;
        yexte:release 1;
        yexte:correction 0;
        reference
            "RFC 7950: The YANG 1.1 Data Modeling Language";
    }

    typedef AlphaIndex {
        description "RTO alpha index.";
        type enumeration {
            enum ALPHA_1_2ND {
                value 1;
                description "RTO.Alpha=1/2.";
            }
            enum ALPHA_1_4TH {
                value 2;
                description "RTO.Alpha=1/4.";
            }
            enum ALPHA_1_8TH {
                value 3;
                description "RTO.Alpha=1/8.";
            }
            enum ALPHA_1_16TH {
                value 4;
                description "RTO.Alpha=1/16.";
            }
        }
    }

    typedef BetaIndex {
        description "RTO beta index.";
        type enumeration {
            enum BETA_1_2ND {
                value 1;
                description "RTO.Beta=1/2.";
            }
            enum BETA_1_4TH {
                value 2;
                description "RTO.Beta=1/4.";
            }
            enum BETA_1_8TH {
                value 3;
                description "RTO.Beta=1/8.";
            }
            enum BETA_1_16TH {
                value 4;
                description "RTO.Beta=1/16.";
            }
        }
    }

    grouping SctpProfileGrp {
        description
            "The SctpProfile defines the configuration that controls the behaviour of an SctpEndpoint.

             The SctpProfile can be shared by one or more SctpEndpoint MOs.";

        leaf alphaIndex {
            description "RTO alpha index.";
            type AlphaIndex;
            default "ALPHA_1_8TH";
            config false;
            reference "RFC 4960, section 6.3.1";
        }

        leaf assocMaxRtx {
            description "Association maximum number of retransmissions packets.";
            type uint8 {
                range "1..20";
            }
            default 20;
            config false;
            yexte:dependencies "primaryPathMaxRtx &lt;= pathMaxRtx &lt;= assocMaxRtx";
            must "../primaryPathMaxRtx &lt;= current() and ../pathMaxRtx &lt;= current()" {
                error-message "primaryPathMaxRtx &lt;= pathMaxRtx &lt;= assocMaxRtx";
            }
            reference "RFC 4960, section 6.3.1";
            tailf:info 'Dependencies: primaryPathMaxRtx &lt;= pathMaxRtx &lt;= assocMaxRtx, Association maximum number of retransmissions packets.';
        }

        leaf betaIndex {
            description "RTO beta index.";
            type BetaIndex;
            default "BETA_1_4TH";
            config false;
            reference "RFC 4960, section 6.3.1";
        }

        leaf bundlingActivated {
            description
                "States whether bundling is allowed for an endpoint.

                 True: An endpoint bundles chunks by including multiple chunks in one outbound SCTP packet.
                 False: Bundling is not used.";
            type boolean;
            default true;
            config false;
            reference "RFC 4960, section 6.10";
        }

        leaf bundlingAdaptiveActivated {
            description
                "States whether adaptive bundling is applied.
                 It is only applicable if bundlingActivated is set to true.
                 According to traffic condition, SCTP bundles chunks by including multiple chunks in one outbound SCTP packet.

                 True : Adaptive bundling is enabled.
                 False : Adaptive bundling is disabled.";
            type boolean;
            config false;
            yexte:initial-value true;
        }

        leaf bundlingTimer {
            description "Maximum allowed bundling delay.";
            type uint16 {
                range "0..1000";
            }
            default 0;
            units ms;
            config false;
        }

        leaf cookieLife {
            description
                "Valid cookie life.
                 A new value of the attribute does not apply to associations that are already established.";
            type uint8 {
                range "1..180";
            }
            default 60;
            units s;
            config false;
            reference "RFC 4960, section 5.1.3";
        }

        leaf dscp {
            description "The DSCP value.";
            type uint8 {
                range "0..63";
            }
            default 40;
            config false;
        }

        leaf hbMaxBurst {
            description
                "HB.MaxBurst value.
                 A new value of the attribute does not apply to associations that are already established.";
            type uint32 {
                range "0..4";
            }
            default 1;
            config false;
            reference "RFC 4960, section 5.4";
        }

        leaf heartbeatActivated {
            description
                "States whether heartbeat is activated.

                 True: Activates heartbeats for SCTP endpoint.
                 False: Disables heartbeats for SCTP endpoint.";
            type boolean;
            default true;
            config false;
            reference "RFC 4960, section 8.3";
        }

        leaf heartbeatInterval {
            description "SCTP heartbeat interval.";
            type uint32 {
                range "10..1800000";
            }
            default 2000;
            units ms;
            config false;
            reference "RFC 4960, section 8.3";
        }

        leaf incCookieLife {
            description
                "Allowed increment of parameter valid.Cookie.Life in local node.

                 Applied when an increase of the parameter is requested from the remote node.
                 A new value of the attribute does not apply to associations that are already established.";
            type uint8 {
                range "0..180";
            }
            default 30;
            units s;
            config false;
            reference "RFC 4960, section 3.3.2.1";
        }

        leaf initARWnd {
            description
                "Value of the initial advertised receiver window credit (a_rwnd sent in the INIT message).

                 If the value of this attribute is increased, it applies to both existing and new associations. If the value is decreased, it does not apply to associations that are already established.";
            type uint32 {
                range "1500..1048576";
            }
            default 16384;
            units bytes;
            config false;
        }

        leaf initialHeartbeatInterval {
            description
                "Period for acceptance of a heartbeat acknowledge message during path probing.

                 It limits the intensity of heartbeats for path probing after association start-up.";
            type uint32 {
                range "10..1800000";
            }
            default 500;
            units ms;
            config false;
        }

        leaf initRto {
            description
                "RTO initial value.

                 A new value of the attribute does not apply to associations that are already established.";
            type uint32 {
                range "10..120000";
            }
            default 200;
            units ms;
            config false;
            yexte:dependencies "minRto &lt;= initRto &lt;= maxRto";
            must "current() &gt;= ../minRto and current() &lt;= ../maxRto" {
                error-message "minRto &lt;= initRto &lt;= maxRto";
            }
            reference "RFC 4960, section 6.3.1";
            tailf:info 'Dependencies: minRto &lt;= initRto &lt;= maxRto, RTO initial value. A new value of the attribute does not apply to associations that are already established.';
        }

        leaf maxActivateThr {
            description
                "Maximum number of consecutive successful heartbeats.

                 It must be sent over the data transfer path (DTP) before switchback can be performed.";
            type uint16 {
                range "1..65535";
            }
            default 65535;
            config false;
            yexte:dependencies "minActivateThr &lt;= maxActivateThr";
            must "current() &gt;= ../minActivateThr" {
                error-message "minActivateThr &lt;= maxActivateThr";
            }
            tailf:info 'Dependencies: minActivateThr &lt;= maxActivateThr, Maximum number of consecutive successful heartbeats. It must be sent over the data transfer path (DTP) before switchback can be performed.';
        }

        leaf maxBurst {
            description
                "Maximum number of consecutive successful heartbeats.

                 It must be sent over the data transfer path (DTP) before switchback can be performed.";
            type uint16 {
                range "1..16384";
            }
            default 4;
            config false;
            reference "RFC 4960, section 6.1";
        }

        leaf maxInitRt {
            description
                "Maximum number of retransmissions allowed for both INIT and COOKIE_ECHO chunks.

                 A new value of the attribute does not apply to associations that are already established.";
            type uint8 {
                range "1..16";
            }
            default 8;
            config false;
        }

        leaf maxInStreams {
            description
                "Maximum number of inbound streams to negotiate for an association.

                 A change to this attribute does not affect the existing associations.
                 To apply a new value, the endpoint must be re-created.";
            type uint16 {
                range "1..16384";
            }
            default 2;
            config false;
            reference "RFC 4960, section 3.3.2";
        }

        leaf maxOutStreams {
            description
                "Maximum number of outbound streams to negotiate for an association.

                 A change to this attribute does not affect the existing associations.
                 To apply a new value, the endpoint must be re-created.";
            type uint16 {
                range "1..16384";
            }
            default 2;
            config false;
            reference "RFC 4960, section 3.3.2";
        }

        leaf maxRto {
            description "Maximum RTO.";
            type uint32 {
                range "11..120000";
            }
            default 400;
            units ms;
            config false;
            yexte:dependencies "minRto &lt;= initRto &lt;= maxRto";
            must "current() &gt;= ../initRto and current() &gt;= ../minRto" {
                error-message "minRto &lt;= initRto &lt;= maxRto";
            }
            reference "RFC 4960, section 6.3.1";
            tailf:info 'Dependencies: minRto &lt;= initRto &lt;= maxRto, Maximum RTO.';
        }

        leaf maxShutdownRt {
            description
                "Maximum number of retransmissions during the shutdown phase of an association.";
            type uint8 {
                range "1..20";
            }
            default 5;
            config false;
        }

        leaf minActivateThr {
            description
                "Minimum and initial number of consecutive successful heartbeats before switchback can be performed.

                 The minimum and initial value for the number of consecutive successful heartbeats that must be sent over the preferred primary path before switchback can be performed.";
            type uint16 {
                range "1..65535";
            }
            default 1;
            config false;
            yexte:dependencies "minActivateThr &lt;= maxActivateThr";
            must "current() &lt;= ../maxActivateThr" {
                error-message "minActivateThr &lt;= maxActivateThr";
            }
            tailf:info 'Dependencies: minActivateThr &lt;= maxActivateThr, Minimum and initial number of consecutive successful heartbeats before switchback can be performed. The minimum and initial value for the number of consecutive successful heartbeats that must be sent over the preferred primary path before switchback can be performed.';
        }

        leaf minRto {
            description "Minimum RTO.";
            type uint32 {
                range "10..5000";
            }
            default 100;
            units ms;
            config false;
            yexte:dependencies "minRto &lt;= initRto &lt;= maxRto";
            must "current() &lt;= ../initRto and current() &lt;= ../maxRto" {
                error-message "minRto &lt;= initRto &lt;= maxRto";
            }
            reference "RFC 4960, section 6.3.1";
            tailf:info 'Dependencies: minRto &lt;= initRto &lt;= maxRto, Minimum RTO.';
        }

        leaf noSwitchback {
            description
                "Recovery of the failed Primary Path does not invoke change of the (current) data transfer path.

                 True: No switchback.
                 False: Switchback.";
            type boolean;
            default false;
            config false;
        }

        leaf pathMaxRtx {
            description
                "Maximum number of consecutive retransmissions on an IP path.

                 An IP path is defined by the pair of local and remote IP addresses.";
            type uint8 {
                range "1..20";
            }
            default 10;
            config false;
            yexte:dependencies "primaryPathMaxRtx &lt;= pathMaxRtx &lt;= assocMaxRtx";
            must "../primaryPathMaxRtx &lt;= current() and current() &lt;= ../assocMaxRtx" {
                error-message "primaryPathMaxRtx &lt;= pathMaxRtx &lt;= assocMaxRtx";
            }
            tailf:info 'Dependencies: primaryPathMaxRtx &lt;= pathMaxRtx &lt;= assocMaxRtx, Maximum number of consecutive retransmissions on an IP path. An IP path is defined by the pair of local and remote IP addresses.';
        }

        leaf primaryPathAvoidance {
            description
                "Whether SCTP can avoid primary path usage when it didn't work for the latest transmission.

                 True: Enable functionality.
                 False: Disable functionality.";
            type boolean;
            default true;
            config false;
        }

        leaf primaryPathMaxRtx {
            description
                "Maximum value of the error counter of the current primary path before switchover.

                 In case of enabled Primary Path Avoidance(PPA), if the error counter of the primary path exceeds this value, SCTP chooses another current primary path.";
            type uint8 {
                range "0..20";
            }
            default 0;
            config false;
            yexte:dependencies "primaryPathMaxRtx &lt;= pathMaxRtx &lt;= assocMaxRtx";
            must "current() &lt;= ../pathMaxRtx and current() &lt;= ../assocMaxRtx" {
                error-message "primaryPathMaxRtx &lt;= pathMaxRtx &lt;= assocMaxRtx";
            }
            tailf:info 'Dependencies: primaryPathMaxRtx &lt;= pathMaxRtx &lt;= assocMaxRtx, Maximum value of the error counter of the current primary path before switchover. In case of enabled Primary Path Avoidance(PPA), if the error counter of the primary path exceeds this value, SCTP chooses another current primary path.';
        }

        leaf sackTimer {
            description
                "The time delay for sending the Selective Acknowledgement (SACK).

                 Time is measured from receiving the DATA chunk to sending the SACK chunk.";
            type uint16 {
                range "0..500";
            }
            default 10;
            units ms;
            config false;
        }

        leaf sctpProfileId {
            description
                "Identifies this SctpProfile MO instance.";
            type transtypes:ReferenceId;
            config false;
        }

        leaf thrTransmitBuffer {
            description
                "Threshold of the transmit buffer size.

                 Upon exceeding this threshold the user of SCTP will be asked to stop sending data.
                 This condition will persist until the occupancy of the transmit buffer drops below thrTransmitBufferCongCeased * thrTransmitBuffer.";
            type uint16 {
                range "1..2048";
            }
            default 48;
            units kB;
            config false;
            yexte:dependencies "thrTransmitBuffer &lt;= transmitBufferSize";
            must "current() &lt;= ../transmitBufferSize" {
                error-message "thrTransmitBuffer &lt;= transmitBufferSize";
            }
            tailf:info 'Dependencies: thrTransmitBuffer &lt;= transmitBufferSize, Threshold of the transmit buffer size. Upon exceeding this threshold the user of SCTP will be asked to stop sending data. This condition will persist until the occupancy of the transmit buffer drops below thrTransmitBufferCongCeased * thrTransmitBuffer.';
        }

        leaf thrTransmitBufferCongCeased {
            description
                "Size of threshold of the transmit buffer in percentage when congestion cease indication is sent.

                 See also description of attribute thrTransmitBuffer.";
            type uint8 {
                range "1..100";
            }
            default 85;
            units %;
            config false;
        }

        leaf transmitBufferSize {
            description
                "Size of the buffer used for storing data pending to be sent or retransmitted in an association.";
            type uint16 {
                range "1..2048";
            }
            default 64;
            units kB;
            config false;
            yexte:dependencies "thrTransmitBuffer &lt;= transmitBufferSize";
            must "../thrTransmitBuffer &lt;= current()" {
                error-message "thrTransmitBuffer &lt;= transmitBufferSize";
            }
            tailf:info 'Dependencies: thrTransmitBuffer &lt;= transmitBufferSize, Size of the buffer used for storing data pending to be sent or retransmitted in an association.';
        }

        leaf userLabel {
            description "Label for free use.";
            type string;
            yexte:restricted;
        }
    }
}
