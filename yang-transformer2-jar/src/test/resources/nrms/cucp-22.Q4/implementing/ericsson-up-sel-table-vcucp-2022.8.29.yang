// Generated by eyang-preprocessor (1.22.0-48 2022-01-20 09:10:06 CET) on Sep 4, 2022, 12:23:59 PM
module ericsson-up-sel-table-vcucp {
    yang-version 1.1;
    namespace urn:rdns:com:ericsson:oammodel:ericsson-up-sel-table-vcucp;
    prefix upseltablevcucp;

    import tailf-common {
        prefix tailf;
    }
    import _3gpp-common-managed-element {
        prefix me3gpp;
    }
    import _3gpp-nr-nrm-gnbcucpfunction {
        prefix gnbcucp3gpp;
    }
    import _3gpp-common-top {
        prefix top3gpp;
    }
    import ericsson-yang-extensions {
        prefix yexte;
    }
    import ericsson-up-selection-vcucp {
        prefix upselectionvcucp;
    }

    organization
      "Ericsson AB";
    contact
      "Ericsson first line support via email";
    description
      "The module defines the UPSelTable data model for the Ericsson vCU-CP.

       Copyright (c) 2022 Ericsson AB. All rights reserved.";

    revision 2022-08-29 {
        description
          "Removed module-status preliminary.
           Removed preliminary status from:
            - list UPSelTable";
        yexte:version 0;
        yexte:release 2;
        yexte:correction 0;
        reference
          "RFC 7950: The YANG 1.1 Data Modeling Language";
    }

    revision 2022-04-20 {
        description
          "Initial version of the UPSelTable model";
        yexte:version 0;
        yexte:release 1;
        yexte:correction 0;
        reference
          "RFC 7950: The YANG 1.1 Data Modeling Language";
    }

    augment "/me3gpp:ManagedElement/gnbcucp3gpp:GNBCUCPFunction/upselectionvcucp:UPSelection" {
        list UPSelTable {
            description
              "Container class for User Plane Selection Entries.

               MO instance UPSelTable=1 is created automatically when
               parent MO is created, unless created manually in the
               same transaction as parent MO.

               The RDN of this MO must always be UPSelTable=1.";
            key id;
            max-elements 1;
            uses top3gpp:Top_Grp {
                refine id {
                    must '. = "1"' {
                        error-message
                          "The RDN of this MO must always be UPSelTable=1";
                    }
                }
            }
            yexte:precondition
                "UPSelTable=1 MO instance must not be deleted unless parent MO is deleted.";
            tailf:info 'Precondition: UPSelTable=1 MO instance must not be deleted unless parent MO is deleted, Container class for User Plane Selection Entries. MO instance UPSelTable=1 is created automatically when parent MO is created, unless created manually in the same transaction as parent MO. The RDN of this MO must always be UPSelTable=1.';
        }
    }
}
