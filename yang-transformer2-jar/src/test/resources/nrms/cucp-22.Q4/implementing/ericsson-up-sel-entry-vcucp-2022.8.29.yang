// Generated by eyang-preprocessor (1.22.0-48 2022-01-20 09:10:06 CET) on Sep 4, 2022, 12:23:59 PM
module ericsson-up-sel-entry-vcucp {
    yang-version 1.1;
    namespace urn:rdns:com:ericsson:oammodel:ericsson-up-sel-entry-vcucp;
    prefix upselentryvcucp;

    import tailf-common {
        prefix tailf;
    }
    import _3gpp-common-managed-element {
        prefix me3gpp;
    }
    import _3gpp-nr-nrm-gnbcucpfunction {
        prefix gnbcucp3gpp;
    }
    import _3gpp-common-top {
        prefix top3gpp;
    }
    import _3gpp-common-yang-types {
        prefix types3gpp;
    }
    import ericsson-yang-extensions {
        prefix yexte;
    }
    import ericsson-up-selection-vcucp {
        prefix upselectionvcucp;
    }
    import ericsson-up-sel-table-vcucp {
        prefix upseltablevcucp;
    }

    organization
      "Ericsson AB";
    contact
      "Ericsson first line support via email";
    description
      "The module defines the UPSelEntry data model for the Ericsson vCU-CP.

       Copyright (c) 2022 Ericsson AB. All rights reserved.";

    revision 2022-08-29 {
        description
          "Removed module-status preliminary.
           Removed preliminary status from:
            - list UPSelEntry
            - list plmnIdList
            - leaf selPriority";
        yexte:version 0;
        yexte:release 2;
        yexte:correction 0;
        reference
          "RFC 7950: The YANG 1.1 Data Modeling Language";
    }

    revision 2022-07-01 {
        description
          "Must rule correction.";
        yexte:version 0;
        yexte:release 1;
        yexte:correction 1;
        reference
          "RFC 7950: The YANG 1.1 Data Modeling Language";
    }

    revision 2022-02-11 {
        description
          "Initial version of the UPSelEntry model";
        yexte:version 0;
        yexte:release 1;
        yexte:correction 0;
        reference
          "RFC 7950: The YANG 1.1 Data Modeling Language";
    }

    grouping UPSelEntryGrp {
        description
          "Represents the UPSelEntry IOC";
        list plmnIdList {
            key "mcc mnc";
            min-elements 1;
            max-elements 12;
            description
              "List of PLMNs for UPSelEntryGrp.

              Initial value set to GNBCUCPFunction::pLMNId in automatically created instance UPSelEntry=Default.

               PLMN ID consists of MobileCountryCode (MCC, three digits) and "
            + "MobileNetworkCode (MNC, two or three digits).";
            uses types3gpp:PLMNId;
            reference
              "3GPP TS 28.541";
            yexte:dependencies
                "At least one UPSelEntry instance must be configured with PLMN ID matching GNBCUCPFunction::pLMNId.

                A PLMN ID can not belong to more than one UPSelEntry instance that reference the same UPDomain instance.";
            yexte:takes-effect
                "New connection";
            tailf:info 'Takes effect: New connection, Dependencies: At least one UPSelEntry instance must be configured with PLMN ID matching GNBCUCPFunction::pLMNId.

                A PLMN ID can not belong to more than one UPSelEntry instance that reference the same UPDomain instance, List of PLMNs for UPSelEntryGrp. Initial value set to GNBCUCPFunction::pLMNId in automatically created instance UPSelEntry=Default. PLMN ID consists of MobileCountryCode (MCC, three digits) and MobileNetworkCode (MNC, two or three digits).';
        }

        leaf selPriority {
            description
              "Defines selection priority for UPSelEntry.

              Initial value set to '0' in automatically created instance UPSelEntry=Default.

              Higher value represents higher priority.";
            type int32 {
                range "0..65535";
            }
            mandatory true;
            yexte:dependencies
                "The selPriority must be unique among UPSelEntry MO instances.

                Value '0' is only allowed in UPSelEntry=Default instance";
            yexte:takes-effect
                "New connection";
            tailf:info "Takes effect: New connection, Dependencies: The selPriority must be unique among UPSelEntry MO instances.

                Value '0' is only allowed in UPSelEntry=Default instance, Defines selection priority for UPSelEntry. Initial value set to '0' in automatically created instance UPSelEntry=Default. Higher value represents higher priority.";
        }
    }

    augment "/me3gpp:ManagedElement/gnbcucp3gpp:GNBCUCPFunction/upselectionvcucp:UPSelection/upseltablevcucp:UPSelTable" {
        list UPSelEntry {
            description
              "Represents User Plane Selection Entry.

               MO instance UPSelEntry=Default is created "
            + "automatically when parent MO is created, unless created "
            + "manually in the same transaction as parent MO.";

            key id;
            unique "attributes/selPriority";
            uses top3gpp:Top_Grp;
            container attributes {
                uses UPSelEntryGrp;
            }
            must "./id = 'Default' or not( ./attributes/selPriority = 0)" {
                error-message
                  "selPriority value '0' is only allowed in the Default configuration instance.";
            }
            must "count(../UPSelEntry/attributes[(plmnIdList/mcc = ../../../../gnbcucp3gpp:attributes/gnbcucp3gpp:pLMNId/gnbcucp3gpp:mcc) and (plmnIdList/mnc = ../../../../gnbcucp3gpp:attributes/gnbcucp3gpp:pLMNId/gnbcucp3gpp:mnc)]) > 0" {
                error-message
                  "At least one UPSelEntry instance must be configured with PLMN ID matching GNBCUCPFunction::pLMNId.";
            }
            yexte:precondition
                "UPSelEntry=Default MO instance can only be created
                in the same transaction as parent MO and must not be deleted
                unless parent MO is deleted. Other instances can be created
                and deleted manually.";
            tailf:info 'Precondition: UPSelEntry=Default MO instance can only be created
                in the same transaction as parent MO and must not be deleted
                unless parent MO is deleted. Other instances can be created
                and deleted manually, Represents User Plane Selection Entry. MO instance UPSelEntry=Default is created automatically when parent MO is created, unless created manually in the same transaction as parent MO.';
        }
    }
}
