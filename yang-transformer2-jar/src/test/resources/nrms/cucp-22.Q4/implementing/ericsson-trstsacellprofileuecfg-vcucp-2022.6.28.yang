// Generated by eyang-preprocessor (1.22.0-48 2022-01-20 09:10:06 CET) on Jun 30, 2022, 8:31:44 AM
module ericsson-trstsacellprofileuecfg-vcucp {
    yang-version 1.1;
    namespace "urn:rdns:com:ericsson:oammodel:ericsson-trstsacellprofileuecfg-vcucp";
    prefix trstsacellprofileuecfg;

    import tailf-common {
        prefix tailf;
    }
    import _3gpp-common-managed-element {
        prefix "me3gpp";
    }
    import _3gpp-nr-nrm-gnbcucpfunction {
        prefix "gnbcucp3gpp";
    }
    import _3gpp-common-top {
        prefix "top3gpp";
    }
    import ericsson-yang-extensions {
        prefix "yexte";
    }
    import ericsson-common-types-vcucp {
        prefix "commontypes";
    }
    import ericsson-trafficsteering-vcucp {
        prefix "trafficsteering";
    }
    import ericsson-trstsacellprofile-vcucp {
        prefix "trstsacellprofile";
    }

    organization
      "Ericsson AB";
    contact
      "Ericsson first line support via email";
    description
      "The module defines the TrStSaCellProfileUeCfg data model for the Ericsson vCU-CP.

       Copyright (c) 2021-2022 Ericsson AB. All rights reserved.";

    revision 2022-06-28 {
        description
            "Removed module-status preliminary.
             Removed preliminary status from TrStSaCellProfileUeCfg.
             Removed preliminary status from actionAtRelease, capAwarePCellSelEnabled,
               criterionBetterUeConfig, rsrpPCellCandidate and t320.";
        yexte:version 0;
        yexte:release 3;
        yexte:correction 0;
        reference
            "RFC 7950: The YANG 1.1 Data Modeling Language";
    }

    revision 2022-03-14 {
        description
          "Updated description, max-elements and precondition for TrStSaCellProfileUeCfg.
           Added rule for number of instances that could be created.
           Removed rule where TrStSaCellProfileUeCfg=Base.
           Added the userLabel attribute.";
        yexte:version 0;
        yexte:release 2;
        yexte:correction 0;
        reference
          "RFC 7950: The YANG 1.1 Data Modeling Language";
    }

    revision 2021-11-05 {
        description
          "Initial version of the TrStSaCellProfileUeCfg model.";
        yexte:version 0;
        yexte:release 1;
        yexte:correction 0;
        reference
          "RFC 7950: The YANG 1.1 Data Modeling Language";
    }

    typedef ActionAtRelease {
        description
            "Traffic steering action at UE release.";

        type enumeration {
            enum DISABLED {
                value 0;
                description
                    "Traffic steering at release is disabled.";
            }

            enum CA_CONF {
                value 1;
                description
                  "CRP traffic steering at RRC release based on current carrier "+
                  "aggregation configuration.

                   CRP is set in RRCRelease message as follows:
                   - Current PCell frequency: 7
                   - Current SCell frequencies: 6
                   - Remaining NR cell frequencies: 5
                   - E-UTRAN frequencies: 4, 3, 2, 1, 0, based on "+
                  "EUtranFreqRelation::cellReselectionPriority

                   To enable CRP traffic steering, as indicated by CA_CONF, "+
                  "TrStSaCellProfileUeCfg::capAwarePCellSelEnabled must be set to "+
                  "true.";
            }
        }
    }

    grouping TrStSaCellProfileUeCfgGrp {
        description
            "Represents the TrStSaCellProfileUeCfg IOC.";

        leaf actionAtRelease {
            description
                "Traffic steering action at UE release.";
            type ActionAtRelease;
            default DISABLED;
            yexte:takes-effect
                "Next usage.";
            tailf:info 'Takes effect: Next usage, Traffic steering action at UE release.';
        }

        leaf capAwarePCellSelEnabled {
            description
                "Whether capability-aware PCell selection is enabled for NR cell.";
            type boolean;
            default false;
            yexte:takes-effect
                "Next usage";
            tailf:info 'Takes effect: Next usage, Whether capability-aware PCell selection is enabled for NR cell.';
        }

        leaf criterionBetterUeConfig {
            description
                "Criterion for better UE configuration.

                Defines a better UE configuration candidate relative to the current "+
                "UE configuration. Expressed as percentage better estimated "+
                "throughput based on the configured bandwidth of respective UE "+
                "configuration.";
            type int32 {
                range "1..100";
            }
            default 100;
            units %;
            yexte:takes-effect
                "Next usage";
            tailf:info 'Takes effect: Next usage, Criterion for better UE configuration. Defines a better UE configuration candidate relative to the current UE configuration. Expressed as percentage better estimated throughput based on the configured bandwidth of respective UE configuration.';
        }

        container rsrpPCellCandidate {
            description
                "RSRP measurement report criteria that define minimum RSRP value for "+
                "NR PCell candidate.

                Used in capability-aware PCell selection function.";
            uses commontypes:ReportConfigA5NoThr1Rsrp;
            reference
                "3GPP TS 38.331";
            yexte:takes-effect
                "Next usage";
            tailf:info 'Takes effect: Next usage, RSRP measurement report criteria that define minimum RSRP value for NR PCell candidate. Used in capability-aware PCell selection function.';
        }

        leaf t320 {
            description
                "Validity time for cell reselection priority information provided by "+
                "dedicated signaling.

                Used by the UE within traffic steering functionality at UE release "+
                "when actionAtRelease is set to CA_CONF.";
            type int32 {
                range "5|10|20|30|60|120|180";
            }
            default 30;
            units minute;
            reference
                "3GPP TS 38.331";
        }
    }

    augment "/me3gpp:ManagedElement/gnbcucp3gpp:GNBCUCPFunction/trafficsteering:TrafficSteering/trstsacellprofile:TrStSaCellProfile" {
        list TrStSaCellProfileUeCfg {
            description
                "Traffic steering function for PCell and SCells in NR "+
                "Standalone, UE configuration group.

                Applicable to UEs that use this cell as PCell in NR "+
                "Standalone. Attributes are used on cell level.

                TrStSaCellProfileUeCfg=Base MO instance is created "+
                "automatically when parent MO is created, unless created "+
                "manually in the same transaction as parent MO.";
            key id;
            max-elements 32;
            uses top3gpp:Top_Grp;
            container attributes {
                uses TrStSaCellProfileUeCfgGrp;
                uses commontypes:UserLabelGrp;
            }
            yexte:precondition
                "TrStSaCellProfileUeCfg=Base MO instance can only be created in "+
                "the same transaction as parent MO and must not be deleted unless "+
                "parent MO is deleted. Other instances can be created and "+
                "deleted manually.

                Maximum 31 TrStSaCellProfileUeCfg instances, with RDN "+
                "different from Base, can be created.";

            must "count(../TrStSaCellProfileUeCfg) &lt; 32 or
                  count(../TrStSaCellProfileUeCfg/id[. = 'Base']) = 1" {
                error-message
                    "Maximum 31 TrStSaCellProfileUeCfg instances under an TrStSaCellProfile "+
                    "can be created with RDN different from Base.";
            }
            tailf:info 'Precondition: TrStSaCellProfileUeCfg=Base MO instance can only be created in the same transaction as parent MO and must not be deleted unless parent MO is deleted. Other instances can be created and deleted manually.

                Maximum 31 TrStSaCellProfileUeCfg instances, with RDN different from Base, can be created, Traffic steering function for PCell and SCells in NR Standalone, UE configuration group. Applicable to UEs that use this cell as PCell in NR Standalone. Attributes are used on cell level. TrStSaCellProfileUeCfg=Base MO instance is created automatically when parent MO is created, unless created manually in the same transaction as parent MO.';
        }
    }
}
