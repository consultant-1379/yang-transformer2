// Generated by eyang-preprocessor (1.22.0-48 2022-01-20 09:10:06 CET) on Jun 30, 2022, 8:31:35 AM
module ericsson-additional-plmn-info-vcucp {
    yang-version 1.1;
    namespace urn:rdns:com:ericsson:oammodel:ericsson-additional-plmn-info-vcucp;
    prefix additionalplmninfo;

    import tailf-common {
        prefix tailf;
    }
    import _3gpp-common-managed-element {
        prefix me3gpp;
    }
    import _3gpp-common-yang-types {
        prefix types3gpp;
    }
    import _3gpp-common-top {
        prefix top3gpp;
    }
    import _3gpp-nr-nrm-gnbcucpfunction {
        prefix gnbcucp3gpp;
    }
    import _3gpp-nr-nrm-nrcellcu {
        prefix nrcellcu3gpp;
    }
    import ericsson-yang-extensions {
        prefix yexte;
    }

    organization
        "Ericsson AB";
    contact
        "Ericsson first line support via email";
    description
        "The module defines the AdditionalPLMNInfo data model for the Ericsson vCU-CP.

        Copyright (c) 2021-2022 Ericsson AB. All rights reserved.";

    revision 2022-06-28 {
        description
            "Removed module-status preliminary.";
        yexte:version 0;
        yexte:release 2;
        yexte:correction 0;
        reference
            "RFC 7950: The YANG 1.1 Data Modeling Language";
    }

    revision 2021-04-29 {
        description
            "Initial version of the AdditionalPLMNInfo model.";
        yexte:version 0;
        yexte:release 1;
        yexte:correction 0;
        reference
            "RFC 7950: The YANG 1.1 Data Modeling Language";
    }

    grouping AdditionalPLMNInfoGrp {
        description "Represents the AdditionalPLMNInfo IOC.";

        leaf nRTAC {
            description "NR Tracking Area Code (TAC).";
            config false;
            type int32;
        }

        list pLMNIdList {
            description "List of supported PLMNs.";
            key "mcc mnc";
            min-elements 1;
            max-elements 12;
            config false;
            uses types3gpp:PLMNId;
            reference "3GPP TS 28.541";
        }
    }

    augment "/me3gpp:ManagedElement/gnbcucp3gpp:GNBCUCPFunction/nrcellcu3gpp:NRCellCU" {
        list AdditionalPLMNInfo {
            description
                "PLMN-related Information that can be additionally served by NR "+
                "cell.

                Created by the system when F1 interface is set up or "+
                "configuration is updated by GNBDUFunction.
                Deleted by the system when configuration is updated by "+
                "GNBDUFunction.

                The RDNs of these MOs are AdditionalPLMNInfo=1 to "+
                "AdditionalPLMNInfo=11.";
            key id;
            max-elements 11;
            uses top3gpp:Top_Grp;
            container attributes {
                uses AdditionalPLMNInfoGrp;
            }
            yexte:is-system-created;
            tailf:meta-data yexte:is-system-created;
        }
    }
}
