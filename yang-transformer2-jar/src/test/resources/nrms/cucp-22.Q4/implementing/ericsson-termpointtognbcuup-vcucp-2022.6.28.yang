// Generated by eyang-preprocessor (1.22.0-48 2022-01-20 09:10:06 CET) on Jun 30, 2022, 8:31:44 AM
module ericsson-termpointtognbcuup-vcucp {
    yang-version 1.1;
    namespace urn:rdns:com:ericsson:oammodel:ericsson-termpointtognbcuup-vcucp;
    prefix tptognbcuup;

    import tailf-common {
        prefix tailf;
    }
    import _3gpp-common-managed-element {
        prefix me3gpp;
    }
    import _3gpp-nr-nrm-gnbcucpfunction {
        prefix gnbcucp3gpp;
    }
    import _3gpp-common-top {
        prefix top3gpp;
    }
    import _3gpp-common-yang-types {
        prefix types3gpp;
    }
    import ericsson-yang-extensions {
        prefix yexte;
    }
    import ericsson-yang-types {
        prefix "typese";
    }
    import ietf-inet-types {
        prefix inet;
    }
    import ericsson-notifications {
        prefix notife;
    }

    organization
        "Ericsson AB";
    contact
        "Ericsson first line support via email";
    description
        "The module defines the TermPointToGNBCUUP data model for the Ericsson vCU-CP.

        Copyright (c) 2021-2022 Ericsson AB. All rights reserved.";

    revision 2022-06-28 {
        description
            "Removed module-status preliminary.";
        yexte:version 2;
        yexte:release 2;
        yexte:correction 0;
        reference
            "RFC 7950: The YANG 1.1 Data Modeling Language";
    }

    revision 2021-07-27 {
        description
            "Bug Fix, leaf-list state notifiable compatibility issue. Adds extension notife:notifiable-state-data false to availabilityStatus.";
        yexte:version 2;
        yexte:release 1;
        yexte:correction 0;
        reference
            "RFC 7950: The YANG 1.1 Data Modeling Language";
    }

    revision 2021-04-06 {
        description
            "Updated Ericsson MO description.";
        yexte:version 1;
        yexte:release 0;
        yexte:correction 1;
        reference
            "RFC 7950: The YANG 1.1 Data Modeling Language";
    }

    revision 2021-01-20 {
        description
            "Add extensions is-system-created.";
        yexte:version 1;
        yexte:release 0;
        yexte:correction 0;
        reference
            "RFC 7950: The YANG 1.1 Data Modeling Language";
    }

    revision 2021-01-11 {
        description
	    "Initial version of the TermPointToGNBCUUP model.";
        yexte:version 0;
        yexte:release 1;
        yexte:correction 0;
        reference
            "RFC 7950: The YANG 1.1 Data Modeling Language";
    }

    grouping TermPointToGNBCUUPGrp {
        description
            "Models an E1 link to a gNodeB-CU-UP.";
        reference "Ericsson documentation";

        leaf-list availabilityStatus {
            description
                "The availability status.

                It contains details about operationalState.";
            config false;
            notife:notifiable-state-data false;
            type typese:avail-status;
            reference
                "ITU-T Rec. X.731";
            tailf:meta-data notife:notifiable-state-data {
                tailf:meta-value false;
            }
        }

        leaf gNBCUUPId {
            description "Central Unit User Plane (CUUP) identity within gNodeB.";
            config false;
            type int64 {
                range "0..68719476735";
            }
            reference "3GPP TS 38.463";
        }

        leaf gNBCUUPName {
            description "Central Unit User Plane (CUUP) name.";
            config false;
            type string {
                length "1..150";
            }
            reference "3GPP TS 38.463";
        }

        leaf operationalState {
            description
                "Operational state of the Link E1 interface. Indicates
                whether the resource is installed and partially or fully operable
                (ENABLED) or the resource is not installed or not operable
                (DISABLED).";
            config false;
            type types3gpp:OperationalState;
            reference "ITU-T Rec. X.731";
        }

        leaf usedIpAddress {
            description
                "Destination address used in underlying connection.

                Contains address of latest successful E1 setup.
                IP address can be an IPv4 or an IPv6 address.";
            config false;
            type inet:ip-address-no-zone;
        }
    }

    augment "/me3gpp:ManagedElement/gnbcucp3gpp:GNBCUCPFunction" {

        list TermPointToGNBCUUP {
            description
                "Models an E1 link to a gNodeB-CU-UP.

                Created by the system when E1 link is set up.
                Deleted by the system at node restart.

                The RDN of this MO is TermPointToGNBCUUP=[Local Ip "+
                "Address]_[Remote Ip Address].";
            key id;
            uses top3gpp:Top_Grp;
            container attributes {
                uses TermPointToGNBCUUPGrp;
            }
            yexte:is-system-created;
            tailf:meta-data yexte:is-system-created;
        }
    }
}
