// Generated by eyang-preprocessor (1.22.0-48 2022-01-20 09:10:06 CET) on Jun 30, 2022, 8:31:35 AM
module ericsson-cucpredundancy-vcucp {
    yang-version 1.1;
    namespace urn:rdns:com:ericsson:oammodel:ericsson-cucpredundancy-vcucp;
    prefix cucpredundancyvcucp;

    import tailf-common {
        prefix tailf;
    }
    import _3gpp-common-managed-element {
        prefix me3gpp;
    }
    import _3gpp-nr-nrm-gnbcucpfunction {
        prefix gnbcucp3gpp;
    }
    import _3gpp-common-top {
        prefix top3gpp;
    }
    import ericsson-yang-extensions {
        prefix yexte;
    }

    organization
        "Ericsson AB";
    contact
        "Ericsson first line support via email";
    description
        "The module defines the CUCPRedundancy data model for the Ericsson vCU-CP.

        Copyright (c) 2022 Ericsson AB. All rights reserved.";

    revision 2022-06-28 {
        description
            "Removed module-status preliminary.";
        yexte:version 0;
        yexte:release 2;
        yexte:correction 0;
        reference
            "RFC 7950: The YANG 1.1 Data Modeling Language";
    }

    revision 2022-04-28 {
        description
            "Modify CUCPRedundancy MO description.";
        yexte:version 0;
        yexte:release 1;
        yexte:correction 1;
        reference
            "RFC 7950: The YANG 1.1 Data Modeling Language";
    }

    revision 2022-04-05 {
        description
            "Initial version of the CUCPRedundancy model.";
        yexte:version 0;
        yexte:release 1;
        yexte:correction 0;
        reference
            "RFC 7950: The YANG 1.1 Data Modeling Language";
    }

    typedef redundancy-type {
        description "Redundancy type.";

        type enumeration {
            enum LOCAL {
                value 1;
                description "geo-redundancy is not enabled";
            }
            enum GEO {
                value 2;
                description "local redundancy is not enabled";
            }
            enum BOTH {
                value 3;
                description "local and geo redundancy are enabled";
            }
        }
    }

    typedef redundancy-state {
        type enumeration {
            enum PASSIVE {
                value 1;
                description "The entity is in passive state standing by for later service";
            }
            enum ACTIVE {
                value 2;
                description "The entity is in active state providing services";
            }
        }
        description "Redundancy state of an entity.";
    }

    typedef redundancy-role {
        type enumeration {
            enum MAIN {
                value 1;
                description "Redundancy role is main which can support both local and geo redundancy";
            }
            enum GEO-REDUNDANT {
                value 2;
                description "Redundancy role is dedicated to geo-redundancy";
            }
        }
        description "gNB-CU-CP redundancy role whether it is main or geo-redundant";
    }

    typedef pair-remote-state {
        type enumeration {
            enum PAIR_ACTIVE {
                value 1;
                description "Redundancy pair is in active state";
            }
            enum PAIR_PASSIVE {
                value 2;
                description "Redundancy pair is in passive state";
            }
            enum PAIR_UNAVAILABLE {
                value 3;
                description "Redundancy pair is not normal due to failure, removal, not configured, etc.";
            }
        }
        description "redundancy pair remote state";
    }

    typedef cm-sync-role {
        type enumeration {
            enum PRIMARY {
                value 1;
                description "CM Sync role is primary";
            }
            enum SECONDARY {
                value 2;
                description "CM Sync role is secondary";
            }
            enum DISABLED {
                value 3;
                description "CM Sync role is not enabled";
            }
        }
    }

    grouping CUCPRedundancyGrp {
        leaf redundancyType {
            description
              "Type of redundancy.
              LOCAL(redundant pair GNBCUCPFunction can be configured in same data center only)
              GEO (redundant pair GNBCUCPFunction can be configured in different data center only)
              BOTH (Local and geo redundancy can be configured simultaneously)";
            config false;
            type redundancy-type;
        }

        leaf redundancyState {
            description
              "Current redundancy state of GNBCUCPFunction. Only 'Active' state can provide the services.";
            config false;
            type redundancy-state;
        }

        leaf redundancyRole {
            description
              "The redundancy role of the gNB-CU-CP.
              GEO-REDUDANT is dedicated for redundancyType GEO when redundancyState is Passive.";
            config false;
            type redundancy-role;
        }

        leaf cmSyncRole {
            description
              "Primary node configuration will be exported and then imported on secondary nodes.";
            config false;
            default DISABLED;
            type cm-sync-role;
        }

        leaf cmSyncStatus {
            description
              "Status information and timestamp from last time CM was synchronized.";
            type string {
                length "0..255";
            }
        }

        leaf localRemoteState {
            description
              "Redundancy pair state.";
            config false;
            type pair-remote-state;
        }

        leaf geoRemoteState {
            description
             "Redundancy pair state";
            config false;
            type pair-remote-state;
        }
    }

    augment "/me3gpp:ManagedElement/gnbcucp3gpp:GNBCUCPFunction" {
        list CUCPRedundancy {
            description
                "Container MO related to CR CU-CP redundancy
                This MO is created automatically when local or geo redundancy is enabled in Helm chart.
                This MO is removed automatically when CucpRedundancy type is disabled.
                The RDN of this MO is CUCPRedundancy=1";
            key id;
            max-elements 1;
            uses top3gpp:Top_Grp;
            container attributes {
                uses CUCPRedundancyGrp;
            }
            yexte:is-system-created;
            tailf:meta-data yexte:is-system-created;
        }
    }
}
