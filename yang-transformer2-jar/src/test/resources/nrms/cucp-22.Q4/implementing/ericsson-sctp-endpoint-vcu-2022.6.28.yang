// Generated by eyang-preprocessor (1.22.0-48 2022-01-20 09:10:06 CET) on Jun 30, 2022, 8:31:44 AM
module ericsson-sctp-endpoint-vcu {
    yang-version 1.1;
    namespace urn:rdns:com:ericsson:oammodel:ericsson-sctp-endpoint-vcu;
    prefix sctpep;

    import tailf-common {
        prefix tailf;
    }
    import ericsson-transport-types-vcu {
        prefix transtypes;
    }
    import ericsson-yang-extensions {
        prefix yexte;
    }
    import ericsson-notifications {
        prefix notife;
    }

    organization
        "Ericsson AB";
    contact
        "Ericsson first line support via email";
    description
        "The module defines the abstract SctpEndpoint data model for the Ericsson vCU.

         Copyright (c) 2021-2022 Ericsson AB. All rights reserved.";

    revision 2022-06-28 {
        description
            "Removed module-status preliminary.";
        yexte:version 2;
        yexte:release 2;
        yexte:correction 0;
        reference
            "RFC 7950: The YANG 1.1 Data Modeling Language";
    }

    revision 2021-07-27 {
        description
            "Bug Fix, leaf-list state notifiable compatibility issue. Adds extension notife:notifiable-state-data false to ipAddressIdList.";
        yexte:version 2;
        yexte:release 1;
        yexte:correction 0;
        reference
            "RFC 7950: The YANG 1.1 Data Modeling Language";
    }

    revision 2021-01-26 {
        description
            "Changed max-elements for ipAddressIdList from 2 to 1.";
        yexte:version 1;
        yexte:release 0;
        yexte:correction 0;
        reference
            "RFC 7950: The YANG 1.1 Data Modeling Language";
    }

    revision 2021-01-08 {
        description
            "Initial revision.";
        yexte:version 0;
        yexte:release 1;
        yexte:correction 0;
        reference
            "RFC 7950: The YANG 1.1 Data Modeling Language";
    }

    grouping SctpEndpointGrp {
        description "Represents logical sender and receiver of SCTP packets.";

        leaf-list ipAddressIdList {
            description
                "List of ID:s that references IpAddress MO:s serving as local addresses for this endpoint.";
            type transtypes:ReferenceId;
            min-elements 1;
            max-elements 1;
            config false;
            notife:notifiable-state-data false;
            tailf:meta-data notife:notifiable-state-data {
                tailf:meta-value false;
            }
        }

        leaf sctpEndpointId {
            description
                "Identifies this SctpEndpoint MO instance.";
            type transtypes:ReferenceId;
            config false;
        }

        leaf sctpProfileId {
            description "Reference to an SctpProfile MO.";
            type transtypes:ReferenceId;
            mandatory true;
            config false;
        }

        leaf userLabel {
            description "Label for free use.";
            type string;
            yexte:restricted;
        }
    }
}
