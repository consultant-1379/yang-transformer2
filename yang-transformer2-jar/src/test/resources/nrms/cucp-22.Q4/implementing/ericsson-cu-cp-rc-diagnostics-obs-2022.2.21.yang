module ericsson-cu-cp-rc-diagnostics-obs {
    yang-version 1.1;
    namespace urn:rdns:com:ericsson:oammodel:ericsson-cu-cp-rc-diagnostics-obs;
    prefix rcdiagobs;
    import tailf-common {
        prefix tailf;
    }
    import ericsson-yang-extensions {
        prefix yexte;
    }
    import ericsson-common-types-diagnostics {
        prefix commontypesdiag;
    }
    import ericsson-cu-cp-rc-diagnostics {
        prefix rcdiag;
    }
    organization
      'Ericsson AB';
    contact
      'Ericsson first line support via email';
    description
      'Diagnostics action:obs for RC Service

       Copyright (c) 2022 Ericsson AB. All rights reserved';
    revision 2022-02-21 {
        description
        'Initial revision';
        yexte:version 1;
        yexte:release 0;
        yexte:correction 0;
    }

    yexte:module-status preliminary;

    augment "/rcdiag:rc-diagnostics" {
        container obs {
            description "obs related actions";
            action active_refs {
                description "print the number of active reference mappings per reference mapping type";
                input {
                    uses commontypesdiag:output-format;
                }
                output {
                    uses commontypesdiag:result;
                }
                tailf:actionpoint cpa-action;
            }
            action discarded_ref_events {
                description "print the number of discarded ObsEvents per reference mapping type";
                input {
                    uses commontypesdiag:output-format;
                }
                output {
                    uses commontypesdiag:result;
                }
                tailf:actionpoint cpa-action;
            }
            action stored_ref_events {
                description "print the number of stored ObsEvents per reference mapping type";
                input {
                    uses commontypesdiag:output-format;
                }
                output {
                    uses commontypesdiag:result;
                }
                tailf:actionpoint cpa-action;
            }
            action pm_event_tcp_stream_status {
                description "print the status of PM event TCP streams";
                input {
                    uses commontypesdiag:output-format;
                }
                output {
                    uses commontypesdiag:result;
                }
                tailf:actionpoint cpa-action;
            }
            action ue_trace_status {
                description "print information for each started ue trace";
                input {
                    uses commontypesdiag:output-format;
                }
                output {
                    uses commontypesdiag:result;
                }
                tailf:actionpoint cpa-action;
            }
            action handler_data {
                description "print EventHandler state information";
                input {
                    uses commontypesdiag:output-format;
                }
                output {
                    uses commontypesdiag:result;
                }
                tailf:actionpoint cpa-action;
            }
        }
    }
}
