// Generated by eyang-preprocessor (1.22.0-48 2022-01-20 09:10:06 CET) on Jun 30, 2022, 8:31:35 AM
module ericsson-endpoint-resource-vcucp {
    yang-version 1.1;
    namespace urn:rdns:com:ericsson:oammodel:ericsson-endpoint-resource-vcucp;
    prefix epresource;

    import _3gpp-common-managed-element {
        prefix me3gpp;
    }
    import _3gpp-nr-nrm-gnbcucpfunction {
        prefix gnbcucp3gpp;
    }
    import _3gpp-common-top {
        prefix top3gpp;
    }
    import ericsson-yang-extensions {
        prefix yexte;
    }
    import ericsson-common-types-vcucp {
        prefix commontypes;
    }

    organization
        "Ericsson AB";
    contact
        "Ericsson first line support via email";
    description
        "The module defines the EndpointResource data model for the Ericsson vCU-CP.

        Copyright (c) 2021-2022 Ericsson AB. All rights reserved.";

    revision 2022-06-28 {
        description
            "Removed module-status preliminary.";
        yexte:version 1;
        yexte:release 1;
        yexte:correction 0;
        reference
            "RFC 7950: The YANG 1.1 Data Modeling Language";
    }

    revision 2021-03-30 {
        description
            "Add Ericsson description to EndpointResource list.";
        yexte:version 1;
        yexte:release 0;
        yexte:correction 1;
        reference
            "RFC 7950: The YANG 1.1 Data Modeling Language";
    }

    revision 2021-03-16 {
        description
            "Parity with ECIM R1A79";
        yexte:version 1;
        yexte:release 0;
        yexte:correction 0;
        reference
            "RFC 7950: The YANG 1.1 Data Modeling Language";
    }

    revision 2021-01-11 {
        description
            "Initial version of the EndpointResource model";
        yexte:version 0;
        yexte:release 1;
        yexte:correction 0;
        reference
            "RFC 7950: The YANG 1.1 Data Modeling Language";
    }

    grouping EndpointResourceGrp {
        description "Represents the EndpointResourceGrp.";
        uses commontypes:UserLabelGrp;
    }

    augment "/me3gpp:ManagedElement/gnbcucp3gpp:GNBCUCPFunction" {

        list EndpointResource {
            description
                "Transport network endpoints for RAN interfaces.

                Configuration is valid for an entity that refers to an instance of "+
                "this MO.";
            key id;
            max-elements 1;
            uses top3gpp:Top_Grp;
            container attributes {
                uses EndpointResourceGrp;
            }
        }
    }
}
