// Generated by eyang-preprocessor (1.22.0-48 2022-01-20 09:10:06 CET) on Jun 30, 2022, 8:31:38 AM
module ericsson-externalnrcellcu-vcucp {
    yang-version 1.1;
    namespace urn:rdns:com:ericsson:oammodel:ericsson-externalnrcellcu-vcucp;
    prefix externalnrcellcu;

    import tailf-common {
        prefix tailf;
    }
    import _3gpp-common-managed-element {
        prefix me3gpp;
    }
    import _3gpp-nr-nrm-gnbcucpfunction {
        prefix gnbcucp3gpp;
    }
    import _3gpp-common-yang-types {
        prefix types3gpp;
    }
    import _3gpp-common-top {
        prefix top3gpp;
    }
    import ericsson-nrnetwork-vcucp {
        prefix nrnetwork;
    }
    import ericsson-nrfrequency-vcucp {
        prefix nrfrequency;
    }
    import ericsson-externalgnbcucpfunction-vcucp {
        prefix externalgnbcucpfunctionvcucp;
    }
    import ericsson-yang-extensions {
        prefix yexte;
    }
    import ericsson-common-types-vcucp {
        prefix commontypes;
    }
    import ericsson-notifications {
        prefix notife;
    }
    import ericsson-nrcellcu-types-vcucp {
        prefix nrcellcutypes;
    }

    organization
      "Ericsson AB";
    contact
      "Ericsson first line support via email";
    description
      "The module defines the ExternalNRCellCU data model for the Ericsson vCU-CP.

       Copyright (c) 2021-2022 Ericsson AB. All rights reserved.";

    revision 2022-06-28 {
        description
            "Removed module-status preliminary.";
        yexte:version 1;
        yexte:release 1;
        yexte:correction 0;
        reference
            "RFC 7950: The YANG 1.1 Data Modeling Language";
    }

    revision 2022-03-14 {
        description
            "Updated takes-effect of nRFrequencyRef";
        yexte:version 1;
        yexte:release 0;
        yexte:correction 1;
        reference
            "RFC 7950: The YANG 1.1 Data Modeling Language";
    }

    revision 2021-11-05 {
        description
            "Mark createdBy obsolete.
            Update description for plmnIdList and sNSSAIList.";
        yexte:version 1;
        yexte:release 0;
        yexte:correction 0;
        reference
            "RFC 7950: The YANG 1.1 Data Modeling Language";
    }

    revision 2021-06-08 {
        description
            "Changed error messages for musts statement.";
        yexte:version 0;
        yexte:release 2;
        yexte:correction 2;
        reference
            "RFC 7950: The YANG 1.1 Data Modeling Language";
    }

    revision 2021-06-03 {
        description
            "Disable notifications for timeOfCreation.";
        yexte:version 0;
        yexte:release 2;
        yexte:correction 1;
        reference
            "RFC 7950: The YANG 1.1 Data Modeling Language";
    }

    revision 2021-05-06 {
        description
            "Remove is-system-created and restricted extensions from configurable attributes";
        yexte:version 0;
        yexte:release 2;
        yexte:correction 0;
        reference
            "RFC 7950: The YANG 1.1 Data Modeling Language";
    }

    revision 2021-04-10 {
        description
          "Parity with ECIM R1A79.";
        yexte:version 0;
        yexte:release 1;
        yexte:correction 0;
        reference
          "RFC 7950: The YANG 1.1 Data Modeling Language";
    }

    grouping ExternalNRCellCUGrp {
        description
            "ExternalNRCellCU MO and related measurement parameters.";
        reference
          "Ericsson documentation";

        leaf cellLocalId {
            must 'count(../../../externalnrcellcu:ExternalNRCellCU/externalnrcellcu:attributes/externalnrcellcu:cellLocalId[current() = .]) = 1' {
                error-message
                  "All ExternalNRCellCUs under the same ExternalGNBCUCPFunction must have a unique cellLocalId.";
            }
            must '(../../../externalgnbcucpfunctionvcucp:attributes/externalgnbcucpfunctionvcucp:gNBIdLength = 32 and current() &lt;= 15) or (../../../externalgnbcucpfunctionvcucp:attributes/externalgnbcucpfunctionvcucp:gNBIdLength = 31 and current() &lt;= 31) or (../../../externalgnbcucpfunctionvcucp:attributes/externalgnbcucpfunctionvcucp:gNBIdLength = 30 and current() &lt;= 63) or (../../../externalgnbcucpfunctionvcucp:attributes/externalgnbcucpfunctionvcucp:gNBIdLength = 29 and current() &lt;= 127) or (../../../externalgnbcucpfunctionvcucp:attributes/externalgnbcucpfunctionvcucp:gNBIdLength = 28 and current() &lt;= 255) or (../../../externalgnbcucpfunctionvcucp:attributes/externalgnbcucpfunctionvcucp:gNBIdLength = 27 and current() &lt;= 511) or (../../../externalgnbcucpfunctionvcucp:attributes/externalgnbcucpfunctionvcucp:gNBIdLength = 26 and current() &lt;= 1023) or (../../../externalgnbcucpfunctionvcucp:attributes/externalgnbcucpfunctionvcucp:gNBIdLength = 25 and current() &lt;= 2047) or (../../../externalgnbcucpfunctionvcucp:attributes/externalgnbcucpfunctionvcucp:gNBIdLength = 24 and current() &lt;= 4095) or (../../../externalgnbcucpfunctionvcucp:attributes/externalgnbcucpfunctionvcucp:gNBIdLength = 23 and current() &lt;= 8191) or ../../../externalgnbcucpfunctionvcucp:attributes/externalgnbcucpfunctionvcucp:gNBIdLength = 22' {
                error-message
                   "cellLocalId must be equal or less than 2^(36-ExternalGNBCUCPFunction::gNBIdLength) - 1.";
            }
            description
              "Together with gNodeB identifier, identifies an NR cell within a PLMN.

               Together with gNBId it forms NCI.";
            type int32 {
                range "0..16383";
            }
            default 0;
            yexte:dependencies
                "Must be unique among ExternalNRCellCU MO instances within an "+
                "ExternalGNBCUCPFunction MO instance.

                cellLocalId &lt; 2^(36 - ExternalGNBCUCPFunction::gNBIdLength)";
            tailf:info 'Dependencies: Must be unique among ExternalNRCellCU MO instances within an ExternalGNBCUCPFunction MO instance.

                cellLocalId &lt; 2^(36 - ExternalGNBCUCPFunction::gNBIdLength), Together with gNodeB identifier, identifies an NR cell within a PLMN. Together with gNBId it forms NCI.';
        }

        leaf createdBy {
            description
                "Whether MO is created by the ANR function or operator.";
            config false;
            type commontypes:CreatedByGutran;
            status obsolete {
                yexte:status-information
                    "Since 21.Q2. Planned to be removed.";
            }
            tailf:info 'Status Info: Since 21.Q2. Planned to be removed, Obsolete, Whether MO is created by the ANR function or operator.';
        }

        leaf nRFrequencyRef {
            description
                "Reference to an instance of NRFrequency MO corresponding to cell SSB "
                + "configuration.";
            mandatory true;
            type types3gpp:DistinguishedName;
            must "re-match(current(), 'ManagedElement=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,GNBCUCPFunction=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,NRNetwork=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,NRFrequency=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?') and
                  re-match(current(), concat('ManagedElement=', ../../../../../../me3gpp:id, ',.*')) and
                  re-match(current(), concat('.*GNBCUCPFunction=', ../../../../../gnbcucp3gpp:id, ',.*')) and
                  count( ../../../../../nrnetwork:NRNetwork[re-match(current(), concat('.*NRNetwork=', nrnetwork:id, ',.*'))]/nrfrequency:NRFrequency[re-match(current(), concat('.*NRFrequency=', nrfrequency:id))]) &gt; 0" {
                error-message
                  "nRFrquencyRef must refer to an NRFrequency under the same GNBCUCPFunction.";
            }
            yexte:takes-effect
                "New connection";
            tailf:info 'Takes effect: New connection, Reference to an instance of NRFrequency MO corresponding to cell SSB configuration.';
        }

        leaf nRPCI {
            description
              "Physical cell identity of external NR cell.";
            mandatory true;
            type int32 {
                range "0..1007";
            }
            reference
              "3GPP TS 28.541";
            yexte:takes-effect
                "New connection";
            tailf:info 'Takes effect: New connection, Physical cell identity of external NR cell.';
        }

        leaf nRTAC {
            description
              "Tracking Area Code for the External NR Cell.

               If empty, Stand Alone is not supported. Not used for non-Stand Alone.";
            type uint32 {
                range "0..16777215";
            }
            reference
              "3GPP TS 28.541";
            yexte:takes-effect
                "New connection";
            tailf:info 'Takes effect: New connection, Tracking Area Code for the External NR Cell. If empty, Stand Alone is not supported. Not used for non-Stand Alone.';
        }

        list plmnIdList {
            key "mcc mnc";
            min-elements 1;
            max-elements 12;
            description
                "List of supported PLMNs.

                PLMN ID consists of MobileCountryCode (MCC, three digits) and "+
                "MobileNetworkCode (MNC, two or three digits).";
            uses types3gpp:PLMNId;
            reference
                "3GPP TS 28.541";
            yexte:takes-effect
                "New connection";
            tailf:info 'Takes effect: New connection, List of supported PLMNs. PLMN ID consists of MobileCountryCode (MCC, three digits) and MobileNetworkCode (MNC, two or three digits).';
        }

        list primaryPLMNId {
            max-elements 1;
            description
                "PLMN ID for NR CGI.";
            config false;
            uses types3gpp:PLMNId;
        }

        leaf serviceState {
            description
                "Service state of external NR cell in remote gNodeB.";
            config false;
            type nrcellcutypes:NRCellServiceState;
        }

        list sNSSAIList {
            key "sd sst";
            max-elements 1024;
            description
                "List of supported network slices.

                If empty, cell can be used for all UEs regardless of their S-NSSAI.";
            uses commontypes:SliceSelectionAssistInfo;
            reference
              "3GPP TS 28.541";
        }

        leaf timeOfCreation {
            description
              "Time and date of MO creation.

               Format: YYYY-MM-DD HH:MM:SS.";
            config false;
            type string {
                length "0..19";
            }
            notife:notifiable-state-data false;
            tailf:meta-data notife:notifiable-state-data {
                tailf:meta-value false;
            }
        }
    }

    augment "/me3gpp:ManagedElement/gnbcucp3gpp:GNBCUCPFunction/nrnetwork:NRNetwork/externalgnbcucpfunctionvcucp:ExternalGNBCUCPFunction" {
        list ExternalNRCellCU {
            description
              "Representation of an external NRCellCU.

               This MO is created automatically. Can also be created and "
            + "deleted manually.

               Created automatically when Xn message is received, unless it "
            + "already exists.
               Deleted automatically.

               When created automatically, the RDN of this MO is "
            + "ExternalNRCellCU=auto&lt;NCI&gt;, where NCI = "
            + "&lt;gNBId&gt;*2^(36-&lt;gNBIdLength&gt;) + &lt;cellLocalId&gt;.";
            reference
              "3GPP TS 28.541";
            key id;
            max-elements 256;
            uses top3gpp:Top_Grp;
            container attributes {
                uses ExternalNRCellCUGrp;
            }
        }
    }
}
