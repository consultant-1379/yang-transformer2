// Generated by eyang-preprocessor (1.22.0-48 2022-01-20 09:10:06 CET) on Jun 30, 2022, 8:31:35 AM
module ericsson-common-types-vcucp {
    yang-version 1.1;
    namespace urn:rdns:com:ericsson:oammodel:ericsson-common-types-vcucp;
    prefix commontypes;

    import tailf-common {
        prefix tailf;
    }
    import ericsson-yang-extensions {
        prefix yexte;
    }

    organization
      "Ericsson AB";
    contact
      "Ericsson first line support via email";
    description
      "The module defines common types for the Ericsson vCU-CP.

       Copyright (c) 2021-2022 Ericsson AB. All rights reserved.";

    revision 2022-06-28 {
        description
            "Removed module-status preliminary.
             Removed preliminary status from userLabel in UserLabelGrp.";
        yexte:version 3;
        yexte:release 1;
        yexte:correction 0;
        reference
            "RFC 7950: The YANG 1.1 Data Modeling Language";
    }

    revision 2022-06-16 {
        description
          "Setting correct max of -29 on ReportConfigA5Rsrp::threshold1
           and ReportConfigA5Rsrp::threshold2.";
        yexte:version 3;
        yexte:release 0;
        yexte:correction 0;
        reference
          "RFC 7950: The YANG 1.1 Data Modeling Language";
    }

    revision 2022-04-13 {
        description
          "Range of ReportConfigA5Rsrp::threshold1 and ReportConfigA5Rsrp::threshold2
           temporary reverted to max -26 until upgrade is ready.";
        yexte:version 2;
        yexte:release 0;
        yexte:correction 1;
        reference
          "RFC 7950: The YANG 1.1 Data Modeling Language";
    }

    revision 2022-03-14 {
        description
          "Added the type UeConfGroupType.
           Moved enums ReportInterval and ReportAmount from ericsson-pmueintrafreqcellprofile-vcucp.
           Moved groupings ReportConfigB1Rsrp and ReportConfigB1Rsrq from ericsson-mcfbcellprofile-vcucp.
           Moved enums EpsFallbackOperationType and EpsFbOperationTypeEm from ericsson-mcfbcellprofile-vcucp.
           Changed description of ReportConfigA5Rsrp and updated range of ReportConfigA5Rsrp::threshold1 and ReportConfigA5Rsrp::threshold2.
           Fixed length on the UserLabel typedef and removed restricted tag from the userLabel attribute.";
        yexte:version 2;
        yexte:release 0;
        yexte:correction 0;
        reference
          "RFC 7950: The YANG 1.1 Data Modeling Language";
    }

    revision 2021-11-05 {
        description
          "Mark CreatedByNr and CreatedByGutran obsolete.";
        yexte:version 1;
        yexte:release 0;
        yexte:correction 0;
        reference
          "RFC 7950: The YANG 1.1 Data Modeling Language";
    }

    revision 2021-09-16 {
        description
          "Added the grouping ReportConfigA5NoThr1Rsrp.";
        yexte:version 0;
        yexte:release 7;
        yexte:correction 0;
        reference
          "RFC 7950: The YANG 1.1 Data Modeling Language";
    }

    revision 2021-08-11 {
        description
          "Moved McpcQuantity and ReportConfigA5Rsrp from ericsson-mcpc-pcell-profile-vcucp.
           Added the grouping ReportConfigA2Rsrp.";
        yexte:version 0;
        yexte:release 6;
        yexte:correction 0;
        reference
          "RFC 7950: The YANG 1.1 Data Modeling Language";
    }

    revision 2021-05-19 {
        description
          "Remove AbsFrameStartOffset.";
        yexte:version 0;
        yexte:release 5;
        yexte:correction 0;
        reference
          "RFC 7950: The YANG 1.1 Data Modeling Language";
    }

    revision 2021-04-23 {
        description
          "Added the grouping ReportConfigA5RsrpOffsets.";
        yexte:version 0;
        yexte:release 4;
        yexte:correction 0;
        reference
          "RFC 7950: The YANG 1.1 Data Modeling Language";
    }

    revision 2021-04-16 {
        description
          "Add types for Intra-freq mobility.";
        yexte:version 0;
        yexte:release 3;
        yexte:correction 0;
        reference
          "RFC 7950: The YANG 1.1 Data Modeling Language";
    }

    revision 2021-04-13 {
        description
          "Added the type CreatedByNR.";
        yexte:version 0;
        yexte:release 2;
        yexte:correction 0;
        reference
          "RFC 7950: The YANG 1.1 Data Modeling Language";
    }

    revision 2021-03-09 {
        description
          "Add common types used by multiple MO classes within vCU-CP.";
        yexte:version 0;
        yexte:release 1;
        yexte:correction 0;
        reference
          "RFC 7950: The YANG 1.1 Data Modeling Language";
    }

    typedef UeConfGroupType {
        description
          "UE configuration group type.";

        type enumeration {
            enum UE_MOBILITY_GROUP {
                value 0;
                description
                  "UE mobility group.

                   Defined by UeMobilityGroupDefinition MO class.";
            }

            enum UE_SERVICE_GROUP {
                value 1;
                description
                  "UE service group.

                   Defined by UeServiceGroupDefinition MO class.";
            }
        }
    }

    typedef CreatedByGutran {
        description
          "Identifies MO creation.";

        status obsolete {
            yexte:status-information
            "Since 21.Q2. Planned to be removed.";
        }

        type enumeration {
            enum ANR {
                value 0;
                description
                  "Created by ANR.";
            }

            enum X2 {
                value 1;
                description
                  "Created by X2.";
            }

            enum OPERATOR {
                value 2;
                description
                  "Created by operator.";
            }
        }
        tailf:info 'Status Info: Since 21.Q2. Planned to be removed, Identifies MO creation.';
    }

    typedef CreatedByNR {
        description
          "Identifies MO creation.";

        status obsolete {
            yexte:status-information
            "Since 21.Q2. Planned to be removed.";
        }
        type enumeration {
            enum XN {
                value 0;
                description
                  "Created by Xn.";
            }

            enum OPERATOR {
                value 1;
                description
                  "Created by operator.";
            }
        }
        tailf:info 'Status Info: Since 21.Q2. Planned to be removed, Identifies MO creation.';
    }

    typedef EpsFallbackOperationType {
        description
          "EPS fallback operation.";

        type enumeration {
            enum INACTIVE {
                value 0;
                description
                  "Always use Voice over NR (VoNR).";
            }

            enum ACTIVE {
                value 1;
                description
                  "Use Release with Redirection EPS fallback without measurement.

                   Applied for UE not supporting Voice over NR (VoNR).";
            }

            enum FORCED {
                value 2;
                description
                  "Use EPS fallback with Release with Redirection without measurement.";
            }

            enum ACTIVE_MEAS_RWR {
                value 3;
                description
                  "Use measurement-based Release with Redirection EPS fallback.

                   Applied for UE not supporting Voice over NR (VoNR).";
            }

            enum ACTIVE_MEAS_IRAT_HO {
                value 4;
                description
                  "Use measurement-based Inter-RAT handover EPS fallback.

                   Applied for UE not supporting Voice over NR (VoNR).";
            }

            enum FORCED_MEAS_RWR {
                value 5;
                description
                  "Use measurement-based Release with Redirection EPS fallback.";
            }

            enum FORCED_MEAS_IRAT_HO {
                value 6;
                description
                  "Use Measurement-based Inter-RAT handover EPS fallback.";
            }
        }
    }

    typedef EpsFbOperationTypeEm {
        description
          "EPS fallback operation for emergency calls.";

        type enumeration {
            enum ACTIVE {
                value 0;
                description
                  "Use Release with Redirection EPS fallback without measurement for " +
                  "emergency call.

                   Applied for UE and RAN not supporting emergency call over NR.";
            }

            enum FORCED {
                value 1;
                description
                  "Use Release with Redirection EPS fallback without measurement for " +
                  "emergency call.";
            }

            enum ACTIVE_MEAS_RWR {
                value 2;
                description
                  "Use measurement-based Release with Redirection EPS fallback for " +
                  "emergency call.

                   Applied for UE and RAN not supporting emergency call over NR.";
            }

            enum ACTIVE_MEAS_IRAT_HO {
                value 3;
                description
                  "Use measurement-based Inter-RAT handover EPS fallback for " +
                  "emergency call.

                   Applied for UE and RAN not supporting emergency call over NR.";
            }

            enum FORCED_MEAS_RWR {
                value 4;
                description
                  "Use measurement-based Release with Redirection EPS fallback for " +
                  "emergency call.";
            }

            enum FORCED_MEAS_IRAT_HO {
                value 5;
                description
                  "Use Measurement-based Inter-RAT handover EPS fallback for " +
                  "emergency call.";
            }
        }
    }

    grouping SliceSelectionAssistInfo {
        description
          "Single Network Slice Selection Assistance Information(S-NSSAI).";

        leaf sd {
            description
              "Slice Differentiator (SD).

               If it is not associated with SST, SD value can be set to 16777215.";
            type int32 {
                range "0..16777215";
            }
            reference
              "3GPP TS 23.003";
        }

        leaf sst {
            description
              "Slice/Service Type (SST).

               Values 0 to 127 belong to standardized SST range and are defined in "
            + "3GPP TS 23.501. Values 128 to 255 belong to operator-specific range.";
            type int32 {
                range "0..255";
            }
            reference
              "3GPP TS 23.003";
        }
    }

    typedef TriggerQuantity {
        description
          "The measurement quantity that triggers a measurement event.";
        type enumeration {
            enum RSRP {
                value 0;
                description
                  "RSRP (Reference Signal Received Power) is used.";
            }
            enum RSRQ {
                value 1;
                description
                  "RSRQ (Reference Signal Received Quality) is used.";
            }
        }
    }

    typedef EndcMobilityAction {
        description
          "Intra-frequency handover evaluation fails to select a target NR cell or SN change procedure fails.";
        type enumeration{
            enum RELEASE {
                value 0;
                description
                  "SN initiated SN Release is triggered.";
            }
            enum IGNORE {
                value 1;
                description
                  "No action is taken.";
            }
        }
    }

    typedef McpcQuantity {
        description
            "Measurement quantity applicable for MCPC function.";

        type enumeration {
            enum RSRP {
                value 0;
                description
                  "Reference signal received power.";
            }
        }
    }

    typedef ReportAmount {
        description
          "Number of periodical or event-triggered measurement reports.";
        type enumeration {
            enum R1 {
                value 0;
                description
                  "One report.";
            }
            enum R2 {
                value 1;
                description
                  "Two reports.";
            }
            enum R4 {
                value 2;
                description
                  "Four reports.";
            }
            enum R8 {
                value 3;
                description
                  "Eight reports.";
            }
            enum R16 {
                value 4;
                description
                  "16 reports.";
            }
            enum R32 {
                value 5;
                description
                  "32 reports.";
            }
            enum R64 {
                value 6;
                description
                  "64 reports.";
            }
            enum INFINITY {
                value 7;
                description
                  "Infinite number of reports.";
            }
        }
    }

    grouping ReportConfigA2Rsrp {
        description
          "Report configuration settings for A2 measurement event when trigger "+
          "quantity is RSRP.";

        leaf hysteresis {
            description
                "Hysteresis value for eventA2.";
            type int32 {
                range "0..150";
            }
            default 10;
            units "0.1 dB";
            must ". mod 5 = 0" {
                error-message
                    "The value must set with resolution/step of 5";
            }
            reference
                "3GPP TS 38.331";
        }

        leaf threshold {
            description
                "RSRP threshold value for eventA2.";
            type int32 {
                range "-156..-29";
            }
            default -156;
            units dBm;
            reference
                "3GPP TS 38.331";
        }

        leaf timeToTrigger {
            description
                "Time-to-trigger value for eventA2.";
            type int32 {
                range "0|40|64|80|100|128|160|256|320|480|512|640|1024|1280|2560|5120";
            }
            default 160;
            units ms;
            reference
                "3GPP TS 38.331";
        }
    }

    grouping ReportConfigA5Rsrp {
        description
          "Report configuration settings for A5 measurement event when trigger "+
          "quantity is RSRP.";

        leaf hysteresis {
            description
              "Hysteresis value for eventA5.";
            type int32 {
                range "0..150";
            }
            must ". mod 5 = 0" {
                error-message
                  "The value must set with resolution/step of 5";
            }
            units "0.1 dB";
            default 10;
            reference
              "3GPP TS 38.331";
        }

        leaf threshold1 {
            description
              "RSRP threshold1 value for eventA5.

              Value -29 defines threshold1 to infinity.";
            type int32 {
                range "-156..-29";
            }
            default -156;
            units dBm;
            reference
              "3GPP TS 38.331";
        }

        leaf threshold2 {
            description
              "RSRP threshold2 value for eventA5.

              Value -29 defines threshold2 to infinity.";
            type int32 {
                range "-156..-29";
            }
            default -156;
            units dBm;
            reference
              "3GPP TS 38.331";
        }

        leaf timeToTrigger {
            description
              "Time-to-trigger value for eventA5.";
            type int32 {
                range "0|40|64|80|100|128|160|256|320|480|512|640|1024|1280|2560|5120";
            }
            default 640;
            units ms;
            reference
              "3GPP TS 38.331";
        }
    }

    grouping ReportConfigA5NoThr1Rsrp {
        description
            "Report configuration settings for A5 measurement event where "+
            "threshold1 is not used.";

        leaf hysteresis {
            description
                "Hysteresis value for A5 measurement event.";
            type int32 {
                range "0..150";
            }
            default 10;
            units "0.1 dB";
            must ". mod 5 = 0" {
                error-message
                    "The value must set with resolution/step of 5";
            }
            reference
                "3GPP TS 38.331";
        }

        leaf threshold2 {
            description
                "RSRP threshold2 value for A5 measurement event.

                Value -29 defines threshold2 to infinity.";
            type int32 {
                range "-156..-29";
            }
            default -156;
            units dBm;
            reference
                "3GPP TS 38.331";
        }

        leaf timeToTrigger {
            description
                "Time-to-trigger value for A5 measurement event.";
            type int32 {
                range "0|40|64|80|100|128|160|256|320|480|512|640|1024|1280|2560|5120";
            }
            default 640;
            units ms;
            reference
                "3GPP TS 38.331";
        }
    }

    grouping ReportConfigA5RsrpOffsets {
        description
            "Threshold offsets for report configuration setting for A5 measurement "+
            "event.

            Applied when trigger quantity is RSRP.";

        leaf threshold1Offset {
            description
                "RSRP threshold1 offset value for eventA5.";
            type int32 {
                range "-100..100";
            }
            default 0;
            units dB;
        }

        leaf threshold2Offset {
            description
                "RSRP threshold2 offset value for eventA5.";
            type int32 {
                range "-100..100";
            }
            default 0;
            units dB;
        }
    }

    grouping ReportConfigA6Rsrp {
        description
          "Report configuration settings for A6 measurements when trigger quantity is RSRP.";
        leaf hysteresis {
            description
              "Hysteresis value for RSRP in event A6 measurements.";
            type int32 {
                range "0..150";
            }
            default 10;
            units "0.1 dB";
            must ". mod 5 = 0" {
                error-message
                  "The value must set with resolution/step of 5";
            }
            reference
              "3GPP TS 38.331";
        }

        leaf offset {
            description
              "RSRP offset value for event A6 measurements.";
            type int32 {
                range "-150..150";
            }
            default 30;
            units "0.1 dB";
            must ". mod 5 = 0" {
                error-message
                  "The value must set with resolution/step of 5";
            }
            reference
              "3GPP TS 38.331";
        }

        leaf timeToTrigger {
            description
              "Time-to-trigger value for RSRP in event A6 measurements.";
            type int32 {
                range "0 | 40 | 64 | 80 | 100 | 128 | 160 | 256 | 320 | 480 | 512 | 640 | 1024 | 1280 | 2560 | 5120";
            }
            default 160;
            units ms;
            reference
              "3GPP TS 38.331";
        }
    }

    grouping ReportConfigA3Rsrp {
        description
          "Report configuration settings for A3 measurement events when trigger quantity is RSRP.";
        leaf hysteresis {
            description
              "Hysteresis value for eventA3.";
            type int32{
                range "0..150";
            }
            default 10;
            units "0.1 dB";
            must ". mod 5 = 0" {
                error-message
                  "The value must set with resolution/step of 5";
            }
            reference
              "3GPP TS 38.331";
        }
        leaf offset {
            description
              "Offset value for eventA3.";
            type int32{
                range "-150..150";
            }
            default 30;
            units "0.1 dB";
            must ". mod 5 = 0" {
                error-message
                  "The value must set with resolution/step of 5";
            }
            reference
              "3GPP TS 38.331";
        }
        leaf timeToTrigger {
            description
              "Time-to-trigger value for eventA3.";
            type int32 {
                range "0 | 40 | 64 | 80 | 100 | 128 | 160 | 256 | 320 | 480 | 512 | 640 | 1024 | 1280 | 2560 | 5120";
            }
            default 640;
            units ms;
            reference
              "3GPP TS 38.331";
        }
    }

    grouping ReportConfigA1A2Rsrp {
        description
          "Report configuration settings for UE DL A1, A2, or both measurements with trigger quantity RSRP.";
        leaf hysteresis {
            description
              "Hysteresis value for RSRP in UE DL event A1, A2, or both measurements.";
            type int32 {
                range "0..150";
            }
            default 10;
            units "0.1 dB";
            must ". mod 5 = 0" {
                error-message
                  "The value must set with resolution/step of 5";
            }
            reference
              "3GPP TS 38.331";
        }
        leaf threshold {
            description
              "RSRP threshold value for UE DL event A1, A2, or both measurements.";
            type int32 {
                range "-156..-29";
            }
            default -156;
            units dBm;
            reference
              "3GPP TS 38.331";
        }
        leaf timeToTrigger {
            description
              "Time-to-trigger value for RSRP in UE DL event A1, A2, or both measurements.";
            type int32 {
                range "0 | 40 | 64 | 80 | 100 | 128 | 160 | 256 | 320 | 480 | 512 | 640 | 1024 | 1280 | 2560 | 5120";
            }
            default 160;
            units ms;
            reference
              "3GPP TS 38.331";
        }
        leaf timeToTriggerA1 {
            description
              "Time-to-trigger value for event A1.

               If set to -1, time-to-trigger value from struct member timeToTrigger is used.";
            type int32 {
                range "-1 | 0 | 40 | 64 | 80 | 100 | 128 | 160 | 256 | 320 | 480 | 512 | 640 | 1024 | 1280 | 2560 | 5120";
            }
            default -1;
            units ms;
            reference
              "3GPP TS 38.331";
        }
    }

    grouping ReportConfigA3Rsrq {
        description
          "Report configuration settings for A3 measurement events when trigger quantity is RSRQ.";
        leaf hysteresis {
            description
              "Hysteresis value for eventA3.";
            type int32 {
                range "0..150";
            }
            default 10;
            units "0.1 dB";
            must ". mod 5 = 0" {
                error-message
                  "The value must set with resolution/step of 5";
            }
            reference
              "3GPP TS 38.331";
        }
        leaf offset {
            description
              "Offset value for eventA3.";
            type int32{
                range "-150..150";
            }
            default 30;
            units "0.1 dB";
            must ". mod 5 = 0" {
                error-message
                  "The value must set with resolution/step of 5";
            }
            reference
              "3GPP TS 38.331";
        }
        leaf timeToTrigger {
            description
              "Time-to-trigger value for eventA3.";
            type int32 {
                range "0 | 40 | 64 | 80 | 100 | 128 | 160 | 256 | 320 | 480 | 512 | 640 | 1024 | 1280 | 2560 | 5120";
            }
            default 640;
            units ms;
            reference
              "3GPP TS 38.331";
        }
    }

    grouping ReportConfigA1A2Rsrq {
        description
          "Report configuration settings for A1 and A2 measurements when trigger quantity is RSRQ.";

        leaf hysteresis {
            description
              "Hysteresis value for RSRQ in event A1 and A2 measurements.";
            type int32 {
                range "0..150";
            }
            default 10;
            units "0.1 dB";
            must ". mod 5 = 0" {
                error-message
                  "The value must set with resolution/step of 5";
            }
            reference
              "3GPP TS 38.331";
        }
        leaf threshold {
            description
              "RSRQ threshold value for event A1 and A2 measurements.";
            type int32 {
                range "-435..200";
            }
            default -435;
            units "0.1 dB";
            must ". mod 5 = 0" {
                error-message
                  "The value must set with resolution/step of 5";
            }
            reference
              "3GPP TS 38.331";
        }
        leaf timeToTrigger {
            description
              "Time-to-trigger value for RSRQ in event A1 and A2 measurements.";
            type int32 {
                range "0 | 40 | 64 | 80 | 100 | 128 | 160 | 256 | 320 | 480 | 512 | 640 | 1024 | 1280 | 2560 | 5120";
            }
            default 160;
            units ms;
            reference
              "3GPP TS 38.331";
        }
        leaf timeToTriggerA1 {
            description
              "The time-to-trigger value for eventA1.

               If set to -1, time-to-trigger value from struct member timeToTrigger is used.";
            type int32 {
                range "-1 | 0 | 40 | 64 | 80 | 100 | 128 | 160 | 256 | 320 | 480 | 512 | 640 | 1024 | 1280 | 2560 | 5120";
            }
            default -1;
            units ms;
            reference
              "3GPP TS 38.331";
        }
    }

    grouping ReportConfigB1Rsrp {
        description
          "Report configuration settings for E-UTRA B1 measurement event when " +
          "trigger quantity is RSRP.";

        leaf hysteresis {
            description
              "Hysteresis value for eventB1.";
            type int32 {
                range "0..150";
            }
            default 10;
            units "0.1 dB";
            must ". mod 5 = 0" {
                error-message
                  "The value must set with resolution/step of 5";
            }
            reference
              "3GPP TS 38.331";
        }

        leaf threshold {
            description
              "RSRP threshold value for eventB1.";
            type int32 {
                range "-140..-44";
            }
            default -140;
            units dBm;
            reference
              "3GPP TS 36.331";
        }

        leaf timeToTrigger {
            description
              "Time-to-trigger value for eventB1 measurement.";
            type int32 {
                range "0|40|64|80|100|128|160|256|320|480|512|640|1024|1280|2560|5120";
            }
            default 40;
            units ms;
            reference
              "3GPP TS 38.331";
        }
    }

    grouping ReportConfigB1Rsrq {
        description
          "Report configuration settings for E-UTRA B1 measurement event when " +
          "trigger quantity is RSRQ.";

        leaf hysteresis {
            description
              "Hysteresis value for eventB1.";
            type int32 {
                range "0..150";
            }
            default 10;
            units "0.1 dB";
            must ". mod 5 = 0" {
                error-message
                  "The value must set with resolution/step of 5";
            }
            reference
              "3GPP TS 38.331";
        }

        leaf threshold {
            description
              "RSRQ threshold value for eventB1.";
            type int32 {
                range "-195..-30";
            }
            default -195;
            units "0.1 dB";
            must ". mod 5 = 0" {
                error-message
                  "The value must set with resolution/step of 5";
            }
            reference
              "3GPP TS 36.331";
        }

        leaf timeToTrigger {
            description
              "Time-to-trigger value for eventB1 measurement.";
            type int32 {
                range "0|40|64|80|100|128|160|256|320|480|512|640|1024|1280|2560|5120";
            }
            default 40;
            units ms;
            reference
              "3GPP TS 38.331";
        }
    }

    typedef ReportInterval {
        description
          "Interval between periodical reports.";
        type enumeration {
            enum MS_120 {
                value 0;
                description
                  "120 ms interval.";
            }
            enum MS_240 {
                value 1;
                description
                  "240 ms interval.";
            }
            enum MS_480 {
                value 2;
                description
                  "480 ms interval.";
            }
            enum MS_640 {
                value 3;
                description
                  "640 ms interval.";
            }
            enum MS_1024 {
                value 4;
                description
                  "1024 ms interval.";
            }
            enum MS_2048 {
                value 5;
                description
                  "2048 ms interval.";
            }
            enum MS_5120 {
                value 6;
                description
                  "5120 ms interval.";
            }
            enum MS_10240 {
                value 7;
                description
                  "10240 ms interval.";
            }
            enum MS_20480 {
                value 8;
                description
                  "20480 ms interval.";
            }
            enum MS_40960 {
                value 9;
                description
                  "40960 ms interval.";
            }
            enum MIN_1 {
                value 10;
                description
                  "1 minute.";
            }
            enum MIN_6 {
                value 11;
                description
                  "6 minutes.";
            }
            enum MIN_12 {
                value 12;
                description
                  "12 minutes.";
            }
            enum MIN_30 {
                value 13;
                description
                  "30 minutes.";
            }
        }
    }

    typedef UserLabel {
        description
            "User-defined label, maximum 128 characters including spaces.";
        type string {
            length "0..128";
        }
    }

    grouping UserLabelGrp {
        leaf userLabel {
            description
                "Label for free use.";
            type UserLabel;
        }
    }
}
