// Generated by eyang-preprocessor (1.22.0-48 2022-01-20 09:10:06 CET) on Jun 30, 2022, 8:31:44 AM
module ericsson-rrc-uecfg-vcucp {
    yang-version 1.1;
    namespace urn:rdns:com:ericsson:oammodel:ericsson-rrc-uecfg-vcucp;

    prefix rrcuecfgvcucp;

    import tailf-common {
        prefix tailf;
    }
    import _3gpp-common-managed-element {
        prefix me3gpp;
    }
    import _3gpp-nr-nrm-gnbcucpfunction {
        prefix gnbcucp3gpp;
    }
    import _3gpp-common-top {
        prefix top3gpp;
    }
    import ericsson-uecc-vcucp {
        prefix ueccvcucp;
    }
    import ericsson-rrc-vcucp {
        prefix rrcvcucp;
    }
    import ericsson-yang-extensions {
        prefix yexte;
    }
    import ericsson-common-types-vcucp {
        prefix commontypes;
    }

    organization
      "Ericsson AB";
    contact
      "Ericsson first line support via email";
    description
      "The module defines the RrcUeCfg data model for the Ericsson vCU-CP.

       Copyright (c) 2022 Ericsson AB. All rights reserved.";

    revision 2022-06-28 {
        description
            "Removed module-status preliminary.
             Removed preliminary status from RrcUeCfg.";
        yexte:version 0;
        yexte:release 2;
        yexte:correction 0;
        reference
            "RFC 7950: The YANG 1.1 Data Modeling Language";
    }

    revision 2022-06-16 {
        description
            "Corrected an error in the MO description.";
        yexte:version 0;
        yexte:release 1;
        yexte:correction 1;
        reference
            "RFC 7950: The YANG 1.1 Data Modeling Language";
    }

    revision 2022-03-14 {
        description
            "Initial version of the RrcUeCfg model.";
        yexte:version 0;
        yexte:release 1;
        yexte:correction 0;
        reference
            "RFC 7950: The YANG 1.1 Data Modeling Language";
    }

    grouping RrcUeCfgGrp {
        description
            "Represents the RrcUeCfg IOC.";

        leaf-list prefUeGroupList {
            max-elements 8;
            description
                "Preference UE group list.

                List of preference UE group identifiers.

                If empty, the MO instance matches preference UE group identifiers " +
                "not defined in prefUeGroupList of any other MO instances under " +
                "parent MO instance.";
            type int32 {
                range "1..255";
            }
            yexte:dependencies
                "Combinations of pair of preference UE group Identifier in " +
                "prefUeGroupList and UE group identifier in ueGroupList must be " +
                "unique among RrcUeCfg instances under parent Rrc instance.

                For all preference UE group identifiers in prefUeGroupList " +
                "attributes under parent Rrc MO instance, exactly one RrcUeCfg MO " +
                "instance must exist that combines the given preference UE group " +
                "identifier with an empty ueGroupList.";
            yexte:takes-effect
                "New connection";
            must "count(../../../RrcUeCfg/attributes[prefUeGroupList = current() and count(ueGroupList) = 0 ]) = 1" {
                error-message
                   "Exactly one RrcUeCfg instance under Rrc must combine a specific preference UE group identifier in attribute prefUeGroupList with an empty ueGroupList.";
            }
            tailf:info 'Takes effect: New connection, Dependencies: Combinations of pair of preference UE group Identifier in prefUeGroupList and UE group identifier in ueGroupList must be unique among RrcUeCfg instances under parent Rrc instance.

                For all preference UE group identifiers in prefUeGroupList attributes under parent Rrc MO instance, exactly one RrcUeCfg MO instance must exist that combines the given preference UE group identifier with an empty ueGroupList, Preference UE group list. List of preference UE group identifiers. If empty, the MO instance matches preference UE group identifiers not defined in prefUeGroupList of any other MO instances under parent MO instance.';
        }

        leaf tWaitForRrcReestRequest {
            description
                "Waiting time for the RRC Reestablishment Request message upon " +
                "detecting Radio Link Failure.";
            type int32 {
                range "1..20";
            }
            default 6;
            units s;
            yexte:takes-effect
                "New connection";
            tailf:info 'Takes effect: New connection, Waiting time for the RRC Reestablishment Request message upon detecting Radio Link Failure.';
        }

        leaf-list ueGroupList {
            max-elements 16;
            description
              "UE group list.

               List of UE group identifiers.

               If empty, the MO instance matches all UE group identifiers.";
            type int32 {
                range "1..255";
            }
            yexte:dependencies
                "Combinations of pair of preference UE group Identifier in "+
                "prefUeGroupList and UE group identifier in ueGroupList must be "+
                "unique among RrcUeCfg instances under parent Rrc instance.

                Combination of a UE group identifier in UeGroupList and empty "+
                "prefUeGroupList must be unique among RrcUeCfg instances under parent "+
                "Rrc instance.";
            yexte:takes-effect
                "New connection";
            must "count(../prefUeGroupList) &gt; 0 or
                  count(../../../RrcUeCfg/attributes[ueGroupList = current() and count(prefUeGroupList) = 0]) &lt;= 1" {
                error-message
                    "Only one RrcUeCfg instance under an Rrc can combine a specific UE group identifier in attribute ueGroupList with an empty prefUeGroupList.";
            }
            tailf:info 'Takes effect: New connection, Dependencies: Combinations of pair of preference UE group Identifier in prefUeGroupList and UE group identifier in ueGroupList must be unique among RrcUeCfg instances under parent Rrc instance.

                Combination of a UE group identifier in UeGroupList and empty prefUeGroupList must be unique among RrcUeCfg instances under parent Rrc instance, UE group list. List of UE group identifiers. If empty, the MO instance matches all UE group identifiers.';
        }
    }

    augment "/me3gpp:ManagedElement/gnbcucp3gpp:GNBCUCPFunction/ueccvcucp:UeCC/rrcvcucp:Rrc" {
        list RrcUeCfg {
            description
                "Configuration of RRC UE groups.

                MO instance RrcUeCfg=Base is created automatically when parent " +
                "MO is created, unless created manually in the same transaction " +
                "as parent MO.

                Attributes prefUeGroupList and ueGroupList must be empty in " +
                "instance RrcUeCfg=Base but cannot all be empty in other " +
                "instances of RrcUeCfg under same parent Rrc.";
            key id;
            max-elements 8;
            container attributes {
                uses RrcUeCfgGrp;
                uses commontypes:UserLabelGrp;
            }
            uses top3gpp:Top_Grp;
            yexte:precondition
                "RrcUeCfg=Base instance can only be created in the same " +
                "transaction as parent MO and must not be deleted unless parent " +
                "MO is deleted. Other instances can be created and deleted " +
                "manually.

                Maximum 7 RrcUeCfg instances, with RDN different from Base, " +
                "can be created.";

            must "count(../RrcUeCfg) &lt; 8 or
                  count(../RrcUeCfg/id[. = 'Base']) = 1" {
                error-message
                    "Maximum 7 RrcUeCfg instances under an Rrc can be created with RDN different from Base.";
            }

            must "./id != 'Base' or ( count(./attributes/prefUeGroupList) = 0 and count(./attributes/ueGroupList) = 0 )" {
                error-message
                    "prefUeGroupList and ueGroupList must be empty in the Base Configuration Instance.";
            }

            must "./id = 'Base' or not( count(./attributes/prefUeGroupList) = 0 and count(./attributes/ueGroupList) = 0 )" {
                error-message
                    "prefUeGroupList and ueGroupList can only be empty in the Base Configuration Instance.";
            }

            must "count(../RrcUeCfg/attributes[prefUeGroupList = current()/attributes/prefUeGroupList  and ueGroupList = current()/attributes/ueGroupList] ) &lt;= 1" {
                error-message
                    "The combinations of a pair of ueGroupId and prefUeGroupId in ueGroupList and prefUeGroupList must be unique among RrcUeCfg under an Rrc";
            }
            tailf:info 'Precondition: RrcUeCfg=Base instance can only be created in the same transaction as parent MO and must not be deleted unless parent MO is deleted. Other instances can be created and deleted manually.

                Maximum 7 RrcUeCfg instances, with RDN different from Base, can be created, Configuration of RRC UE groups. MO instance RrcUeCfg=Base is created automatically when parent MO is created, unless created manually in the same transaction as parent MO. Attributes prefUeGroupList and ueGroupList must be empty in instance RrcUeCfg=Base but cannot all be empty in other instances of RrcUeCfg under same parent Rrc.';
        }
    }
}
