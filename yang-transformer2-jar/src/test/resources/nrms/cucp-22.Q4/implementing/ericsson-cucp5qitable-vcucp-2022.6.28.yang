// Generated by eyang-preprocessor (1.22.0-48 2022-01-20 09:10:06 CET) on Jun 30, 2022, 8:31:35 AM
module ericsson-cucp5qitable-vcucp {
    yang-version 1.1;
    namespace urn:rdns:com:ericsson:oammodel:ericsson-cucp5qitable-vcucp;
    prefix cucp5qitablevcucp;

    import tailf-common {
        prefix tailf;
    }
    import _3gpp-common-managed-element {
        prefix me3gpp;
    }
    import _3gpp-common-top {
        prefix top3gpp;
    }
    import _3gpp-nr-nrm-gnbcucpfunction {
        prefix gnbcucp3gpp;
    }
    import ericsson-yang-extensions {
        prefix yexte;
    }

    organization
      "Ericsson AB";
    contact
      "Ericsson first line support via email";
    description
      "QoS configuration corresponding to 3GPP-defined and operator-defined 5QI profiles for the Ericsson vCU-CP.

       Copyright (c) 2021-2022 Ericsson AB. All rights reserved.";

    revision 2022-06-28 {
        description
            "Removed module-status preliminary.";
        yexte:version 0;
        yexte:release 3;
        yexte:correction 0;
        reference
            "RFC 7950: The YANG 1.1 Data Modeling Language";
    }

    revision 2022-03-14 {
        description
          "Updated description for CUCP5qiTable.
          Updated dependecies for default5qiTable.";
        yexte:version 0;
        yexte:release 2;
        yexte:correction 1;
        reference
          "RFC 7950: The YANG 1.1 Data Modeling Language";
    }

    revision 2021-07-09 {
        description
          "Add attribute default5qiTable, update description and add must statement.";
        yexte:version 0;
        yexte:release 2;
        yexte:correction 0;
        reference
          "RFC 7950: The YANG 1.1 Data Modeling Language";
    }

    revision 2021-03-27 {
        description
          "Add attributes on ericsson-cucp5qitable-vcucp.";
        yexte:version 0;
        yexte:release 1;
        yexte:correction 0;
        reference
          "RFC 7950: The YANG 1.1 Data Modeling Language";
    }

    grouping CUCP5qiTableGrp {
        description
          "Represents the CUCP5qiTable IOC.";

        leaf default5qiTable {
            description
                "Indicates that the CUCP5qiTable instance is a default 5QI table.

                The default 5QI table will be used when no CUCP5qiTable has been "
                + "configured for a resource partition.";
            type boolean;
            default false;
            yexte:dependencies
                "Only one CUCP5qiTable instance can have the attribute default5qiTable set to true.";
            yexte:takes-effect
                "New connection";
            tailf:info 'Takes effect: New connection, Dependencies: Only one CUCP5qiTable instance can have the attribute default5qiTable set to true, Indicates that the CUCP5qiTable instance is a default 5QI table. The default 5QI table will be used when no CUCP5qiTable has been configured for a resource partition.';
        }
    }

    augment "/me3gpp:ManagedElement/gnbcucp3gpp:GNBCUCPFunction" {
        list CUCP5qiTable {
            description
                "Mapping from 5G QoS Identifier to parameters that have impact on QoS.

                At least one CUCP5qi MO instance must be created in the same "+
                "transaction when a CUCP5qiTable is created.";
            key id;
            max-elements 36;
            uses top3gpp:Top_Grp;
            must "count(../CUCP5qiTable/attributes/default5qiTable[.='true']) = 1" {
                error-message
                  "One and only one CUCP5qiTable must be configured as default (default5qiTable=true).";
            }
            container attributes {
                uses CUCP5qiTableGrp;
            }
        }
    }
}
