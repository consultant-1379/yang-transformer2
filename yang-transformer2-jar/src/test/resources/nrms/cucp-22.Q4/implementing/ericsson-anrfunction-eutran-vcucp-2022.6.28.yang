// Generated by eyang-preprocessor (1.22.0-48 2022-01-20 09:10:06 CET) on Jun 30, 2022, 8:31:35 AM
module ericsson-anrfunction-eutran-vcucp {
    yang-version 1.1;
    namespace "urn:rdns:com:ericsson:oammodel:ericsson-anrfunction-eutran-vcucp";
    prefix anrfunctioneutran;

    import _3gpp-common-managed-element {
        prefix "me3gpp";
    }
    import _3gpp-nr-nrm-gnbcucpfunction {
        prefix "gnbcucp3gpp";
    }
    import ericsson-anrfunction-vcucp {
        prefix "anrfunction";
    }
    import _3gpp-common-top {
        prefix "top3gpp";
    }
    import ericsson-yang-extensions {
        prefix "yexte";
    }

    organization
        "Ericsson AB";
    contact
        "Ericsson first line support via email";
    description
        "The module defines the AnrFunctionEUtran data model for the Ericsson vCU-CP.

        Copyright (c) 2022 Ericsson AB. All rights reserved.";

    revision 2022-06-28 {
        description
            "Removed module-status preliminary.
             Removed preliminary status from AnrFunctionEUtran.";
        yexte:version 0;
        yexte:release 2;
        yexte:correction 0;
        reference
            "RFC 7950: The YANG 1.1 Data Modeling Language";
    }

    revision 2022-03-14 {
        description
            "Initial version of the AnrFunctionEUtran model.";
        yexte:version 0;
        yexte:release 1;
        yexte:correction 0;
        reference
            "RFC 7950: The YANG 1.1 Data Modeling Language";
    }

    grouping AnrFunctionEUtranGrp {
        description
            "Represents the AnrFunctionEUtran IOC.";

        leaf anrCgiMeasEUtranEnabled {
            description
              "Whether ANR with CGI measurement for E-UTRAN is enabled.";
            type boolean;
            default false;
        }
    }

    augment "/me3gpp:ManagedElement/gnbcucp3gpp:GNBCUCPFunction/anrfunction:AnrFunction" {
        list AnrFunctionEUtran {
            description
              "E-UTRAN ANR functions.

              The RDN of this MO must always be AnrFunctionEUtran=1.";
            key id;
            max-elements 1;
            uses top3gpp:Top_Grp {
                refine id {
                    must '. = "1"' {
                        error-message
                          "The RDN of this MO must always be AnrFunctionEUtran=1";
                    }
                }
            }
            container attributes {
                uses AnrFunctionEUtranGrp;
            }
        }
    }
}
