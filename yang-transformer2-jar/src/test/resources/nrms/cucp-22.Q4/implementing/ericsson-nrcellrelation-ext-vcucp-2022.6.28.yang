// Generated by eyang-preprocessor (1.22.0-48 2022-01-20 09:10:06 CET) on Jun 30, 2022, 8:31:41 AM
module ericsson-nrcellrelation-ext-vcucp {
    yang-version 1.1;
    namespace urn:rdns:com:ericsson:oammodel:ericsson-nrcellrelation-ext-vcucp;
    prefix nrcellrel3gppext;

    import tailf-common {
        prefix tailf;
    }
    import _3gpp-common-managed-element {
        prefix me3gpp;
    }
    import _3gpp-nr-nrm-gnbcucpfunction {
        prefix gnbcucp3gpp;
    }
    import _3gpp-nr-nrm-nrcellcu {
        prefix nrcellcu3gpp;
    }
    import _3gpp-nr-nrm-nrfreqrelation {
        prefix nrfreqrel3gpp;
    }
    import _3gpp-nr-nrm-nrcellrelation {
        prefix nrcellrel3gpp;
    }
    import _3gpp-common-yang-extensions {
        prefix yext3gpp;
    }
    import ericsson-nrnetwork-vcucp {
        prefix nrnetwork;
    }
    import ericsson-externalgnbcucpfunction-vcucp {
        prefix externalgnbcucpfunctionvcucp;
    }
    import ericsson-nrcellcu-dev-vcucp {
        prefix nrcellcu3gppdev;
    }
    import ericsson-externalnrcellcu-vcucp {
        prefix externalnrcellcu;
    }
    import ericsson-yang-extensions {
        prefix yexte;
    }
    import ericsson-common-types-vcucp {
        prefix commontypes;
    }
    import ericsson-notifications {
        prefix notife;
    }

    organization
      "Ericsson AB";
    contact
      "Ericsson first line support via email";
    description
      "The module defines the NRCellRelation data model extensions for the Ericsson vCU-CP.

       Copyright (c) 2021-2022 Ericsson AB. All rights reserved.";

    revision 2022-06-28 {
        description
            "Removed module-status preliminary.";
        yexte:version 2;
        yexte:release 1;
        yexte:correction 0;
        reference
            "RFC 7950: The YANG 1.1 Data Modeling Language";
    }

    revision 2022-03-14 {
        description
          "Updated description of NRCellRelation.
          Updated dependencies of adjacentNRCellRef.
          Updated description and dependencies of nRFreqRelationRef";
        yexte:version 2;
        yexte:release 0;
        yexte:correction 1;
        reference
          "RFC 7950: The YANG 1.1 Data Modeling Language";
    }

    revision 2021-11-07 {
        description
          "Mark createdBy obsolete.
          Add enum E5_MAND_CAP_MISMATCH to CaStatusCause.
          Update description for nRFreqRelationRef, and remove dependencies tag and must rule.";
        yexte:version 2;
        yexte:release 0;
        yexte:correction 0;
        reference
          "RFC 7950: The YANG 1.1 Data Modeling Language";
    }

    revision 2021-06-09 {
        description
          "Add must rule to adjacentNRCellRef and nRFreqRelationRef.
           Changed error messages for must statements.";
        yexte:version 1;
        yexte:release 1;
        yexte:correction 2;
        reference
          "RFC 7950: The YANG 1.1 Data Modeling Language";
    }

    revision 2021-06-03 {
        description
          "Disable notifications for timeOfCreation.";
        yexte:version 1;
        yexte:release 1;
        yexte:correction 1;
        reference
          "RFC 7950: The YANG 1.1 Data Modeling Language";
    }

    revision 2021-05-06 {
        description
          "Remove is-system-created and restricted extensions.
           Add yext3gpp:inVariant to adjacentNRCellRef and nRFreqRelationRef.";
        yexte:version 1;
        yexte:release 1;
        yexte:correction 0;
        reference
          "RFC 7950: The YANG 1.1 Data Modeling Language";
    }

    revision 2021-03-29 {
        description
          "Add attributes on _3gpp-nr-nrm-nrcellrelation";
        yexte:version 1;
        yexte:release 0;
        yexte:correction 0;
        reference
          "RFC 7950: The YANG 1.1 Data Modeling Language";
    }

    typedef CaStatusCause {
        description
          "Additional status information when caStatusActive is false.";

        type enumeration {
            enum E5_TUNNEL_CAP {
                value 0;
                description
                  "E5 tunnel capacity is reached.";
            }

            enum E5_TUNNEL_CAP_REMOTE {
                value 1;
                description
                  "E5 tunnel capacity is reached on remote host.";
            }

            enum E5_CELL_ALLOC_CAP {
                value 2;
                description
                  "E5 cell allocation capacity is reached.";
            }

            enum E5_CELL_ALLOC_CAP_REMOTE {
                value 3;
                description
                  "E5 cell allocation capacity is reached on remote host.";
            }

            enum E5_SW_VERSION_MISMATCH {
                value 4;
                description
                  "Software version mismatch detected towards external gNodeB-DU partner during E5 setup.";
            }

            enum E5_MAND_CAP_MISMATCH {
                value 5;
                description
                  "E5 mandatory capability mismatch detected towards external "+
                  "gNodeB-DU partner during E5 setup.";
            }
        }
    }

    typedef SupportedCoverage {
        description
          "Coverage relation.";

        type enumeration {
            enum NONE {
                value 0;
                description
                  "No coverage relation between cells.";
            }

            enum COVERS {
                value 1;
                description
                  "Related cell covers current cell.";
            }

            enum OVERLAP {
                value 2;
                description
                  "Related cell and current cell has approximately the same coverage area.";
            }

            enum CONTAINED_IN {
                value 3;
                description
                  "Related cell is contained in current cell.";
            }
        }
    }
    typedef SCellCandidate {
        description
          "SCell candidate status.";
        type enumeration {
            enum NOT_ALLOWED {
                value 0;
                description
                  "Not allowed as SCell candidate.";
            }

            enum ALLOWED {
                value 1;
                description
                  "Allowed as SCell candidate.";
            }
        }
    }

    deviation "/me3gpp:ManagedElement/gnbcucp3gpp:GNBCUCPFunction/nrcellcu3gpp:NRCellCU/nrcellrel3gpp:NRCellRelation" {
        deviate add {
            yexte:updated-description
              "Handover relationship between NR cell and a neighboring NR cell.

              This MO is updated or deleted automatically when configuration "+
              "message over F1, Xn or X2 interface is received, with changed "+
              "frequency of neighbor cell.
              If matching NRFreqRelation MO instance exists, then "+
              "nRFreqRelationRef is updated. Otherwise, NRCellRelation MO "+
              "instance is deleted.
              See dependencies of nRFreqRelationRef.";
            max-elements 512;
        }
    }

    deviation "/me3gpp:ManagedElement/gnbcucp3gpp:GNBCUCPFunction/nrcellcu3gpp:NRCellCU/nrcellrel3gpp:NRCellRelation/nrcellrel3gpp:attributes/nrcellrel3gpp:adjacentNRCellRef" {
        deviate add {
            must "re-match(current(), concat('ManagedElement=', ../../../../../me3gpp:id, ',.*')) and
                  re-match(current(), concat('.*GNBCUCPFunction=', ../../../../gnbcucp3gpp:id, ',.*')) and
                  (
                    ( re-match(current(),'ManagedElement=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,GNBCUCPFunction=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,NRNetwork=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,ExternalGNBCUCPFunction=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,ExternalNRCellCU=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?') and
                      count(../../../../nrnetwork:NRNetwork[re-match(current(), concat('.*NRNetwork=', nrnetwork:id, ',.*'))]/externalgnbcucpfunctionvcucp:ExternalGNBCUCPFunction[re-match(current(), concat('.*ExternalGNBCUCPFunction=', externalgnbcucpfunctionvcucp:id, ',.*'))]/externalnrcellcu:ExternalNRCellCU[re-match(current(), concat('.*ExternalNRCellCU=', externalnrcellcu:id))]) &gt; 0
                    )
                    or
                    ( re-match(current(),'ManagedElement=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,GNBCUCPFunction=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,NRCellCU=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?') and
                      count(../../../../nrcellcu3gpp:NRCellCU[re-match(current(), concat('.*NRCellCU=', nrcellcu3gpp:id))]) &gt; 0
                    )
                  )" {
                error-message
                  "adjacentNRCellRef must refer to an NRCellCU or ExternalNRCellCU under the same GNBCUCPFunction.";
            }
            must "count(../../../nrcellrel3gpp:NRCellRelation/nrcellrel3gpp:attributes/nrcellrel3gpp:adjacentNRCellRef[current() = .]) = 1" {
                error-message
                    "Must be unique among NRCellRelations under the same NRCellCU.";
            }
            yexte:updated-description
                "Reference to an instance of NRCellCU or ExternalNRCellCU MO.";
            yext3gpp:inVariant;
            yexte:dependencies
                "Must be unique among NRCellRelations under an NRCellCU.
                See also dependencies of attribute nRFreqRelationRef.";
        }
    }

    deviation "/me3gpp:ManagedElement/gnbcucp3gpp:GNBCUCPFunction/nrcellcu3gpp:NRCellCU/nrcellrel3gpp:NRCellRelation/nrcellrel3gpp:attributes/nrcellrel3gpp:nRFreqRelationRef" {
        deviate add {
            must "re-match(current(), 'ManagedElement=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,GNBCUCPFunction=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,NRCellCU=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,NRFreqRelation=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?') and
                  re-match(current(), concat('ManagedElement=', ../../../../../me3gpp:id, ',.*')) and
                  re-match(current(), concat('.*GNBCUCPFunction=', ../../../../gnbcucp3gpp:id, ',.*')) and
                  re-match(current(), concat('.*NRCellCU=', ../../../nrcellcu3gpp:id, ',.*')) and
                  count(../../../nrfreqrel3gpp:NRFreqRelation[re-match(current(), concat('.*NRFreqRelation=', nrfreqrel3gpp:id))]) &gt; 0" {
                error-message
                  "nRFreqRelationRef must refer to an NRFreqRelation under the same NRCellCU.";
            }
            must "(
                    ../../../nrfreqrel3gpp:NRFreqRelation[re-match(current(), concat('.*NRFreqRelation=', nrfreqrel3gpp:id))]/nrfreqrel3gpp:attributes/nrfreqrel3gpp:nRFrequencyRef =
                    ../../../../nrnetwork:NRNetwork[re-match(current()/../nrcellrel3gpp:adjacentNRCellRef, concat('.*NRNetwork=', nrnetwork:id, ',.*'))]/externalgnbcucpfunctionvcucp:ExternalGNBCUCPFunction[re-match(current()/../nrcellrel3gpp:adjacentNRCellRef, concat('.*ExternalGNBCUCPFunction=', externalgnbcucpfunctionvcucp:id, ',.*'))]/externalnrcellcu:ExternalNRCellCU[re-match(current()/../nrcellrel3gpp:adjacentNRCellRef, concat('.*ExternalNRCellCU=', externalnrcellcu:id))]/externalnrcellcu:attributes/externalnrcellcu:nRFrequencyRef
                  )
                  or
                  (
                    ../../../nrfreqrel3gpp:NRFreqRelation[re-match(current(), concat('.*NRFreqRelation=', nrfreqrel3gpp:id))]/nrfreqrel3gpp:attributes/nrfreqrel3gpp:nRFrequencyRef =
                    ../../../../nrcellcu3gpp:NRCellCU[re-match(current()/../nrcellrel3gpp:adjacentNRCellRef, concat('.*,NRCellCU=', nrcellcu3gpp:id))]/nrcellcu3gpp:attributes/nrcellcu3gpp:nRFrequencyRef
                  )" {
                error-message
                    "nRFrequencyRef in NRFreqRelation MO referred by attribute "+
                    "nRFreqRelationRef must be equal to nRFrequencyRef in the NRCellCU or "+
                    "ExternalNRCellCU referred by attribute adjacentNRCellRef";
            }
            yexte:updated-description
                "Reference to an instance of NRFreqRelation MO under the same parent "+
                "NRCellCU.

                The NRFreqRelation MO instance refers to the NRFrequency MO instance "+
                "referenced by the neighboring NRCellCU or ExternalNRCellCU.";
            yext3gpp:inVariant;
            yexte:dependencies
                "The nRFrequencyRef in NRFreqRelation MO referenced by attribute "+
                "nRFreqRelationRef must be equal to nRFrequencyRef in the NRCellCU or "+
                "ExternalNRCellCU referenced by attribute nRCellRef.";
        }
    }

    deviation "/me3gpp:ManagedElement/gnbcucp3gpp:GNBCUCPFunction/nrcellcu3gpp:NRCellCU/nrcellrel3gpp:NRCellRelation/nrcellrel3gpp:attributes/nrcellrel3gpp:isHOAllowed" {
        deviate add {
            yexte:updated-description
            "Specifies if handover between the cells in this relation is allowed.";
        }
    }

    deviation "/me3gpp:ManagedElement/gnbcucp3gpp:GNBCUCPFunction/nrcellcu3gpp:NRCellCU/nrcellrel3gpp:NRCellRelation/nrcellrel3gpp:attributes/nrcellrel3gpp:isRemoveAllowed" {
        deviate replace {
            default false;
        }
        deviate add {
            yexte:updated-description
                "Whether ANR function is allowed to remove this object.

                The setting does not restrict operator removal of the object. Objects created by ANR have this parameter set to true initially.";
        }
    }

    grouping NRCellRelationVCUCPGrp {
        description
          "Represents the NRCellRelation IOC.";

        leaf caStatusActive {
            description
              "Active status of carrier aggregation for this NRCellRelation.";
            config false;
            type boolean;
        }

        leaf caStatusInfo {
            description
              "Additional status information when caStatusActive is false.
               Empty when caStatusActive is true or additional status information "
            + "is unavailable.";
            config false;
            type CaStatusCause;
        }

        leaf cellIndividualOffsetNR {
            description
              "Offset value for neighbor cell.
               Used when UE is in connected mode.";
            type int32 {
                range "-24|-22|-20|-18|-16|-14|-12|-10|-8|-6..6|8|10|12|14|16|18|20|22|24";
            }
            default 0;
            units dB;
            reference
              "3GPP TS 38.331";
            yexte:takes-effect
                "New connection";
            tailf:info 'Takes effect: New connection, Offset value for neighbor cell. Used when UE is in connected mode.';
        }

        leaf coverageIndicator {
            description
              "Coverage indication.
               Relation between coverage area of cell referenced by nRCellRef and "
            + "current cell. Can be:
               - overlap
               - referenced cell contains current cell
               - current cell contains reference cell";
            type SupportedCoverage;
            default NONE;
        }

        leaf createdBy {
            description
              "Whether MO is created by the ANR function or operator.";
            config false;
            type commontypes:CreatedByGutran;
            status obsolete {
                yexte:status-information
                "Since 21.Q2. Planned to be removed.";
            }
            tailf:info 'Status Info: Since 21.Q2. Planned to be removed, Obsolete, Whether MO is created by the ANR function or operator.';
        }

        leaf sCellCandidate {
            description
              "SCell candidate status.

               Whether cell referenced by nRCellRef can be SCell for carrier "
            + "aggregation.";
            type SCellCandidate;
            default NOT_ALLOWED;
        }

        leaf timeOfCreation {
            description
              "Time and date of MO creation.
               Format: YYYY-MM-DD HH:MM:SS.";
            config false;
            type string {
                length "0..19";
            }
            notife:notifiable-state-data false;
            tailf:meta-data notife:notifiable-state-data {
                tailf:meta-value false;
            }
        }
    }

    augment "/me3gpp:ManagedElement/gnbcucp3gpp:GNBCUCPFunction/nrcellcu3gpp:NRCellCU/nrcellrel3gpp:NRCellRelation/nrcellrel3gpp:attributes" {
        description
          "Adds Ericsson attributes to 3gpp NRCellRelation.";
        uses NRCellRelationVCUCPGrp;
    }
}
