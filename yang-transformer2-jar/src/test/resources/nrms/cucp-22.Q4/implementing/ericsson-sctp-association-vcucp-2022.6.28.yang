// Generated by eyang-preprocessor (1.22.0-48 2022-01-20 09:10:06 CET) on Jun 30, 2022, 8:31:44 AM
module ericsson-sctp-association-vcucp {
    yang-version 1.1;
    namespace urn:rdns:com:ericsson:oammodel:ericsson-sctp-association-vcucp;
    prefix sctpassvcucp;

    import tailf-common {
        prefix tailf;
    }
    import _3gpp-common-managed-element {
        prefix me3gpp;
    }
    import _3gpp-common-top {
        prefix top3gpp;
    }
    import ericsson-sctp-association-vcu {
        prefix sctpass;
    }
    import ericsson-sctp-endpoint-vcucp {
        prefix sctpepvcucp;
    }
    import ericsson-transport-service-vcucp {
        prefix transservice;
    }
    import ericsson-yang-extensions {
        prefix yexte;
    }

    organization
        "Ericsson AB";
    contact
        "Ericsson first line support via email";
    description
        "The module defines the SctpAssociation data model for the Ericsson vCU-CP.

         Copyright (c) 2021-2022 Ericsson AB. All rights reserved.";

    revision 2022-06-28 {
        description
            "Removed module-status preliminary.";
        yexte:version 0;
        yexte:release 2;
        yexte:correction 0;
        reference
            "RFC 7950: The YANG 1.1 Data Modeling Language";
    }

    revision 2021-01-14 {
        description
            "Initial version of the SctpAssociation model.";
        yexte:version 0;
        yexte:release 1;
        yexte:correction 0;
        reference
            "RFC 7950: The YANG 1.1 Data Modeling Language";
    }

    augment "/me3gpp:ManagedElement/transservice:TransportService/sctpepvcucp:SctpEndpoint" {
        list SctpAssociation {
            description
                "The SctpAssociation is a representation of the protocol relationship between two SCTP Endpoints.

                 It is composed of the two SCTP Endpoints and protocol state information.";
            key id;
            uses top3gpp:Top_Grp;
            container attributes {
                uses sctpass:SctpAssociationGrp;
            }
            yexte:is-system-created;
            tailf:meta-data yexte:is-system-created;
        }
    }
}
