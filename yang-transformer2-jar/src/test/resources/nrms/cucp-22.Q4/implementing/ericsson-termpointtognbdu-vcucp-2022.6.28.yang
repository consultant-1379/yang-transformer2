// Generated by eyang-preprocessor (1.22.0-48 2022-01-20 09:10:06 CET) on Jun 30, 2022, 8:31:44 AM
module ericsson-termpointtognbdu-vcucp {
    yang-version 1.1;
    namespace urn:rdns:com:ericsson:oammodel:ericsson-termpointtognbdu-vcucp;
    prefix tptognbdu;

    import tailf-common {
        prefix tailf;
    }
    import _3gpp-common-managed-element {
        prefix me3gpp;
    }
    import _3gpp-nr-nrm-gnbcucpfunction {
        prefix gnbcucp3gpp;
    }
    import _3gpp-common-top {
        prefix top3gpp;
    }
    import _3gpp-common-yang-types {
        prefix types3gpp;
    }
    import ericsson-yang-extensions {
        prefix yexte;
    }
    import ericsson-yang-types {
        prefix "typese";
    }
    import ietf-inet-types {
        prefix inet;
    }
    import ericsson-notifications {
        prefix notife;
    }

    organization
        "Ericsson AB";
    contact
        "Ericsson first line support via email";
    description
        "The module defines the TermPointToGNBDU data model for the Ericsson vCU-CP.

         Copyright (c) 2021-2022 Ericsson AB. All rights reserved.";

    revision 2022-06-28 {
        description
            "Removed module-status preliminary.";
        yexte:version 2;
        yexte:release 2;
        yexte:correction 0;
        reference
            "RFC 7950: The YANG 1.1 Data Modeling Language";
    }

    revision 2021-07-27 {
        description
            "Bug Fix, leaf-list state notifiable compatibility issue. Adds extension notife:notifiable-state-data false to availabilityStatus.";
        yexte:version 2;
        yexte:release 1;
        yexte:correction 0;
        reference
            "RFC 7950: The YANG 1.1 Data Modeling Language";
    }

    revision 2021-04-06 {
        description
            "Updated Ericsson MO description.";
        yexte:version 1;
        yexte:release 0;
        yexte:correction 1;
        reference
            "RFC 7950: The YANG 1.1 Data Modeling Language";
    }

    revision 2021-01-20 {
        description
            "Add extensions is-system-created.";
        yexte:version 1;
        yexte:release 0;
        yexte:correction 0;
        reference
            "RFC 7950: The YANG 1.1 Data Modeling Language";
    }

    revision 2021-01-11 {
        description
	    "Initial version of the TermPointToGNBDU model";
        yexte:version 0;
        yexte:release 1;
        yexte:correction 0;
        reference
	    "RFC 7950: The YANG 1.1 Data Modeling Language";
    }

    grouping TermPointToGNBDUGrp {
        description "Models an F1-C link to a gNodeB-DU.";
        reference "Ericsson documentation";

        leaf-list availabilityStatus {
            description
                "The availability status.

                It contains details about operationalState.";
            config false;
            notife:notifiable-state-data false;
            type typese:avail-status;
            reference
                "ITU-T Rec. X.731";
            tailf:meta-data notife:notifiable-state-data {
                tailf:meta-value false;
            }
        }

        leaf gNBDUId {
            description "Distributed Unit (DU) Identity within the gNodeB.";
            config false;
            type int64 {
                range "0..68719476735";
            }
            reference "3GPP TS 38.473";
        }

        leaf gNBDUName {
            description "Distributed Unit (DU) name.";
            config false;
            type string {
                length "1..150";
            }
            reference "3GPP TS 38.473";
        }

        leaf operationalState {
            description
                "Operational state of the F1-C interface. Indicates
                whether the resource is installed and partially or fully operable
               (ENABLED) or the resource is not installed or not operable
               (DISABLED).";
            config false;
            type types3gpp:OperationalState;
            reference "ITU-T Rec. X.731";
        }

        leaf usedIpAddress {
            description
                "Destination address used in underlying connection.

                Contains address of latest successful F1-C setup. IP address can be "+
                "an IPv4 or an IPv6 address.";
            config false;
            type inet:ip-address-no-zone;
        }
    }

    augment "/me3gpp:ManagedElement/gnbcucp3gpp:GNBCUCPFunction" {

        list TermPointToGNBDU {
            description
                "Models an F1-C link to a gNodeB-DU.

                Created by the system when F1-C link is set up.
                Deleted by the system at node restart.

                The RDN of this MO is TermPointToGNBDU=[gNBDUId].";
            key id;
            uses top3gpp:Top_Grp;
            container attributes {
                uses TermPointToGNBDUGrp;
            }
            yexte:is-system-created;
            tailf:meta-data yexte:is-system-created;
        }
    }
}
