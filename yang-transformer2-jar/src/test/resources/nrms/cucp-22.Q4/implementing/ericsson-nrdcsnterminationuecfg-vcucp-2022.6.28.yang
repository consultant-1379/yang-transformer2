// Generated by eyang-preprocessor (1.22.0-48 2022-01-20 09:10:06 CET) on Jun 30, 2022, 8:31:41 AM
module ericsson-nrdcsnterminationuecfg-vcucp {
    yang-version 1.1;
    namespace urn:rdns:com:ericsson:oammodel:ericsson-nrdcsnterminationuecfg-vcucp;
    prefix nrdcsnterminationuecfg;

    import tailf-common {
        prefix tailf;
    }
    import _3gpp-common-managed-element {
        prefix me3gpp;
    }
    import _3gpp-nr-nrm-gnbcucpfunction {
        prefix gnbcucp3gpp;
    }
    import _3gpp-common-top {
        prefix top3gpp;
    }
    import ericsson-nrdcsntermination-vcucp {
        prefix nrdcsntermination;
    }
    import ericsson-yang-extensions {
        prefix yexte;
    }

    organization
      "Ericsson AB";
    contact
      "Ericsson first line support via email";
    description
      "The module defines the NrdcSnTerminationUeCfg data model for the Ericsson vCU-CP.

       Copyright (c) 2021-2022 Ericsson AB. All rights reserved.";

    revision 2022-06-28 {
        description
            "Removed module-status preliminary.";
        yexte:version 0;
        yexte:release 4;
        yexte:correction 0;
        reference
            "RFC 7950: The YANG 1.1 Data Modeling Language";
    }

    revision 2022-06-16 {
        description
          "Updated description and precondition for the NrdcSnTerminationUeCfg MO list.";
        yexte:version 0;
        yexte:release 3;
        yexte:correction 1;
        reference
          "RFC 7950: The YANG 1.1 Data Modeling Language";
    }

    revision 2022-05-11 {
        description
          "Increased cardinality from 1 to 32";
        yexte:version 0;
        yexte:release 3;
        yexte:correction 0;
        reference
          "RFC 7950: The YANG 1.1 Data Modeling Language";
    }

    revision 2022-03-14 {
        description
          "Updated description of NrdcSnTerminationUeCfg and added precondition.
          Added dependencies to nrdcSnTermAllowed";
        yexte:version 0;
        yexte:release 2;
        yexte:correction 1;
        reference
          "RFC 7950: The YANG 1.1 Data Modeling Language";
    }

    revision 2021-11-05 {
        description
          "Update description for nrdcSnTermAllowed and preliminary status removed.";
        yexte:version 0;
        yexte:release 2;
        yexte:correction 0;
        reference
          "RFC 7950: The YANG 1.1 Data Modeling Language";
    }

    revision 2021-04-14 {
        description
          "Initial version of the NrdcSnTerminationUeCfg model.";
        yexte:version 0;
        yexte:release 1;
        yexte:correction 0;
        reference
          "RFC 7950: The YANG 1.1 Data Modeling Language";
    }

    grouping NrdcSnTerminationUeCfgGrp {
        description
          "Represents the NrdcSnTerminationUeCfg IOC.";

        leaf nrdcSnTermAllowed {
            description
              "Whether Secondary Node termination for NR-DC is allowed for each ARP.

              Bitmap [1-15], each bit corresponds to one ARP value. First or "+
              "rightmost bit is for ARP1, second bit is for ARP2, and so on.
              Each bit has one of the following the values:
              0: Secondary Node termination is not allowed for this ARP.
              1: Secondary Node termination is allowed for this ARP.
              Bitmap is displayed as decimal value { 0..32767 }.

              Examples of decimal value definitions of certain ARP combinations "+
              "for allowing Secondary Node termination:
              * 0: Not allowed for any ARP.
              * 1: Allowed for ARP1.
              * 2: Allowed for ARP2.
              * 3: Allowed for ARP1 and ARP2.
              * 4: Allowed for ARP3.
              * 5: Allowed for ARP1 and ARP3.
              * 15: Allowed for ARP1, ARP2, ARP3 and ARP4.
              * 128: Allowed for ARP8.
              * 256: Allowed for ARP9.
              * 4097: Allowed for ARP1 and ARP13.
              * 32767: Allowed for all ARPs.";
            type uint16 {
                range "0..32767";
            }
            default 0;
            yexte:dependencies
                "Must be set to 0 in NrdcSnTerminationUeCfg MO instances under MO "+
                "instance NrdcSnTermination=SnTerminationProhibited.";
            yexte:takes-effect
                "New connection";
            tailf:info 'Takes effect: New connection, Dependencies: Must be set to 0 in NrdcSnTerminationUeCfg MO instances under MO instance NrdcSnTermination=SnTerminationProhibited, Whether Secondary Node termination for NR-DC is allowed for each ARP. Bitmap [1-15], each bit corresponds to one ARP value. First or rightmost bit is for ARP1, second bit is for ARP2, and so on. Each bit has one of the following the values: 0: Secondary Node termination is not allowed for this ARP. 1: Secondary Node termination is allowed for this ARP. Bitmap is displayed as decimal value { 0..32767 }. Examples of decimal value definitions of certain ARP combinations for allowing Secondary Node termination: * 0: Not allowed for any ARP. * 1: Allowed for ARP1. * 2: Allowed for ARP2. * 3: Allowed for ARP1 and ARP2. * 4: Allowed for ARP3. * 5: Allowed for ARP1 and ARP3. * 15: Allowed for ARP1, ARP2, ARP3 and ARP4. * 128: Allowed for ARP8. * 256: Allowed for ARP9. * 4097: Allowed for ARP1 and ARP13. * 32767: Allowed for all ARPs.';
        }
    }

    augment "/me3gpp:ManagedElement/gnbcucp3gpp:GNBCUCPFunction/nrdcsntermination:NrdcSnTermination" {

        list NrdcSnTerminationUeCfg {
            description
                "UE configuration of Secondary Node termination for NR-DC.

                 MO instance NrdcSnTerminationUeCfg=Base is created automatically when parent MO is created, "+
                "unless created manually in the same transaction as parent MO.";
            yexte:precondition
                "NrdcSnTerminationUeCfg=Base MO instance can only be created in the same "+
                "transaction as parent MO and cannot be deleted unless parent MO is deleted. "+
                "Other instances can be created and deleted manually.
                 Maximum 31 NrdcSnTerminationUeCfg instances with RDN different from Base can be created.";
            key id;
            max-elements 32;
            uses top3gpp:Top_Grp;
            container attributes {
                uses NrdcSnTerminationUeCfgGrp;
            }
            must "./id='Base' or ../nrdcsntermination:id != 'SnTerminationProhibited'" {
                error-message
                    "RDN value must be Base for NrdcSnTerminationUeCfg instance under NrdcSnTermination=SnTerminationProhibited.";
            }
            must "./attributes/nrdcSnTermAllowed=0 or ../nrdcsntermination:id != 'SnTerminationProhibited'" {
                error-message
                    "NrdcSnTerminationUeCfg under NrdcSnTermination=SnTerminationProhibited instance must have attribute nrdcSnTermAllowed set to 0.";
            }

            tailf:info 'Precondition: NrdcSnTerminationUeCfg=Base MO instance can only be created in the same transaction as parent MO and cannot be deleted unless parent MO is deleted. Other instances can be created and deleted manually.
                 Maximum 31 NrdcSnTerminationUeCfg instances with RDN different from Base can be created, UE configuration of Secondary Node termination for NR-DC. MO instance NrdcSnTerminationUeCfg=Base is created automatically when parent MO is created, unless created manually in the same transaction as parent MO.';
        }
    }
}
