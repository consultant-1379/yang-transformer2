// Generated by eyang-preprocessor (1.22.0-48 2022-01-20 09:10:06 CET) on Jun 30, 2022, 8:31:38 AM
module ericsson-inactivityprofileuecfg-vcucp {
    yang-version 1.1;
    namespace urn:rdns:com:ericsson:oammodel:ericsson-inactivityprofileuecfg-vcucp;
    prefix inactivityprofileuecfgvcucp;

    import tailf-common {
        prefix tailf;
    }
    import _3gpp-common-managed-element {
        prefix "me3gpp";
    }
    import _3gpp-nr-nrm-gnbcucpfunction {
        prefix "gnbcucp3gpp";
    }
    import _3gpp-common-top {
        prefix "top3gpp";
    }
    import ericsson-uecc-vcucp {
        prefix "ueccvcucp";
    }
    import ericsson-inactivityprofile-vcucp {
        prefix "inactivityprofilevcucp";
    }
    import ericsson-yang-extensions {
        prefix "yexte";
    }
    import ericsson-common-types-vcucp {
        prefix commontypes;
    }

    organization
      "Ericsson AB";
    contact
      "Ericsson first line support via email";
    description
      "The module defines the InactivityProfileUeCfg data model for the Ericsson vCU-CP.

       Copyright (c) 2021-2022 Ericsson AB. All rights reserved.";

    revision 2022-06-28 {
        description
            "Removed module-status preliminary.";
        yexte:version 0;
        yexte:release 3;
        yexte:correction 0;
        reference
            "RFC 7950: The YANG 1.1 Data Modeling Language";
    }

    revision 2022-03-14 {
        description
          "Correct description and precondition for InactivityProfileUeCfg.
           Added the userLabel attribute.";
        yexte:version 0;
        yexte:release 2;
        yexte:correction 0;
        reference
          "RFC 7950: The YANG 1.1 Data Modeling Language";
    }

    revision 2021-10-24 {
        description
          "Initial version of the InactivityProfileUeCfg model.";
        yexte:version 0;
        yexte:release 1;
        yexte:correction 0;
        reference
          "RFC 7950: The YANG 1.1 Data Modeling Language";
    }

    grouping InactivityProfileUeCfgGrp {
        description
          "Represents the InactivityProfileUeCfg IOC.";

        leaf-list prefUeGroupList {
            max-elements 8;
            description
                "Preference UE groups that use values in this MO instance.";
            type int32 {
                range "0..255";
            }
            yexte:dependencies
                "A combination of UE Group in ueGroupList attribute and Preference UE " +
                "Group in this attribute must be unique among InactivityProfileUeCfg " +
                "MOs.";
            yexte:takes-effect
                "New connection";
            tailf:info 'Takes effect: New connection, Dependencies: A combination of UE Group in ueGroupList attribute and Preference UE Group in this attribute must be unique among InactivityProfileUeCfg MOs, Preference UE groups that use values in this MO instance.';
        }

        leaf tInactivityTimer {
            description
                "Time NR SA UEs can be inactive before released.";
            type int32 {
                range "1..7200";
            }
            default 10;
            units s;
            yexte:takes-effect
                "New connection";
            tailf:info 'Takes effect: New connection, Time NR SA UEs can be inactive before released.';
        }

        leaf tInactivityTimerEndcSn {
            description
                "Time before inactivity is reported to master node for an EN-DC UE in " +
                "Secondary Node.";
            type int32 {
                range "1..7200";
            }
            default 5;
            units s;
            yexte:takes-effect
                "New connection";
            tailf:info 'Takes effect: New connection, Time before inactivity is reported to master node for an EN-DC UE in Secondary Node.';
        }

        leaf tInactivityTimerNrdcSn {
            description
                "Time before inactivity is reported to master node for an NR-DC UE in " +
                "Secondary Node.";
            type int32 {
                range "1..7200";
            }
            default 10;
            units s;
            yexte:takes-effect
                "New connection";
            tailf:info 'Takes effect: New connection, Time before inactivity is reported to master node for an NR-DC UE in Secondary Node.';
        }

        leaf-list ueGroupList {
            max-elements 16;
            description
                "UE groups that use values in this MO instance.";
            type int32 {
                range "0..255";
            }
            yexte:dependencies
                "A combination of UE group in this attribute and Preference UE Group "+
                "in prefUeGroupList attributes must be unique among "+
                "InactivityProfileUeCfg MOs.";
            yexte:takes-effect
                "New connection";
            tailf:info 'Takes effect: New connection, Dependencies: A combination of UE group in this attribute and Preference UE Group in prefUeGroupList attributes must be unique among InactivityProfileUeCfg MOs, UE groups that use values in this MO instance.';
        }
    }

    augment "/me3gpp:ManagedElement/gnbcucp3gpp:GNBCUCPFunction/ueccvcucp:UeCC/inactivityprofilevcucp:InactivityProfile" {
        list InactivityProfileUeCfg {
            description
              "Configuration of inactivity timer profile for UE groups.

               MO instance InactivityProfileUeCfg=Base is created "
            + "automatically when parent MO is created, unless created "
            + "manually in the same transaction as parent MO.

               Attributes prefUeGroupList and ueGroupList must be empty in "
            + "instance InactivityProfileUeCfg=Base.
               Both prefUeGroupList and ueGroupList cannot be empty in other "
            + "instances.
               A combination of an element of ueGroupList and an element of "
            + "prefUeGroupList in InactivityProfileUeCfg must be unique under "
            + "InactivityProfile.";
            key id;
            max-elements 8;
            uses top3gpp:Top_Grp;
            container attributes {
                uses InactivityProfileUeCfgGrp;
                uses commontypes:UserLabelGrp;
            }
            yexte:precondition
                "InactivityProfileUeCfg=Base instance can only be created in the"+
                "same transaction as parent MO is created and must not be deleted "+
                "unless parent MO is deleted. Other instances can be created "+
                "and deleted manually.";
            must "./id != 'Base' or ( count(./attributes/prefUeGroupList) = 0 and count(./attributes/ueGroupList) = 0 )" {
                error-message
                  "prefUeGroupList and ueGroupList must be empty in the Base Configuration Instance.";
            }
            must "./id = 'Base' or not( count(./attributes/prefUeGroupList) = 0 and count(./attributes/ueGroupList) = 0 )" {
                error-message
                  "prefUeGroupList and ueGroupList can only be empty in the Base Configuration Instance.";
            }
            must "
                count( ../InactivityProfileUeCfg/attributes[ueGroupList = current()/attributes/ueGroupList and count(prefUeGroupList) = 0 ]) &lt;= 1
                  and
                count( ../InactivityProfileUeCfg/attributes[prefUeGroupList = current()/attributes/prefUeGroupList and count(ueGroupList) = 0 ]) &lt;= 1
                  and
                count(../InactivityProfileUeCfg/attributes[prefUeGroupList = current()/attributes/prefUeGroupList  and ueGroupList = current()/attributes/ueGroupList] ) &lt;= 1" {
                error-message
                  "The combinations of a pair of ueGroupId and prefUeGroupId in ueGroupList and prefUeGroupList must be unique among InactivityProfileUeCfg under InactivityProfileUe";
            }

            must "count(../inactivityprofileuecfgvcucp:InactivityProfileUeCfg) &lt; 8 or
                  count(../inactivityprofileuecfgvcucp:InactivityProfileUeCfg/id[. = 'Base']) = 1" {
                error-message
                  "One InactivityProfileUeCfg must be configured as the Base Configuration Instance under UeMCNrFreqRelProfile.";
            }
            tailf:info 'Precondition: InactivityProfileUeCfg=Base instance can only be created in thesame transaction as parent MO is created and must not be deleted unless parent MO is deleted. Other instances can be created and deleted manually, Configuration of inactivity timer profile for UE groups. MO instance InactivityProfileUeCfg=Base is created automatically when parent MO is created, unless created manually in the same transaction as parent MO. Attributes prefUeGroupList and ueGroupList must be empty in instance InactivityProfileUeCfg=Base. Both prefUeGroupList and ueGroupList cannot be empty in other instances. A combination of an element of ueGroupList and an element of prefUeGroupList in InactivityProfileUeCfg must be unique under InactivityProfile.';
        }
    }
}
