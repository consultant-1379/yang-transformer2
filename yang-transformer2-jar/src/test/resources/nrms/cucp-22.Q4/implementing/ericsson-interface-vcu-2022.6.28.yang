// Generated by eyang-preprocessor (1.24.0-23 2022-06-22 14:11:55 CEST) on Jun 28, 2022, 10:45:18 AM
module ericsson-interface-vcu {
    yang-version 1.1;
    namespace urn:rdns:com:ericsson:oammodel:ericsson-interface-vcu;
    prefix interface;

    import ericsson-yang-extensions {
        prefix yexte;
    }

    organization
        "Ericsson AB";
    contact
        "Ericsson first line support via email";
    description
        "The module defines the abstract Interface data model for the Ericsson vCU.

         Copyright (c) 2021-2022 Ericsson AB. All rights reserved.";

    revision 2022-06-28 {
        description
            "Removed module-status preliminary.";
        yexte:version 0;
        yexte:release 2;
        yexte:correction 0;
        reference
            "RFC 7950: The YANG 1.1 Data Modeling Language";
    }

    revision 2021-01-05 {
        description
            "Initial revision.";
        yexte:version 0;
        yexte:release 1;
        yexte:correction 0;
        reference
            "RFC 7950: The YANG 1.1 Data Modeling Language";
    }

    grouping InterfaceGrp {
        description "Represents an IP termination point.";

        leaf mtu {
            description
                "Maximum Transmission Unit (MTU).
                 Real MTU is minimum of this configured value and MTU given by encapsulation.";
            type uint16 {
                range "576..9000";
            }
            default 1500;
            config false;
        }

        leaf userLabel {
            description "Label for free use.";
            type string;
            yexte:restricted;
        }
    }
}
