// Generated by eyang-preprocessor (1.22.0-48 2022-01-20 09:10:06 CET) on Jun 30, 2022, 8:31:44 AM
module ericsson-transport-service-vcucp {
    yang-version 1.1;
    namespace urn:rdns:com:ericsson:oammodel:ericsson-transport-service-vcucp;
    prefix transservice;

    import tailf-common {
        prefix tailf;
    }
    import _3gpp-common-managed-element {
        prefix me3gpp;
    }
    import _3gpp-common-top {
        prefix top3gpp;
    }
    import ericsson-transport-types-vcu {
        prefix transtypes;
    }
    import ericsson-yang-extensions {
        prefix yexte;
    }

    organization
        "Ericsson AB";
    contact
        "Ericsson first line support via email";
    description
        "The module defines the TransportService data model for the Ericsson vCU-CP.

         Copyright (c) 2021-2022 Ericsson AB. All rights reserved.";

    revision 2022-06-28 {
        description
            "Removed module-status preliminary.";
        yexte:version 0;
        yexte:release 2;
        yexte:correction 0;
        reference
            "RFC 7950: The YANG 1.1 Data Modeling Language";
    }

    revision 2021-01-13 {
        description
            "Initial version of the TransportService model.";
        yexte:version 0;
        yexte:release 1;
        yexte:correction 0;
        reference
            "RFC 7950: The YANG 1.1 Data Modeling Language";
    }

    grouping TransportServiceGrp {
        description
            "Container for common transport functions used within a vCU-CP.";

        leaf transportServiceId {
            description "Identifies this TransportService MO instance.";
            type transtypes:ReferenceId;
            mandatory true;
            config false;
        }
    }

    augment "/me3gpp:ManagedElement" {
        list TransportService {
            description
                "Container for common transport functions used within a vCU-CP.";
            key id;
            uses top3gpp:Top_Grp;
            container attributes {
                uses TransportServiceGrp;
            }
            yexte:is-system-created;
            tailf:meta-data yexte:is-system-created;
        }
    }
}
