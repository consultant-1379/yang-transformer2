// Generated by eyang-preprocessor (1.22.0-48 2022-01-20 09:10:06 CET) on Jun 30, 2022, 8:31:38 AM
module ericsson-geoswitchback-vcucp {
    yang-version 1.1;
    namespace urn:rdns:com:ericsson:oammodel:ericsson-geoswitchback-vcucp;
    prefix geoswitchbackvcucp;

    import tailf-common {
        prefix tailf;
    }
    import _3gpp-common-managed-element {
        prefix me3gpp;
    }
    import _3gpp-nr-nrm-gnbcucpfunction {
        prefix gnbcucp3gpp;
    }
    import _3gpp-common-top {
        prefix top3gpp;
    }
    import ericsson-cucpredundancy-vcucp {
        prefix cucpredundancyvcucp;
    }
    import ericsson-yang-extensions {
        prefix yexte;
    }
    import ericsson-yang-types {
        prefix "typese";
    }

    organization
        "Ericsson AB";
    contact
        "Ericsson first line support via email";
    description
        "The module defines the GeoSwitchBack data model for the Ericsson vCU-CP.

    Copyright (c) 2022 Ericsson AB. All rights reserved.";

    revision 2022-06-28 {
        description
            "Removed module-status preliminary.";
        yexte:version 0;
        yexte:release 2;
        yexte:correction 0;
        reference
            "RFC 7950: The YANG 1.1 Data Modeling Language";
    }

    revision 2022-06-16 {
        description
            "Minor changes in description for switchBackOffset and switchBackTime.";
        yexte:version 0;
        yexte:release 1;
        yexte:correction 2;
        reference
            "RFC 7950: The YANG 1.1 Data Modeling Language";
    }

    revision 2022-04-28 {
        description
            "Modify GeoSwitchBack MO description.";
        yexte:version 0;
        yexte:release 1;
        yexte:correction 1;
        reference
            "RFC 7950: The YANG 1.1 Data Modeling Language";
    }

    revision 2022-04-05 {
        description
            "Initial version of the GeoSwitchBack model.";
        yexte:version 0;
        yexte:release 1;
        yexte:correction 0;
        reference
            "RFC 7950: The YANG 1.1 Data Modeling Language";
    }

    typedef auto-switch-back {
        type enumeration {
            enum disable {
                value 1;
                description "auto switch back is disabled";
            }
            enum immediate {
                value 2;
                description "just after remote(main) GNBCUCPFunction is back to normal";
            }
            enum offset {
                value 3;
                description
            "after dedicated offset period after main is back to normal.";
            }
            enum time {
                value 4;
                description
            "switch back to main at dedicated time. If state of main is not Passive, switch back is not triggered";
            }
        }
        description "Auto Switch Back";
    }

    grouping GeoSwitchBackGrp {
        leaf autoSwitchBack {
            description
              "Type of auto switch back.
              Must configure switchBackOffset when set to offset and must configure switchBackTime when it set to time";
            default disable;
            type auto-switch-back;
            must '(current()="disable") or (current()="immediate") or (current()="offset" and count(../switchBackOffset)=1) or (current()="time" and count(../switchBackTime)=1)' {
                error-message "switchBackTime or switchBackOffset must be set when autoSwitchBack is set to time or offset.";
            }
        }

        leaf switchBackOffset {
            description
              "Offset time to switch back after main gNB-CU-CP back to normal,
              when autoSwitchBack is set to 'offset'.
              If autoSwitchBack is changed to offset and/or switchBackOffset is changed when geo-redundant gNB is active, then offset timer will be reset and restart at that point.
              Unit: minute
              When switchBackResult is false, retry after offset time.";
            type uint32 {
                range "30..720";
            }
            units minute;
        }

        leaf switchBackTime {
            description
              "Absolute time to switch back, when autoSwitchBack is set to 'time'.
              When switchBackResult is false, retry next time.
              Format: HH:MM:SS.";
            type typese:time;
        }

        leaf switchBackResult {
            description
              "Result of switch back to main";
            type typese:action-result-type;
            config false;
        }
    }

    augment "/me3gpp:ManagedElement/gnbcucp3gpp:GNBCUCPFunction/cucpredundancyvcucp:CUCPRedundancy" {
        list GeoSwitchBack {
            description
                "Geo redundancy switch back related parameters
                This MO is created automatically when CUCPRedundancy::redundancyRole is geo-redundant.
                This MO is removed automatically when CucpRedundancy type is disabled.
                The RDN of this MO is GeoSwitchBack=1";
            key id;
            max-elements 1;
            uses top3gpp:Top_Grp;
            container attributes {
                uses GeoSwitchBackGrp;
            }
            yexte:is-system-created;
            tailf:meta-data yexte:is-system-created;
        }
    }
}
