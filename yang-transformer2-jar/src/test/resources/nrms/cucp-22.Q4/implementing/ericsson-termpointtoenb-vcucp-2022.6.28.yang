// Generated by eyang-preprocessor (1.22.0-48 2022-01-20 09:10:06 CET) on Jun 30, 2022, 8:31:44 AM
module ericsson-termpointtoenb-vcucp {
    yang-version 1.1;
    namespace "urn:rdns:com:ericsson:oammodel:ericsson-termpointtoenb-vcucp";
    prefix "tptoenb";

    import tailf-common {
        prefix tailf;
    }
    import _3gpp-common-managed-element {
        prefix "me3gpp";
    }
    import _3gpp-nr-nrm-gnbcucpfunction {
        prefix "gnbcucp3gpp";
    }
    import _3gpp-common-yang-types {
        prefix "types3gpp";
    }
    import _3gpp-common-top {
        prefix "top3gpp";
    }
    import ietf-inet-types {
        prefix "inet";
    }
    import ericsson-eutranetwork-vcucp {
        prefix "eutranet";
    }
    import ericsson-externalenbfunction-vcucp {
        prefix "extenb";
    }
    import ericsson-yang-extensions {
        prefix "yexte";
    }
    import ericsson-yang-types {
        prefix "typese";
    }
    import ericsson-notifications {
        prefix notife;
    }

    organization
        "Ericsson AB";
    contact
        "Ericsson first line support via email";
    description
        "The module defines the TermPointToENB data model for the Ericsson vCU-CP.

        Copyright (c) 2021-2022 Ericsson AB. All rights reserved.";

    revision 2022-06-28 {
        description
            "Removed module-status preliminary.";
        yexte:version 3;
        yexte:release 1;
        yexte:correction 0;
        reference
            "RFC 7950: The YANG 1.1 Data Modeling Language";
    }

    revision 2021-09-06 {
        description
            "Bug Fix, remove mandatory from operationalState, and update description.";
        yexte:version 3;
        yexte:release 0;
        yexte:correction 0;
        reference
            "RFC 7950: The YANG 1.1 Data Modeling Language";
    }

    revision 2021-07-27 {
        description
            "Bug Fix, leaf-list state notifiable compatibility issue. Adds extension notife:notifiable-state-data false to availabilityStatus.";
        yexte:version 2;
        yexte:release 1;
        yexte:correction 0;
        reference
            "RFC 7950: The YANG 1.1 Data Modeling Language";
    }

    revision 2021-05-06 {
        description
            "Remove is-system-created and restricted extensions from configurable attributes";
        yexte:version 1;
        yexte:release 1;
        yexte:correction 0;
        reference
            "RFC 7950: The YANG 1.1 Data Modeling Language";
    }

    revision 2021-04-06 {
        description
            "Updated Ericsson MO description.";
        yexte:version 1;
        yexte:release 0;
        yexte:correction 1;
        reference
            "RFC 7950: The YANG 1.1 Data Modeling Language";
    }

    revision 2021-01-20 {
        description
            "Add extensions is-system-created and restricted.";
        yexte:version 1;
        yexte:release 0;
        yexte:correction 0;
        reference
            "RFC 7950: The YANG 1.1 Data Modeling Language";
    }

    revision 2021-01-11 {
        description
            "Initial version of the TermPointToENB model.";
        yexte:version 0;
        yexte:release 1;
        yexte:correction 0;
        reference "RFC 7950: The YANG 1.1 Data Modeling Language";
    }

    grouping TermPointToENBGrp {
        description "Represents the TermPointToENB IOC.";
        leaf administrativeState {
            description
                "The administrative state.

                If set to SHUTTINGDOWN, the state is immediately brought to LOCKED.";
            type types3gpp:AdministrativeState;
            default LOCKED;
            reference "ITU-T Rec. X.731";
        }

        leaf operationalState {
            description
              "The operational state.";
            type types3gpp:OperationalState;
            config false;
            reference "ITU-T Rec. X.731";
        }

        leaf-list availabilityStatus {
            description
                "The availability status.

                It contains details about operational state.";
            type typese:avail-status;
            config false;
            notife:notifiable-state-data false;
            reference
                "ITU-T Rec. X.731";
            tailf:meta-data notife:notifiable-state-data {
                tailf:meta-value false;
            }
        }

        leaf ipsecEpAddress {
            description
                "Outer IP address of X2 eNodeB neighbor in EN-DC case.

                Manual configuration is only applicable if peer node is not upgraded "+
                "to support automatic direct X2 IPsec functionality.

                Can be IPv4 or IPv6 address.

                For IPv4, input format is four fields of digits, separated by dots. "+
                "Each field can consist of three digits. Value of each field is in "+
                "range 0-255.

                For IPv6, input format is eight fields, separated by colons. Each "+
                "field consists of four hexadecimal characters. Value of each field "+
                "is in range 0-FFFF.
                Leading zeroes can be omitted in a field.
                Multiple groups of 16 bits of zeroes can be compressed to :: and can "+
                "appear once in address.";
            type inet:ip-address-no-zone;
            yexte:takes-effect
                "Next MO unlock for the change by operator.
                Outer IP address received from X2 neighbor node overwrites manual "+
                "configuration by operator, and manual configuration is ignored.";
            tailf:info 'Takes effect: Next MO unlock for the change by operator.
                Outer IP address received from X2 neighbor node overwrites manual configuration by operator, and manual configuration is ignored, Outer IP address of X2 eNodeB neighbor in EN-DC case. Manual configuration is only applicable if peer node is not upgraded to support automatic direct X2 IPsec functionality. Can be IPv4 or IPv6 address. For IPv4, input format is four fields of digits, separated by dots. Each field can consist of three digits. Value of each field is in range 0-255. For IPv6, input format is eight fields, separated by colons. Each field consists of four hexadecimal characters. Value of each field is in range 0-FFFF. Leading zeroes can be omitted in a field. Multiple groups of 16 bits of zeroes can be compressed to :: and can appear once in address.';
        }

        leaf upIpAddress {
            description
                "User plane address of X2 eNodeB neighbor in EN-DC case.

                Manual configuration is only applicable if peer node is not upgraded "+
                "to support automatic direct X2 IPsec functionality.
                Can be IPv4 or IPv6 address.

                For IPv4, input format is four fields of digits, separated by dots. "+
                "Each field can consist of three digits. Value of each field is in "+
                "range 0-255.

                For IPv6, input format is eight fields, separated by colons. Each "+
                "field consists of four hexadecimal characters. Value of each field "+
                "is in range 0-FFFF.
                Leading zeroes can be omitted in a field.
                Multiple groups of 16 bits of zeroes can be compressed to :: and can "+
                "appear once in address. Multiple groups of 16 bits of zeroes can be "+
                "compressed to :: and can appear once in address.";
            type inet:ip-address-no-zone;
            yexte:takes-effect
                "Next MO unlock for the change by operator.
                User plan address received from X2 neighbor node overwrites manual "+
                "configuration by operator, and manual configuration is ignored.";
            tailf:info 'Takes effect: Next MO unlock for the change by operator.
                User plan address received from X2 neighbor node overwrites manual configuration by operator, and manual configuration is ignored, User plane address of X2 eNodeB neighbor in EN-DC case. Manual configuration is only applicable if peer node is not upgraded to support automatic direct X2 IPsec functionality. Can be IPv4 or IPv6 address. For IPv4, input format is four fields of digits, separated by dots. Each field can consist of three digits. Value of each field is in range 0-255. For IPv6, input format is eight fields, separated by colons. Each field consists of four hexadecimal characters. Value of each field is in range 0-FFFF. Leading zeroes can be omitted in a field. Multiple groups of 16 bits of zeroes can be compressed to :: and can appear once in address. Multiple groups of 16 bits of zeroes can be compressed to :: and can appear once in address.';
        }
    }

    augment "/me3gpp:ManagedElement/gnbcucp3gpp:GNBCUCPFunction/eutranet:EUtraNetwork/extenb:ExternalENBFunction" {
        list TermPointToENB {
            description
                "Local eNodeB termination point of X2 link between gNodeB and "+
                "eNodeB.

                This MO is created automatically. Can also be created and "+
                "deleted manually.

                Created automatically when X2 interface is set up, unless it "+
                "already exists.
                Deleted automatically.

                When created automatically, the RDN of this MO is "+
                "TermPointToENB=auto1.";
            key id;
            max-elements 1;
            uses top3gpp:Top_Grp;
            container attributes {
                uses TermPointToENBGrp;
            }
        }
    }
}
