// Generated by eyang-preprocessor (1.22.0-48 2022-01-20 09:10:06 CET) on Jun 30, 2022, 8:31:44 AM
module ericsson-sctp-association-vcu {
    yang-version 1.1;
    namespace urn:rdns:com:ericsson:oammodel:ericsson-sctp-association-vcu;
    prefix sctpass;

    import tailf-common {
        prefix tailf;
    }
    import ietf-inet-types {
        prefix inet;
    }
    import ericsson-transport-types-vcu {
        prefix transtypes;
    }
    import ericsson-yang-extensions {
        prefix yexte;
    }
    import ericsson-notifications {
        prefix notife;
    }

    organization
        "Ericsson AB";
    contact
        "Ericsson first line support via email";
    description
        "The module defines the abstract SCTP Association data model for the Ericsson vCU.

    Copyright (c) 2021-2022 Ericsson AB. All rights reserved.";

    revision 2022-06-28 {
        description
            "Removed module-status preliminary.";
        yexte:version 1;
        yexte:release 2;
        yexte:correction 0;
        reference
            "RFC 7950: The YANG 1.1 Data Modeling Language";
    }

    revision 2021-07-27 {
        description
            "Bug Fix, leaf-list state notifiable compatibility issue. Adds extension notife:notifiable-state-data false to localIpAddress, remoteIpAddress.";
        yexte:version 1;
        yexte:release 1;
        yexte:correction 0;
        reference
            "RFC 7950: The YANG 1.1 Data Modeling Language";
    }

    revision 2021-02-04 {
        description
            "Updated the pmtudSctpPduSize from a leaf-list to a leaf ";
        yexte:version 0;
        yexte:release 1;
        yexte:correction 1;
        reference
            "RFC 7950: The YANG 1.1 Data Modeling Language";
    }

    revision 2021-01-08 {
        description
            "Initial revision.";
        yexte:version 0;
        yexte:release 1;
        yexte:correction 0;
        reference
            "RFC 7950: The YANG 1.1 Data Modeling Language";
    }

    typedef AssociationSecurityState {
        description "The SCTP association security state.";
        type enumeration {
            enum UNSECURED {
                value 0;
                description "SCTP association is unsecured.";
            }
            enum SECURED {
                value 1;
                description "SCTP association is secured";
            }
        }
    }

    typedef AssociationState {
        description "The SCTP association state.";
        type enumeration {
            enum CLOSED {
                value 0;
                description "SCTP association is closed.";
            }
            enum ESTABLISHED {
                value 3;
                description "SCTP association is established";
            }
        }
    }

    typedef RedundancyStatus {
        description "The SCTP redundancy status.";
        type enumeration {
            enum UNDEFINED {
                value 0;
                description "The SCTP redundancy undefined status. SCTP association is closed.";
            }
            enum DORMANT {
                value 1;
                description "All remote IP addresses are inactive.";
            }
            enum NOT_REDUNDANT {
                value 2;
                description "Redundancy addresses are unreachable. All remote IP addresses except primary are inactive.";
            }
            enum REDUNDANT {
                value 3;
                description "At least one remote IP address except primary is active.";
            }
            enum REDUNDANCY_NOT_POSSIBLE {
                value 4;
                description "SCTP association has only one remote IP address.";
            }
        }
    }

    grouping SctpAssociationGrp {
        description
            "The SctpAssociation is a representation of the protocol relationship between two SCTP Endpoints.

             It is composed of the two SCTP Endpoints and protocol state information.";

        leaf associationSecurityState {
            description "The SCTP association security state.";
            type AssociationSecurityState;
            config false;
        }

        leaf associationState {
            description "The SCTP association state.";
            type AssociationState;
            config false;
        }

        leaf-list localIpAddress {
            description "One or several local IP addresses used by the association.";
            type inet:ip-address-no-zone;
            config false;
            notife:notifiable-state-data false;
            tailf:meta-data notife:notifiable-state-data {
                tailf:meta-value false;
            }
        }

        leaf localPortNumber {
            description "Local port number of the association.";
            type transtypes:PortNumber;
            config false;
        }

        leaf localPrimaryAddress {
            description "Local IP address normally used for outgoing traffic.";
            type inet:ip-address-no-zone;
            config false;
        }

        leaf pmtudSctpPduSize {
            description "SCTP PDU size determined by Path MTU discovery.";
            type uint16;
            config false;
        }

        leaf redundancyStatus {
            description "SCTP redundancy status indicates if there are redundant remote IP addresses available for SCTP traffic.";
            type RedundancyStatus;
            config false;
        }

        leaf-list remoteIpAddress {
            description "One or several remote IP addresses used by the association.";
            type inet:ip-address-no-zone;
            config false;
            notife:notifiable-state-data false;
            tailf:meta-data notife:notifiable-state-data {
                tailf:meta-value false;
            }
        }

        leaf remotePortNumber {
            description "Remote port number of the association.";
            type transtypes:PortNumber;
            config false;
        }

        leaf remotePrimaryAddress {
            description "Remote IP address normally used for outgoing traffic.";
            type inet:ip-address-no-zone;
            config false;
        }
    }
}
