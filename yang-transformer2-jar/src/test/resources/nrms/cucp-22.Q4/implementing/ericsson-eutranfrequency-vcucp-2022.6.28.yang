// Generated by eyang-preprocessor (1.22.0-48 2022-01-20 09:10:06 CET) on Jun 30, 2022, 8:31:37 AM
module ericsson-eutranfrequency-vcucp {
    yang-version 1.1;
    namespace "urn:rdns:com:ericsson:oammodel:ericsson-eutranfrequency-vcucp";
    prefix "eutranfrequency";

    import tailf-common {
        prefix tailf;
    }
    import _3gpp-common-managed-element {
        prefix "me3gpp";
    }
    import _3gpp-nr-nrm-gnbcucpfunction {
        prefix "gnbcucp3gpp";
    }
    import _3gpp-common-top {
        prefix "top3gpp";
    }
    import _3gpp-common-yang-extensions {
        prefix yext3gpp;
    }
    import ericsson-eutranetwork-vcucp {
        prefix "eutranet";
    }
    import ericsson-yang-extensions {
        prefix "yexte";
    }
    import ericsson-common-types-vcucp {
        prefix commontypes;
    }
    import ericsson-notifications {
        prefix notife;
    }

    organization
        "Ericsson AB";
    contact
        "Ericsson first line support via email";
    description
        "The module defines the EUtranFrequency data model for the Ericsson vCU-CP.

        Copyright (c) 2021-2022 Ericsson AB. All rights reserved.";

    revision 2022-06-28 {
        description
            "Removed module-status preliminary.";
        yexte:version 3;
        yexte:release 1;
        yexte:correction 0;
        reference
            "RFC 7950: The YANG 1.1 Data Modeling Language";
    }

    revision 2021-11-05 {
        description
            "excludeAdditionalFreqBandList marked obsolete.
             freqBandList marked obsolete.";
        yexte:version 3;
        yexte:release 0;
        yexte:correction 0;
        reference
            "RFC 7950: The YANG 1.1 Data Modeling Language";
    }

    revision 2021-07-27 {
        description
            "Bug Fix, leaf-list state notifiable compatibility issue. Adds extension notife:notifiable-state-data false to freqBandList.";
        yexte:version 2;
        yexte:release 1;
        yexte:correction 0;
        reference
            "RFC 7950: The YANG 1.1 Data Modeling Language";
    }

    revision 2021-07-05 {
        description
            "Removed min-elements from freqBandList";
        yexte:version 1;
        yexte:release 2;
        yexte:correction 2;
        reference
            "RFC 7950: The YANG 1.1 Data Modeling Language";
    }

    revision 2021-05-24 {
        description
            "Add must statement to arfcnValueEUtranDl.";
        yexte:version 1;
        yexte:release 2;
        yexte:correction 1;
        reference
            "RFC 7950: The YANG 1.1 Data Modeling Language";
    }

    revision 2021-05-06 {
        description
            "Remove is-system-created and restricted extensions from configurable attributes.
             Add yext3gpp:inVariant to arfcnValueEUtranDl.";
        yexte:version 1;
        yexte:release 2;
        yexte:correction 0;
        reference
            "RFC 7950: The YANG 1.1 Data Modeling Language";
    }

    revision 2021-03-30 {
        description
            "Add Ericsson descriptions and tags to attributes.";
        yexte:version 1;
        yexte:release 1;
        yexte:correction 1;
        reference
            "RFC 7950: The YANG 1.1 Data Modeling Language";
    }

    revision 2021-03-16 {
        description
            "Parity with ECIM R1A79";
        yexte:version 1;
        yexte:release 1;
        yexte:correction 0;
        reference
            "RFC 7950: The YANG 1.1 Data Modeling Language";
    }
    revision 2021-01-20 {
        description
            "Add extensions is-system-created.";
        yexte:version 1;
        yexte:release 0;
        yexte:correction 0;
        reference
            "RFC 7950: The YANG 1.1 Data Modeling Language";
    }

    revision 2021-01-11 {
        description
            "Initial version of the EUtranFrequency model.";
        yexte:version 0;
        yexte:release 1;
        yexte:correction 0;
        reference
            "RFC 7950: The YANG 1.1 Data Modeling Language";
    }

    grouping EUtranFrequencyGrp {
        description "Represents the EUtranFrequency IOC.";

        leaf arfcnValueEUtranDl {
            description
                "ARFCN applicable for a downlink E-UTRA carrier frequency.

                For TDD this also indicates the ARFCN for uplink.
                Values that can be used depend on national operator-specific frequency "+
                "allocation and supported frequency bands of the equipment in the eNodeB.
                Must match the ID of EUtranFrequency.";
            must "../../id = string(.)" {
                error-message "arfcnValueEUtranDl must match the RDN of EUtranFrequency (e.g. EUtranFrequency=&lt;arfcnValueEUtranDl&gt;).";
            }
            mandatory true;
            yext3gpp:inVariant;
            type int32 {
                range "0..17999 | 36000..262143";
            }
            reference "3GPP TS 36.104";
            yexte:dependencies
                "Must match RDN of MO, EUtranFrequency=&lt;arfcnValueEUtranDl&gt;.
                For example, EUtranFrequency=2586.";
            tailf:info 'Dependencies: Must match RDN of MO, EUtranFrequency=&lt;arfcnValueEUtranDl&gt;.
                For example, EUtranFrequency=2586, ARFCN applicable for a downlink E-UTRA carrier frequency. For TDD this also indicates the ARFCN for uplink. Values that can be used depend on national operator-specific frequency allocation and supported frequency bands of the equipment in the eNodeB. Must match the ID of EUtranFrequency.';
        }

        leaf-list excludeAdditionalFreqBandList {
            description
                "A list of frequency bands to be excluded from the list in the freqBandList attribute.

                The list must not include the frequency band indicated by the EARFCN value of the frequency (primary frequency band).

                These frequency bands are excluded from the list of broadcast additional frequency bands in"+
                " SystemInformationBlockType5 in case the feature Multiple Frequency Band Indicators is enabled in the cell.";
            type int32 {
                range "1..256";
            }
            yexte:takes-effect
                "New connection";
            max-elements 8;
            status obsolete {
                yexte:status-information
                    "Since 21.Q3. Planned to be removed.";
            }
            tailf:info 'Status Info: Since 21.Q3. Planned to be removed, Obsolete, Takes effect: New connection, A list of frequency bands to be excluded from the list in the freqBandList attribute. The list must not include the frequency band indicated by the EARFCN value of the frequency (primary frequency band). These frequency bands are excluded from the list of broadcast additional frequency bands in SystemInformationBlockType5 in case the feature Multiple Frequency Band Indicators is enabled in the cell.';
        }

        leaf-list freqBandList {
            description
                "List of frequency bands that the frequency belongs to.

                The primary frequency band that the frequency belongs to, according to its defined EARFCN, is the first element in the list.";
            type int32 {
                range "1..256";
            }
            max-elements 9;
            config false;
            notife:notifiable-state-data false;
            status obsolete {
                yexte:status-information
                    "Since 21.Q3. Planned to be removed.";
            }
            tailf:info 'Status Info: Since 21.Q3. Planned to be removed, Obsolete, List of frequency bands that the frequency belongs to. The primary frequency band that the frequency belongs to, according to its defined EARFCN, is the first element in the list.';
            tailf:meta-data notife:notifiable-state-data {
                tailf:meta-value false;
            }
        }

        uses commontypes:UserLabelGrp;
    }

    augment "/me3gpp:ManagedElement/gnbcucp3gpp:GNBCUCPFunction/eutranet:EUtraNetwork" {
        list EUtranFrequency {
            description
                "Container for information of a specific E-UTRAN frequency.

                The RDNs of these MOs are EUtranFrequency=&lt;number&gt;, for example EUtranFrequency=2586.
                RDN must match attribute arfcnValueEUtranDl.";
            key id;
            max-elements 32;
            uses top3gpp:Top_Grp;
            container attributes {
                uses EUtranFrequencyGrp;
            }
        }
    }
}
