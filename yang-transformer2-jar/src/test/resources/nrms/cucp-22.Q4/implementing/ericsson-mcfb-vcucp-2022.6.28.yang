// Generated by eyang-preprocessor (1.22.0-48 2022-01-20 09:10:06 CET) on Jun 30, 2022, 8:31:38 AM
module ericsson-mcfb-vcucp {
    yang-version 1.1;
    namespace urn:rdns:com:ericsson:oammodel:ericsson-mcfb-vcucp;
    prefix mcfb;

    import tailf-common {
        prefix tailf;
    }
    import _3gpp-common-managed-element {
        prefix me3gpp;
    }
    import _3gpp-nr-nrm-gnbcucpfunction {
        prefix gnbcucp3gpp;
    }
    import _3gpp-common-top {
        prefix top3gpp;
    }
    import ericsson-yang-extensions {
        prefix yexte;
    }

    organization
      "Ericsson AB";
    contact
      "Ericsson first line support via email";
    description
      "The module defines the Mcfb data model for the Ericsson vCU-CP.

       Copyright (c) 2021-2022 Ericsson AB. All rights reserved.";

    revision 2022-06-28 {
        description
            "Removed module-status preliminary.";
        yexte:version 1;
        yexte:release 1;
        yexte:correction 0;
        reference
            "RFC 7950: The YANG 1.1 Data Modeling Language";
    }

    revision 2022-03-14 {
        description
          "Update Mcfb description and precondition.
           Update description for voiceEpsFbPossible.";
        yexte:version 1;
        yexte:release 0;
        yexte:correction 1;
        reference
          "RFC 7950: The YANG 1.1 Data Modeling Language";
    }

    revision 2021-11-17 {
        description
          "Update Mcfb description and precondition.
           Marked mcfbCellProfileEnabled as obsolete.";
        yexte:version 1;
        yexte:release 0;
        yexte:correction 0;
        reference
          "RFC 7950: The YANG 1.1 Data Modeling Language";
    }

    revision 2021-06-08 {
        description
            "Changed error message for a must statement.";
        yexte:version 0;
        yexte:release 1;
        yexte:correction 1;
        reference
            "RFC 7950: The YANG 1.1 Data Modeling Language";
    }

    revision 2021-04-25 {
        description
          "Initial version of the Mcfb model.";
        yexte:version 0;
        yexte:release 1;
        yexte:correction 0;
        reference
          "RFC 7950: The YANG 1.1 Data Modeling Language";
    }

    grouping McfbGrp {
        description
          "Represents the Mcfb IOC.";

        leaf mcfbCellProfileEnabled {
            description
              "McfbCellProfile MO class usage indication.

              If false:
              - VoNR fallback operation is defined by attribute "+
              "epsFallbackOperation under NRCellCU.
              - Emergency fallback operation behaves as if "+
              "McfbCellProfile::epsFallbackOperationEm is set to FORCED.
              If true, fallback function is defined by McfbCellProfile referred by "+
              "NRCellCU.";
            type boolean;
            status obsolete {
                yexte:status-information
                    "Since 21.Q4. McfbCellProfile MO class is now always used.";
            }
            tailf:info 'Status Info: Since 21.Q4. McfbCellProfile MO class is now always used, Obsolete, McfbCellProfile MO class usage indication. If false: - VoNR fallback operation is defined by attribute epsFallbackOperation under NRCellCU. - Emergency fallback operation behaves as if McfbCellProfile::epsFallbackOperationEm is set to FORCED. If true, fallback function is defined by McfbCellProfile referred by NRCellCU.';
        }

        leaf voiceEpsFbPossible {
            description
                "Whether EPS fallback is assumed possible.

                When Redirection for Voice EPS Fallback IE is not included from core "+
                "network (AMF node), the IE is assumed set to possible.

                The IE Redirection for Voice EPS Fallback is indicated over NGAP "+
                "from core network. This IE controls whether it is possible to "+
                "perform EPS fallback or not. This IE is optional, and this attribute "+
                "is used to define the behavior when this IE is not indicated from "+
                "core network.
                This attribute should be false if core network supports CR S2-2007918 "+
                "for NGAP in 3GPP TS 38.413 Rel-16.";
            type boolean;
            default true;
            reference
              "3GPP TS 38.413";
            yexte:takes-effect
              "Next usage.";
            tailf:info 'Takes effect: Next usage, Whether EPS fallback is assumed possible. When Redirection for Voice EPS Fallback IE is not included from core network (AMF node), the IE is assumed set to possible. The IE Redirection for Voice EPS Fallback is indicated over NGAP from core network. This IE controls whether it is possible to perform EPS fallback or not. This IE is optional, and this attribute is used to define the behavior when this IE is not indicated from core network. This attribute should be false if core network supports CR S2-2007918 for NGAP in 3GPP TS 38.413 Rel-16.';
        }
    }

    augment "/me3gpp:ManagedElement/gnbcucp3gpp:GNBCUCPFunction" {

        list Mcfb {
            description
              "Container class for mobility control fallback attributes and "+
              "profile classes.

              MO instance Mcfb=1 is created automatically when parent MO is "+
              "created, unless created manually in the same transaction as parent MO.

              The RDN of this MO is Mcfb=1.";
            yexte:precondition
              "Mcfb=1 MO instance can only be created in the same transaction as "+
              "parent MO and must not be deleted unless parent MO is deleted.";
            key id;
            max-elements 1;
            uses top3gpp:Top_Grp {
                refine id {
                    must '. = "1"' {
                        error-message
                          "The RDN of this MO must always be Mcfb=1";
                    }
                }
            }
            container attributes {
                uses McfbGrp;
            }
            tailf:info 'Precondition: Mcfb=1 MO instance can only be created in the same transaction as parent MO and must not be deleted unless parent MO is deleted, Container class for mobility control fallback attributes and profile classes. MO instance Mcfb=1 is created automatically when parent MO is created, unless created manually in the same transaction as parent MO. The RDN of this MO is Mcfb=1.';
        }
    }
}
