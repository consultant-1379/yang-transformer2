// Generated by eyang-preprocessor (1.24.0-23 2022-06-22 14:11:55 CEST) on Jun 28, 2022, 10:45:18 AM
module ericsson-ipaddress-vcu {
    yang-version 1.1;
    namespace urn:rdns:com:ericsson:oammodel:ericsson-ipaddress-vcu;
    prefix ipaddress;

    import tailf-common {
        prefix tailf;
    }
    import _3gpp-common-top {
        prefix "top3gpp";
    }
    import ietf-inet-types {
        prefix inet;
    }
    import ericsson-transport-types-vcu {
        prefix transtypes;
    }
    import ericsson-yang-extensions {
        prefix yexte;
    }

    organization
        "Ericsson AB";
    contact
        "Ericsson first line support via email";
    description
        "The module defines the abstract IpAddress data model for the Ericsson vCU.

         Copyright (c) 2021-2022 Ericsson AB. All rights reserved.";

    revision 2022-06-28 {
        description
            "Removed module-status preliminary.";
        yexte:version 0;
        yexte:release 2;
        yexte:correction 0;
        reference
            "RFC 7950: The YANG 1.1 Data Modeling Language";
    }

    revision 2021-02-05 {
        description
            "Added config false statement for wrapper containers.";
        yexte:version 0;
        yexte:release 1;
        yexte:correction 1;
        reference
            "RFC 7950: The YANG 1.1 Data Modeling Language";
    }

    revision 2021-01-05 {
        description
            "Initial revision.";
        yexte:version 0;
        yexte:release 1;
        yexte:correction 0;
        reference
            "RFC 7950: The YANG 1.1 Data Modeling Language";
    }

    grouping IpAddressGrp {
        description "Assigned IP address.";

        leaf address {
            description
                "Configured IP address.";
            type inet:ip-address-no-zone;
            config false;
        }

        leaf ipAddressId {
            description
                "Identifies the IpAddress MO.";
            mandatory true;
            type transtypes:ReferenceId;
            config false;
        }

        leaf usedAddress {
            description
                "Used IP address.";
            type inet:ip-address-no-zone;
            config false;
        }

        leaf userLabel {
            description "Label for free use.";
            type string;
            yexte:restricted;
        }
    }

    grouping IpAddressV4Wrapper {
        list IpAddressV4 {
            description
                "Represents an IP address version 4 model.";
            key id;
            uses top3gpp:Top_Grp;
            max-elements 1;
            container attributes {
                uses IpAddressGrp;
                must "re-match(address, '[0-9\\.]*')" {
                    error-message
                        "address must be an IPv4 address.";
                }
                must "re-match(usedAddress, '[0-9\\.]*')" {
                    error-message
                        "usedAddress must be an IPv4 address.";
                }
                config false;
            }
            yexte:is-system-created;
            tailf:meta-data yexte:is-system-created;
        }
    }

    grouping IpAddressV6Wrapper {
        list IpAddressV6 {
            description
                "Represents an IP address version 6 model.";
            key id;
            uses top3gpp:Top_Grp;
            max-elements 1;
            container attributes {
                uses IpAddressGrp;
                must "re-match(address, '[0-9a-fA-F:\\.]*')" {
                    error-message
                        "address must be an IPv6 address.";
                }
                must "re-match(usedAddress, '[0-9a-fA-F:\\.]*')" {
                    error-message
                        "usedAddress must be an IPv6 address.";
                }
                config false;
            }
            yexte:is-system-created;
            tailf:meta-data yexte:is-system-created;
        }
    }
}
