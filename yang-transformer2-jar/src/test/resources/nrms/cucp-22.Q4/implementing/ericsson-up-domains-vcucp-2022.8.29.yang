// Generated by eyang-preprocessor (1.22.0-48 2022-01-20 09:10:06 CET) on Sep 4, 2022, 12:23:59 PM
module ericsson-up-domains-vcucp {
    yang-version 1.1;
    namespace urn:rdns:com:ericsson:oammodel:ericsson-up-domains-vcucp;
    prefix updomainsvcucp;

    import tailf-common {
        prefix tailf;
    }
    import _3gpp-common-managed-element {
        prefix me3gpp;
    }
    import _3gpp-nr-nrm-gnbcucpfunction {
        prefix gnbcucp3gpp;
    }
    import _3gpp-common-top {
        prefix top3gpp;
    }
    import ericsson-yang-extensions {
        prefix yexte;
    }
    import ericsson-up-selection-vcucp {
        prefix upselectionvcucp;
    }

    organization
      "Ericsson AB";
    contact
      "Ericsson first line support via email";
    description
      "The module defines the UPDomains data model for the Ericsson vCU-CP.


       Copyright (c) 2022 Ericsson AB. All rights reserved.";

    revision 2022-08-29 {
        description
          "Removed module-status preliminary.
           Removed preliminary status from:
            - list UPDomains";
        yexte:version 0;
        yexte:release 2;
        yexte:correction 0;
        reference
          "RFC 7950: The YANG 1.1 Data Modeling Language";
    }

    revision 2022-04-20 {
        description
          "Initial version of the UPDomains model";
        yexte:version 0;
        yexte:release 1;
        yexte:correction 0;
        reference
          "RFC 7950: The YANG 1.1 Data Modeling Language";
    }

    augment "/me3gpp:ManagedElement/gnbcucp3gpp:GNBCUCPFunction/upselectionvcucp:UPSelection" {
        list UPDomains {
            description
              "Container class for User Plane Domains.

               MO instance UPDomains=1 is created automatically when parent MO is "
            + "created, unless created manually in the same transaction as parent MO.

               The RDN of this MO must always be UPDomains=1.";
            key id;
            max-elements 1;
            uses top3gpp:Top_Grp {
                refine id {
                    must '. = "1"' {
                        error-message
                          "The RDN of this MO must always be UPDomains=1";
                    }
                }
            }
            yexte:precondition
                "UPDomains=1 MO instance must not be deleted unless parent MO is deleted.";
            tailf:info 'Precondition: UPDomains=1 MO instance must not be deleted unless parent MO is deleted, Container class for User Plane Domains. MO instance UPDomains=1 is created automatically when parent MO is created, unless created manually in the same transaction as parent MO. The RDN of this MO must always be UPDomains=1.';
        }
    }
}
