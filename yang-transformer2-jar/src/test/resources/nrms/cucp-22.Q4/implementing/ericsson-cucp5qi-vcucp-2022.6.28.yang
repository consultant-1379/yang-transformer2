// Generated by eyang-preprocessor (1.22.0-48 2022-01-20 09:10:06 CET) on Jun 30, 2022, 8:31:35 AM
module ericsson-cucp5qi-vcucp {
    yang-version 1.1;
    namespace urn:rdns:com:ericsson:oammodel:ericsson-cucp5qi-vcucp;
    prefix cucp5qivcucp;

    import tailf-common {
        prefix tailf;
    }
    import _3gpp-common-managed-element {
        prefix me3gpp;
    }
    import _3gpp-common-yang-types {
        prefix types3gpp;
    }
    import _3gpp-common-top {
        prefix top3gpp;
    }
    import _3gpp-nr-nrm-gnbcucpfunction {
        prefix gnbcucp3gpp;
    }
    import ericsson-yang-extensions {
        prefix yexte;
    }
    import ericsson-nrdcsntermination-vcucp {
        prefix nrdcsntermination;
    }
    import ericsson-cucp5qitable-vcucp {
        prefix cucp5qitablevcucp;
    }
    import ericsson-common-types-vcucp {
        prefix commontypes;
    }

    organization
      "Ericsson AB";
    contact
      "Ericsson first line support via email";
    description
      "QoS configuration corresponding to 3GPP-defined and operator-defined 5QI profiles for the Ericsson vCU-CP.

       Copyright (c) 2021-2022 Ericsson AB. All rights reserved.";

    revision 2022-06-28 {
        description
            "Removed module-status preliminary.";
        yexte:version 0;
        yexte:release 5;
        yexte:correction 0;
        reference
            "RFC 7950: The YANG 1.1 Data Modeling Language";
    }

    revision 2022-03-14 {
        description
          "Updated description for nrdcSnTerminationRef.
           Fixed the 3GPP references in the RlcMode enum.
           Added the userLabel attribute.";
        yexte:version 0;
        yexte:release 4;
        yexte:correction 0;
        reference
          "RFC 7950: The YANG 1.1 Data Modeling Language";
    }

    revision 2021-11-05 {
        description
          "Add attributes nrdcSnTerminationRef, pdcpSnSize and tReorderingDl.
           Changed description on tPdcpDiscard.
           Removed preliminary tags on RlcMode enum values";
        yexte:version 0;
        yexte:release 3;
        yexte:correction 0;
        reference
          "RFC 7950: The YANG 1.1 Data Modeling Language";
    }

    revision 2021-07-09 {
        description
          "Add attributes profile5qi, rlcMode and tPdcpDiscard.
           Add must statements and updated descriptions.";
        yexte:version 0;
        yexte:release 2;
        yexte:correction 0;
        reference
          "RFC 7950: The YANG 1.1 Data Modeling Language";
    }

    revision 2021-03-27 {
        description
          "Add attributes on ericsson-cucp5qi-vcucp.";
        yexte:version 0;
        yexte:release 1;
        yexte:correction 0;
        reference
          "RFC 7950: The YANG 1.1 Data Modeling Language";
    }

    typedef RlcMode {
        description
          "RLC mode.";

        type enumeration {
            enum AM {
                value 0;
                description
                  "RLC mode is AM.";
                reference
                  "3GPP TS 38.463";
            }

            enum UM {
                value 1;
                description
                  "RLC mode is UM Bidirectional.";
                reference
                  "3GPP TS 38.463";
            }
        }
    }

    grouping CUCP5qiGrp {
        description
          "Represents the CUCP5qi IOC.";

        leaf nrdcSnTerminationRef {
            description
              "Reference to an instance of NrdcSnTermination MO.

              For 5QIs 1,5,65,66 and 69, if empty then SnTerminationProhibited " +
              "instance of NrdcSnTermination MO is used.
              For all other 5QI, if empty then instance of NrdcSnTermination MO is " +
              "used where defaultNrdcSnTerm attribute is true.

              If empty, and no such MO exists, SN termination is not allowed for " +
              "this 5QI.

              Referenced NrdcSnTermination must be under same GNBCUCPFunction as " +
              "CUCP5qi.";
            type types3gpp:DistinguishedName;

            must "re-match(current(), 'ManagedElement=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,GNBCUCPFunction=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,NrdcSnTermination=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?') and
                  re-match(current(), concat('ManagedElement=', ../../../../../me3gpp:id, ',.*')) and
                  re-match(current(), concat('.*GNBCUCPFunction=', ../../../../gnbcucp3gpp:id, ',.*')) and
                  count(../../../../nrdcsntermination:NrdcSnTermination[re-match(current(), concat('.*NrdcSnTermination=', nrdcsntermination:id))]) &gt; 0" {
                description
                    "The reference must point at a NrdcSnTermination entry.

                    An example of a valid value is
                    ManagedElement=1,GNBCUCPFunction=1,NrdcSnTermination=1";
                error-message
                  "nrdcSnTerminationRef must refer to a NrdcSnTermination under the same GNBCUCPFunction";
            }
            yexte:takes-effect
                "New connection";
            tailf:info 'Takes effect: New connection, Reference to an instance of NrdcSnTermination MO. For 5QIs 1,5,65,66 and 69, if empty then SnTerminationProhibited instance of NrdcSnTermination MO is used. For all other 5QI, if empty then instance of NrdcSnTermination MO is used where defaultNrdcSnTerm attribute is true. If empty, and no such MO exists, SN termination is not allowed for this 5QI. Referenced NrdcSnTermination must be under same GNBCUCPFunction as CUCP5qi.';
        }

        leaf pdcpSnSize {
            description
              "PDCP sequence number length.

               Following values are recommended:
               * 12 if profile5qi is 1, 2, 3, 4, 5, 6, 7, 65, 66, 67, 69, 70, 79, "
            + "80, 82, 83, 84 or 85.
               * 18 if profile5qi is 8 or 9.";
            type int32 {
                range "12|18";
            }
            default 18;
            yexte:dependencies
                "Must be greater than or equal to rlcSNLength in corresponding DU5qi "+
                "profile.";
            tailf:info 'Dependencies: Must be greater than or equal to rlcSNLength in corresponding DU5qi profile, PDCP sequence number length. Following values are recommended: * 12 if profile5qi is 1, 2, 3, 4, 5, 6, 7, 65, 66, 67, 69, 70, 79, 80, 82, 83, 84 or 85. * 18 if profile5qi is 8 or 9.';
        }
        leaf profile5qi {
            description
              "5G QoS Identifier unique within a table.

               For 3GPP-defined 5QIs, 5QI can be 1, 2, 3, 4, 5, 6, 7, 8, "
            + "9, 65, 66, 67, 69, 70, 79, 80, 82, 83, 84 or 85.";
            type int32 {
                range "0..255";
            }
            mandatory true;
            yexte:dependencies
                "Value must be unique in 5qiTable.

                For 3GPP-defined profiles:
                - profile5qi=1, rlcMode must be UM.
                - profile5qi=5, rlcMode must be AM.
                - profile5qi=65, rlcMode must be UM.
                - profile5qi=66, rlcMode must be UM.
                - profile5qi=69, rlcMode must be AM.
                - profile5qi=79, rlcMode must be UM.
                - profile5qi=80, rlcMode must be UM.
                - profile5qi=82, rlcMode must be UM.
                - profile5qi=83, rlcMode must be UM.
                - profile5qi=84, rlcMode must be UM.
                - profile5qi=85, rlcMode must be UM.";
            tailf:info 'Dependencies: Value must be unique in 5qiTable.

                For 3GPP-defined profiles:
                - profile5qi=1, rlcMode must be UM.
                - profile5qi=5, rlcMode must be AM.
                - profile5qi=65, rlcMode must be UM.
                - profile5qi=66, rlcMode must be UM.
                - profile5qi=69, rlcMode must be AM.
                - profile5qi=79, rlcMode must be UM.
                - profile5qi=80, rlcMode must be UM.
                - profile5qi=82, rlcMode must be UM.
                - profile5qi=83, rlcMode must be UM.
                - profile5qi=84, rlcMode must be UM.
                - profile5qi=85, rlcMode must be UM, 5G QoS Identifier unique within a table. For 3GPP-defined 5QIs, 5QI can be 1, 2, 3, 4, 5, 6, 7, 8, 9, 65, 66, 67, 69, 70, 79, 80, 82, 83, 84 or 85.';
        }

        leaf rlcMode {
            description
              "RLC mode for DRB.

               Recommended values for non-restricted 5QIs:
               UM if profile5qi is 2.
               AM if profile5qi is 6, 7, 8, 9 or 70.";
            type RlcMode;
            default AM;
            yexte:dependencies
                "For restricted 5QIs:
                UM if profile5qi is 1, 65, 66, 79, 80, 82, 83, 84, or 85.
                AM if profile5qi is 5 or 69.";
            tailf:info 'Dependencies: For restricted 5QIs:
                UM if profile5qi is 1, 65, 66, 79, 80, 82, 83, 84, or 85.
                AM if profile5qi is 5 or 69, RLC mode for DRB. Recommended values for non-restricted 5QIs: UM if profile5qi is 2. AM if profile5qi is 6, 7, 8, 9 or 70.';
        }

        leaf tPdcpDiscard {
            description
              "UL PDCP discard timer used in UE.

               Following values are recommended:
               * 150 if profile5qi is 1.
               * 200 if profile5qi is 2, 3, 4, 65, 66, 67, 69, 70, 79, 80, 82, 83, 84 or 85.
               * 1500 if profile5qi is 6, 7, 8 or 9.
               * 2147483646 (infinity) if profile5qi is 5.";
            type int32 {
                range "10|20|30|40|50|60|75|100|150|200|250|300|500|750|1500..2147483646";
            }
            default 1500;
            units ms;
        }

        leaf tReorderingDl {
            description
                "T-reordering DL timer used by the receiving-end PDCP entity in the "+
                "UE.

                Recommended value is 200 if profile5qi is 1, 2, 3, 4, 5, 6, 7, 8, 9, "+
                "65, 66, 67, 69, 70, 79, 80, 82, 83, 84 or 85.";
            type int32 {
                range "0|1|2|4|5|8|10|15|20|30|40|50|60|80|100|120|140|160|180|200|220|"+
                    "240|260|280|300|500|750|1000|1250|1500|1750|2000|2250|2500|2750|"+
                    "3000";
            }
            default 200;
            units bit;
        }

        leaf tReorderingUl {
            description
              "T-reordering UL timer used by the receiving-end PDCP entity in the gNodeB.

               Recommended value is 20 if profile5qi is 1, 2, 3, 4, 5, 6, 7, 8, 9, 65, 66,"
            + " 67, 69, 70, 79, 80, 82, 83, 84 or 85.";
            type int32 {
                range "0|1|2|4|5|8|10|15|20|30|40|50|60|80|100|120|140|160|180|200|220|240|"+
                "260|280|300|500|750|1000|1250|1500|1750|2000|2250|2500|2750|3000";
            }
            default 20;
            units ms;
        }
    }

    augment "/me3gpp:ManagedElement/gnbcucp3gpp:GNBCUCPFunction/cucp5qitablevcucp:CUCP5qiTable" {
        when 'true()'; // temp fix to force augment statement to allow adding mandatory attributes.
        list CUCP5qi {
            description
              "QoS configuration corresponding to 3GPP-defined and operator-defined 5QI profiles.

               Maximum number of operator-defined profiles is 9.

               Each profile can be present once in each table.";
            key id;
            unique 'attributes/profile5qi';
            uses top3gpp:Top_Grp;
            min-elements 1;
            max-elements 29;
            must 'count(../cucp5qivcucp:CUCP5qi/cucp5qivcucp:attributes/cucp5qivcucp:profile5qi[not((. &lt;= 9) or (. &gt;= 65 and . &lt;= 70 and . != 68) or (. &gt;= 79 and . &lt;= 85 and . != 81))]) &lt; 10' {
                error-message
                  "Max operator defined CUCP5qis is 9 under CUCP5qiTable";
            }
            container attributes {
                uses CUCP5qiGrp;
                uses commontypes:UserLabelGrp;

                must 'not(current()/profile5qi = 1) or (current()/rlcMode = "UM")' {
                    error-message
                      "For GNBCUCPFunction,CUCP5qiTable,CUCP5qi,profile5qi=1, rlcMode must be UM(1).";
                }
                must 'not(current()/profile5qi = 5) or (current()/rlcMode = "AM")' {
                    error-message
                      "For GNBCUCPFunction,CUCP5qiTable,CUCP5qi,profile5qi=5, rlcMode must be AM(0)";
                }
                must 'not(current()/profile5qi = 65) or (current()/rlcMode = "UM")' {
                    error-message
                      "For GNBCUCPFunction,CUCP5qiTable,CUCP5qi,profile5qi=65, rlcMode must be UM(1)";
                }
                must 'not(current()/profile5qi = 66) or (current()/rlcMode = "UM")' {
                    error-message
                      "For GNBCUCPFunction,CUCP5qiTable,CUCP5qi,profile5qi=66, rlcMode must be UM(1)";
                }
                must 'not(current()/profile5qi = 69) or (current()/rlcMode="AM")' {
                    error-message
                      "For GNBCUCPFunction,CUCP5qiTable,CUCP5qi,profile5qi=69, rlcMode must be AM(0)";
                }
                must 'not(current()/profile5qi = 79) or (current()/rlcMode = "UM")' {
                    error-message
                      "For GNBCUCPFunction,CUCP5qiTable,CUCP5qi,profile5qi=79, rlcMode must be UM(1)";
                }
                must 'not(current()/profile5qi = 80) or (current()/rlcMode = "UM")' {
                    error-message
                      "For GNBCUCPFunction,CUCP5qiTable,CUCP5qi,profile5qi=80, rlcMode must be UM(1)";
                }
                must 'not(current()/profile5qi = 82) or (current()/rlcMode = "UM")' {
                    error-message
                      "For GNBCUCPFunction,CUCP5qiTable,CUCP5qi,profile5qi=82, rlcMode must be UM(1)";
                }
                must 'not(current()/profile5qi = 83) or (current()/rlcMode = "UM")' {
                    error-message
                      "For GNBCUCPFunction,CUCP5qiTable,CUCP5qi,profile5qi=83, rlcMode must be UM(1)";
                }
                must 'not(current()/profile5qi = 84) or (current()/rlcMode = "UM")' {
                    error-message
                      "For GNBCUCPFunction,CUCP5qiTable,CUCP5qi,profile5qi=84, rlcMode must be UM(1)";
                }
                must 'not(current()/profile5qi = 85) or (current()/rlcMode = "UM")' {
                    error-message
                      "For GNBCUCPFunction,CUCP5qiTable,CUCP5qi,profile5qi=85, rlcMode must be UM(1)";
                }
            }
        }
    }
}
