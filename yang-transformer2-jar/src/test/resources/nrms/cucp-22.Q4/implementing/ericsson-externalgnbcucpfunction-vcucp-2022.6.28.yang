// Generated by eyang-preprocessor (1.22.0-48 2022-01-20 09:10:06 CET) on Jun 30, 2022, 8:31:38 AM
module ericsson-externalgnbcucpfunction-vcucp {
    yang-version 1.1;
    namespace "urn:rdns:com:ericsson:oammodel:ericsson-externalgnbcucpfunction-vcucp";
    prefix "externalgnbcucpfunctionvcucp";

    import tailf-common {
        prefix tailf;
    }
    import _3gpp-common-managed-element {
        prefix "me3gpp";
    }
    import _3gpp-nr-nrm-gnbcucpfunction {
        prefix "gnbcucp3gpp";
    }
    import _3gpp-common-top {
        prefix "top3gpp";
    }
    import _3gpp-common-yang-extensions {
        prefix yext3gpp;
    }
    import ericsson-nrnetwork-vcucp {
        prefix "nrnetwork";
    }
    import ericsson-yang-extensions {
        prefix "yexte";
    }
    import ericsson-common-types-vcucp {
        prefix commontypes;
    }
    import ericsson-notifications {
        prefix notife;
    }
    import _3gpp-common-yang-types {
        prefix types3gpp;
    }

    organization
      "Ericsson AB";
    contact
      "Ericsson first line support via email";
    description
      "The module defines the ExternalGNBCUCPFunction data model for the Ericsson vCU-CP.

       Copyright (c) 2021-2022 Ericsson AB. All rights reserved.";

    revision 2022-06-28 {
        description
            "Removed module-status preliminary.";
        yexte:version 2;
        yexte:release 1;
        yexte:correction 0;
        reference
            "RFC 7950: The YANG 1.1 Data Modeling Language";
    }

    revision 2021-11-06 {
        description
          "Add attributes amfRegionInfoList, isRemoveAllowed, and noRelationTimeStamp.
          Mark createdBy as obsolete.";
        yexte:version 2;
        yexte:release 0;
        yexte:correction 0;
        reference
          "RFC 7950: The YANG 1.1 Data Modeling Language";
    }

    revision 2021-06-09 {
        description
          "Add must statment related to gNBId, gNBIdLength, and pLMNId uniqueness.";
        yexte:version 1;
        yexte:release 0;
        yexte:correction 1;
        reference
          "RFC 7950: The YANG 1.1 Data Modeling Language";
    }

    revision 2021-06-08 {
        description
          "Correct name of PLMNId to pLMNId.
           Disable notifications for timeOfCreation.";
        yexte:version 1;
        yexte:release 0;
        yexte:correction 0;
        reference
          "RFC 7950: The YANG 1.1 Data Modeling Language";
    }

    revision 2021-05-06 {
        description
          "Remove is-system-created from MO and configurable attributes.
           Add yext3gpp:inVariant to gNBId and gNBIdLength.";
        yexte:version 0;
        yexte:release 2;
        yexte:correction 0;
        reference
          "RFC 7950: The YANG 1.1 Data Modeling Language";
    }

    revision 2021-03-18 {
        description
          "Initial version of the ExternalGNBCUCPFunction model.";
        yexte:version 0;
        yexte:release 1;
        yexte:correction 0;
        reference
          "RFC 7950: The YANG 1.1 Data Modeling Language";
    }

    grouping GlobalUniqueAmfRegionId {
        description
          "AMF regions to which the external gNodeB belongs.";

        leaf amfRegionId {
            description
              "Indicates AMF region.";
            type int32 {
                range "0..255";
            }
            reference
              "3GPP TS 38.423";
        }

        leaf mcc {
            description
              "MCC identifies uniquely domicile country of mobile subscriber.

               MCC consists of three decimal digits. The first digit of MCC "
            + "identifies geographic region. (Value 1 and 8 in the first digit are "
            + "not allowed.)";
            type types3gpp:Mcc;
            reference
              "3GPP TS 38.423";
        }

        leaf mnc {
            description
              "MNC identifies home PLMN of mobile subscription.

               MNC consists of two or three decimal digits. For example, MNC of 001 "
            + "is not same as MNC of 01.";
            type types3gpp:Mnc;
            reference
              "3GPP TS 38.423";
        }
    }

    grouping ExternalGNBCUCPFunctionGrp {
        reference
          "3GPP TS 28.541";

        list amfRegionInfoList {
            key "amfRegionId mcc mnc";
            max-elements 16;
            description
                "List of global AMF region IDs to which the external gNodeB belongs.

                For key amfRegionId, default value 0 can be used.
                For key mcc, default value 001 can be used.
                For key mnc, default value 01 can be used.";
            uses GlobalUniqueAmfRegionId;
            reference
                "3GPP TS 38.423";
            yexte:takes-effect
                "Next usage";
            tailf:info 'Takes effect: Next usage, List of global AMF region IDs to which the external gNodeB belongs. For key amfRegionId, default value 0 can be used. For key mcc, default value 001 can be used. For key mnc, default value 01 can be used.';
        }

        leaf createdBy {
            description
              "Whether MO is created by the ANR function or operator.";
            config false;
            type commontypes:CreatedByGutran;
            status obsolete {
                yexte:status-information
                "Since 21.Q2. Planned to be removed.";
            }
            tailf:info 'Status Info: Since 21.Q2. Planned to be removed, Obsolete, Whether MO is created by the ANR function or operator.';
        }

        leaf gNBId {
            description
              "Identifies a gNodeB within a PLMN.";
            must '(../gNBIdLength = 22 and ../gNBId &lt;= 4194303) or (../gNBIdLength = 23 and ../gNBId &lt;= 8388607) or (../gNBIdLength = 24 and ../gNBId &lt;= 16777215) or (../gNBIdLength = 25 and ../gNBId &lt;= 33554431) or (../gNBIdLength = 26 and ../gNBId &lt;= 67108863) or (../gNBIdLength = 27 and ../gNBId &lt;= 134217727) or (../gNBIdLength = 28 and ../gNBId &lt;= 268435455) or (../gNBIdLength = 29 and ../gNBId &lt;= 536870911) or (../gNBIdLength = 30 and ../gNBId &lt;= 1073741823) or (../gNBIdLength = 31 and ../gNBId &lt;= 2147483647) or ../gNBIdLength = 32' {
                error-message
                  "The gNBId must be equal or less than 2^gNBIdLength - 1.";
            }
            yexte:dependencies
                "The gNBId, gNBIdLength, and pLMNId attribute combination must be "+
                "unique across ExternalGNBCUCPFunction MO instances.";
            reference
              "3GPP TS 28.541";
            yexte:takes-effect
                "New connection";
            mandatory true;
            type int64 {
                range "0..4294967295";
            }
            yext3gpp:inVariant;
            tailf:info 'Takes effect: New connection, Dependencies: The gNBId, gNBIdLength, and pLMNId attribute combination must be unique across ExternalGNBCUCPFunction MO instances, Identifies a gNodeB within a PLMN.';
        }

        leaf gNBIdLength {
            description
              "Number of bits for encoding gNodeB ID.";
            yexte:dependencies
                "The gNBId, gNBIdLength, and pLMNId attribute combination must be "+
                "unique across ExternalGNBCUCPFunction MO instances.";
            reference
              "3GPP TS 28.541";
            type int32 {
                range "22..32";
            }
            default 22;
            yext3gpp:inVariant;
            tailf:info 'Dependencies: The gNBId, gNBIdLength, and pLMNId attribute combination must be unique across ExternalGNBCUCPFunction MO instances, Number of bits for encoding gNodeB ID.';
        }

        leaf isRemoveAllowed {
            description
                "Whether ANR function is allowed to remove this object.

                Setting does not restrict operator removal of the object. "+
                "Automatically created objects have this parameter set to true "+
                "initially.";
            type boolean;
            default false;
        }

        leaf noRelationTimeStamp {
            description
                "Point in time when this MO instance had no relation to "+
                "GNBCUCPFunction anymore.

                A periodic check will compare this timestamp with "+
                "AnrFunction::removeGnbTime.

                Format: EPOCH time - Number of seconds since 1970-01-01 00:00:00 UTC.";
            config false;
            type uint64;
            notife:notifiable-state-data false;
            tailf:meta-data notife:notifiable-state-data {
                tailf:meta-value false;
            }
        }

        list pLMNId {
            key "mcc mnc";
            min-elements 1;
            max-elements 1;
            description
              "PLMN identifier part of global RAN node identity.

               This and gNodeB ID form the global gNodeB ID.
               Note: Value MCC=001, MNC=01 means PLMN is not initiated. This value "
            + "cannot be used as a valid PLMN Identity.";
            yexte:dependencies
                "The gNBId, gNBIdLength, and pLMNId attribute combination must be "+
                "unique across ExternalGNBCUCPFunction MO instances.";
            reference
              "3GPP TS 23.541";
            yexte:takes-effect
                "New connection";
            uses types3gpp:PLMNId;
            tailf:info 'Takes effect: New connection, Dependencies: The gNBId, gNBIdLength, and pLMNId attribute combination must be unique across ExternalGNBCUCPFunction MO instances, PLMN identifier part of global RAN node identity. This and gNodeB ID form the global gNodeB ID. Note: Value MCC=001, MNC=01 means PLMN is not initiated. This value cannot be used as a valid PLMN Identity.';
        }

        leaf timeOfCreation {
            description
              "Time and date of MO creation.

               Format: YYYY-MM-DD HH:MM:SS.";
            type string {
                length "0..19";
            }
            config false;
            notife:notifiable-state-data false;
            tailf:meta-data notife:notifiable-state-data {
                tailf:meta-value false;
            }
        }
    }

    augment "/me3gpp:ManagedElement/gnbcucp3gpp:GNBCUCPFunction/nrnetwork:NRNetwork" {
        list ExternalGNBCUCPFunction {
            description
              "Representation of external gNodeB-CU-CP function.

               This MO is created automatically. Can also be created and deleted manually.

               Created automatically when Xn interface is set up, unless it already exists.
               Deleted automatically.

               When created automatically, the RDN of this MO is ExternalGNBCUCPFunction=auto&lt;mcc&gt;_&lt;mnc&gt;_&lt;mncLength&gt;_&lt;gNodeBId&gt;.";

            must "count(../externalgnbcucpfunctionvcucp:ExternalGNBCUCPFunction/externalgnbcucpfunctionvcucp:attributes[gNBId = current()/externalgnbcucpfunctionvcucp:attributes/gNBId and gNBIdLength = current()/externalgnbcucpfunctionvcucp:attributes/gNBIdLength and pLMNId/mcc = current()/externalgnbcucpfunctionvcucp:attributes/pLMNId/mcc and pLMNId/mnc = current()/externalgnbcucpfunctionvcucp:attributes/pLMNId/mnc] ) &lt; 2" {
                error-message
                    "Every ExternalGNBCUCPFunction under the same NRNetwork must have a unique" +
                    "combination of pLMNId, gNBIdLength and gNBId.";
            }

            key id;
            max-elements 512;
            uses top3gpp:Top_Grp;
            container attributes {
                uses ExternalGNBCUCPFunctionGrp;
            }
        }
    }
}
