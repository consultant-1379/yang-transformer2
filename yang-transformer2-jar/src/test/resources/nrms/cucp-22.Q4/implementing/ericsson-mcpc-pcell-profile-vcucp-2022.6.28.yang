// Generated by eyang-preprocessor (1.22.0-48 2022-01-20 09:10:06 CET) on Jun 30, 2022, 8:31:39 AM
module ericsson-mcpc-pcell-profile-vcucp {
    yang-version 1.1;
    namespace "urn:rdns:com:ericsson:oammodel:ericsson-mcpc-pcell-profile-vcucp";
    prefix "mcpcpcellprofile";

    import tailf-common {
        prefix tailf;
    }
    import _3gpp-common-managed-element {
        prefix "me3gpp";
    }
    import _3gpp-nr-nrm-gnbcucpfunction {
        prefix "gnbcucp3gpp";
    }
    import _3gpp-common-top {
        prefix "top3gpp";
    }
    import ericsson-common-types-vcucp {
        prefix "commontypes";
    }
    import ericsson-yang-extensions {
        prefix "yexte";
    }
    import ericsson-mcpc-vcucp {
        prefix "mcpc";
    }

    organization
      "Ericsson AB";
    contact
      "Ericsson first line support via email";
    description
      "The module defines the McpcPCellProfile data model for the Ericsson vCU-CP.

       Copyright (c) 2021-2022 Ericsson AB. All rights reserved.";

    revision 2022-06-28 {
        description
            "Removed module-status preliminary.
             Removed preliminary status from ueConfGroupType.";
        yexte:version 1;
        yexte:release 1;
        yexte:correction 0;
        reference
            "RFC 7950: The YANG 1.1 Data Modeling Language";
    }

    revision 2022-03-14 {
        description
          "Update McpcPCellProfile description and precondition.
           Marked attributes lowHighFreqPrioClassification, mcpcQuantityList,
           rsrpCandidateA5, rsrpCandidateB2, rsrpCritical, rsrpCriticalEnabled,
           rsrpSearchTimeRestriction and rsrpSearchZone as obsolete.
           Added attributes ueConfGroupType and userLabel.";
        yexte:version 1;
        yexte:release 0;
        yexte:correction 0;
        reference
          "RFC 7950: The YANG 1.1 Data Modeling Language";
    }

    revision 2021-11-05 {
        description
          "Update McpcPCellProfile description and precondition.
           Corrected range on lowHighFreqPrioClassification.";
        yexte:version 0;
        yexte:release 2;
        yexte:correction 1;
        reference
          "RFC 7950: The YANG 1.1 Data Modeling Language";
    }

    revision 2021-08-11 {
        description
          "Moved the typedef McpcQuantity and grouping ReportConfigA5Rsrp
           to ericsson-common-types-vcucp.";
        yexte:version 0;
        yexte:release 2;
        yexte:correction 0;
        reference
          "RFC 7950: The YANG 1.1 Data Modeling Language";
    }

    revision 2021-04-26 {
        description
          "Initial version of the McpcPCellProfile model";
        yexte:version 0;
        yexte:release 1;
        yexte:correction 0;
        reference
          "RFC 7950: The YANG 1.1 Data Modeling Language";
    }

    grouping ReportConfigA1A2RsrpObsolete {
        description
          "Report configuration settings for UE DL A1, A2, or both measurements with trigger quantity RSRP.";
        leaf hysteresis {
            description
              "Hysteresis value for RSRP in UE DL event A1, A2, or both measurements.";
            type int32 {
                range "0..150";
            }
            units "0.1 dB";
            must ". mod 5 = 0" {
                error-message
                  "The value must set with resolution/step of 5";
            }
            reference
              "3GPP TS 38.331";
            status obsolete;
            tailf:info 'Obsolete, Hysteresis value for RSRP in UE DL event A1, A2, or both measurements.';
        }
        leaf threshold {
            description
              "RSRP threshold value for UE DL event A1, A2, or both measurements.";
            type int32 {
                range "-156..-29";
            }
            units dBm;
            reference
              "3GPP TS 38.331";
            status obsolete;
            tailf:info 'Obsolete, RSRP threshold value for UE DL event A1, A2, or both measurements.';
        }
        leaf timeToTrigger {
            description
              "Time-to-trigger value for RSRP in UE DL event A1, A2, or both measurements.";
            type int32 {
                range "0 | 40 | 64 | 80 | 100 | 128 | 160 | 256 | 320 | 480 | 512 | 640 | 1024 | 1280 | 2560 | 5120";
            }
            units ms;
            reference
              "3GPP TS 38.331";
            status obsolete;
            tailf:info 'Obsolete, Time-to-trigger value for RSRP in UE DL event A1, A2, or both measurements.';
        }
        leaf timeToTriggerA1 {
            description
              "Time-to-trigger value for event A1.

               If set to -1, time-to-trigger value from struct member timeToTrigger is used.";
            type int32 {
                range "-1 | 0 | 40 | 64 | 80 | 100 | 128 | 160 | 256 | 320 | 480 | 512 | 640 | 1024 | 1280 | 2560 | 5120";
            }
            units ms;
            reference
              "3GPP TS 38.331";
            status obsolete;
            tailf:info 'Obsolete, Time-to-trigger value for event A1. If set to -1, time-to-trigger value from struct member timeToTrigger is used.';
        }
    }

    grouping ReportConfigA5RsrpObsolete {
        description
          "Report configuration settings for A5 measurement event when trigger "+
          "quantity is RSRP.";

        leaf hysteresis {
            description
              "Hysteresis value for eventA5.";
            type int32 {
                range "0..150";
            }
            must ". mod 5 = 0" {
                error-message
                  "The value must set with resolution/step of 5";
            }
            units "0.1 dB";
            reference
              "3GPP TS 38.331";
            status obsolete {
                yexte:status-information
                "Since 22.Q1. Replaced by McpcPCellProfileUeCfg::rsrpCandidateA5::hysteresis. "+
                "Planned to be removed.";
            }
            tailf:info 'Status Info: Since 22.Q1. Replaced by McpcPCellProfileUeCfg::rsrpCandidateA5::hysteresis. Planned to be removed, Obsolete, Hysteresis value for eventA5.';
        }

        leaf threshold1 {
            description
              "RSRP threshold1 value for eventA5.

              Value -29 defines threshold1 to infinity.";
            type int32 {
                range "-156..-29";
            }
            units dBm;
            reference
              "3GPP TS 38.331";
            status obsolete {
                yexte:status-information
                "Since 22.Q1. Replaced by McpcPCellProfileUeCfg::rsrpCandidateA5::threshold1. "+
                "Planned to be removed.";
            }
            tailf:info 'Status Info: Since 22.Q1. Replaced by McpcPCellProfileUeCfg::rsrpCandidateA5::threshold1. Planned to be removed, Obsolete, RSRP threshold1 value for eventA5. Value -29 defines threshold1 to infinity.';
        }

        leaf threshold2 {
            description
              "RSRP threshold2 value for eventA5.

              Value -29 defines threshold2 to infinity.";
            type int32 {
                range "-156..-29";
            }
            units dBm;
            reference
              "3GPP TS 38.331";
            status obsolete {
                yexte:status-information
                "Since 22.Q1. Replaced by McpcPCellProfileUeCfg::rsrpCandidateA5::threshold2. "+
                "Planned to be removed.";
            }
            tailf:info 'Status Info: Since 22.Q1. Replaced by McpcPCellProfileUeCfg::rsrpCandidateA5::threshold2. Planned to be removed, Obsolete, RSRP threshold2 value for eventA5. Value -29 defines threshold2 to infinity.';
        }

        leaf timeToTrigger {
            description
              "Time-to-trigger value for eventA5.";
            type int32 {
                range "0|40|64|80|100|128|160|256|320|480|512|640|1024|1280|2560|5120";
            }
            units ms;
            reference
              "3GPP TS 38.331";
            status obsolete {
                yexte:status-information
                "Since 22.Q1. Replaced by McpcPCellProfileUeCfg::rsrpCandidateA5::timeToTrigger. "+
                "Planned to be removed.";
            }
            tailf:info 'Status Info: Since 22.Q1. Replaced by McpcPCellProfileUeCfg::rsrpCandidateA5::timeToTrigger. Planned to be removed, Obsolete, Time-to-trigger value for eventA5.';
        }
    }

    grouping ReportConfigB2RsrpObsolete {
        description
          "Report configuration settings for B2 measurement event when trigger quantity is RSRP.";

        leaf hysteresis {
            description
              "Hysteresis value for event B2.";
            type int32 {
                range "0..150";
            }
            must ". mod 5 = 0" {
                error-message
                  "The value must set with resolution/step of 5";
            }
            units "0.1 dB";
            reference
              "3GPP TS 38.331";
            status obsolete {
                yexte:status-information
                "Since 22.Q1. Replaced by McpcPCellProfileUeCfg::rsrpCandidateB2::hysteresis. "+
                "Planned to be removed.";
            }
            tailf:info 'Status Info: Since 22.Q1. Replaced by McpcPCellProfileUeCfg::rsrpCandidateB2::hysteresis. Planned to be removed, Obsolete, Hysteresis value for event B2.';
        }

        leaf threshold1 {
            description
              "RSRP threshold1 value for event B2.

              Value -29 defines threshold1 to infinity.";
            type int32 {
                range "-156..-29";
            }
            units dBm;
            reference
              "3GPP TS 38.331";
            status obsolete {
                yexte:status-information
                "Since 22.Q1. Replaced by McpcPCellProfileUeCfg::rsrpCandidateB2::threshold1. "+
                "Planned to be removed.";
            }
            tailf:info 'Status Info: Since 22.Q1. Replaced by McpcPCellProfileUeCfg::rsrpCandidateB2::threshold1. Planned to be removed, Obsolete, RSRP threshold1 value for event B2. Value -29 defines threshold1 to infinity.';
        }

        leaf threshold2EUtra {
            description
              "RSRP threshold2 value for event B2.";
            type int32 {
                range "-140..-44";
            }
            units dBm;
            reference
              "3GPP TS 38.331";
            status obsolete {
                yexte:status-information
                "Since 22.Q1. Replaced by McpcPCellProfileUeCfg::rsrpCandidateB2::threshold2EUtra. "+
                "Planned to be removed.";
            }
            tailf:info 'Status Info: Since 22.Q1. Replaced by McpcPCellProfileUeCfg::rsrpCandidateB2::threshold2EUtra. Planned to be removed, Obsolete, RSRP threshold2 value for event B2.';
        }

        leaf timeToTrigger {
            description
              "Time-to-trigger value for eventB2.";
            type int32 {
                range "0|40|64|80|100|128|160|256|320|480|512|640|1024|1280|2560|5120";
            }
            units ms;
            reference
              "3GPP TS 38.331";
            status obsolete {
                yexte:status-information
                "Since 22.Q1. Replaced by McpcPCellProfileUeCfg::rsrpCandidateB2::timeToTrigger. "+
                "Planned to be removed.";
            }
            tailf:info 'Status Info: Since 22.Q1. Replaced by McpcPCellProfileUeCfg::rsrpCandidateB2::timeToTrigger. Planned to be removed, Obsolete, Time-to-trigger value for eventB2.';
        }
    }

    grouping McpcPCellProfileGrp {
        description
          "Represents the McpcPCellProfile IOC.";

        leaf lowHighFreqPrioClassification {
            description
              "Classification of low and high frequency relation priority.

              NR frequency relation priorities are defined by "+
              "UeMCNrFreqRelProfileUeCfg::connModePrioPSCell.

              Frequency relation priority is classified as high priority if its "+
              "value is higher or equal to value of lowHighFreqPrioClassification, "+
              "else classified as low priority.";
            type int32 {
                range "0..7";
            }
            yexte:takes-effect
              "Next usage";
            status obsolete {
                yexte:status-information
                "Since 22.Q1. Replaced by "+
                "McpcPCellProfileUeCfg::lowHighFreqPrioClassification. Planned to "+
                "be removed.";
            }
            tailf:info 'Status Info: Since 22.Q1. Replaced by McpcPCellProfileUeCfg::lowHighFreqPrioClassification. Planned to be removed, Obsolete, Takes effect: Next usage, Classification of low and high frequency relation priority. NR frequency relation priorities are defined by UeMCNrFreqRelProfileUeCfg::connModePrioPSCell. Frequency relation priority is classified as high priority if its value is higher or equal to value of lowHighFreqPrioClassification, else classified as low priority.';
        }

        leaf-list mcpcQuantityList {
            max-elements 2;
            description
              "Measurement quantities on which PSCell mobility control at poor "+
              "coverage function is applied.";
            type commontypes:McpcQuantity;
            yexte:takes-effect
              "New connection";
            status obsolete {
                yexte:status-information
                "Since 22.Q1. Replaced by McpcPCellProfileUeCfg::mcpcQuantityList. "+
                "Planned to be removed.";
            }
            tailf:info 'Status Info: Since 22.Q1. Replaced by McpcPCellProfileUeCfg::mcpcQuantityList. Planned to be removed, Obsolete, Takes effect: New connection, Measurement quantities on which PSCell mobility control at poor coverage function is applied.';
        }

        container rsrpCandidateA5 {
            description
              "RSRP A5 measurement report criteria when searching for PCell candidate.";
            uses ReportConfigA5RsrpObsolete {
                status obsolete;
            }
            status obsolete {
                yexte:status-information
                "Since 22.Q1. Replaced by McpcPCellProfileUeCfg::rsrpCandidateA5. "+
                "Planned to be removed.";
            }
            reference
               "3GPP TS 38.331";
            yexte:takes-effect
              "Next usage.";
            tailf:info 'Takes effect: Next usage, Status Info: Since 22.Q1. Replaced by McpcPCellProfileUeCfg::rsrpCandidateA5. Planned to be removed, Obsolete, RSRP A5 measurement report criteria when searching for PCell candidate.';
        }

        container rsrpCandidateB2 {
            description
              "RSRP B2 measurement report criteria when searching for PCell candidate.";
            uses ReportConfigB2RsrpObsolete {
                status obsolete;
            }
            status obsolete {
                yexte:status-information
                "Since 22.Q1. Replaced by McpcPCellProfileUeCfg::rsrpCandidateB2. "+
                "Planned to be removed.";
            }
            reference
               "3GPP TS 38.331";
            yexte:takes-effect
              "Next usage.";
            tailf:info 'Takes effect: Next usage, Status Info: Since 22.Q1. Replaced by McpcPCellProfileUeCfg::rsrpCandidateB2. Planned to be removed, Obsolete, RSRP B2 measurement report criteria when searching for PCell candidate.';
        }

        container rsrpCritical {
            description
              "RSRP measurement report criteria for detecting critical coverage.";
            uses ReportConfigA1A2RsrpObsolete {
                status obsolete;
            }
            status obsolete {
                yexte:status-information
                "Since 22.Q1. Replaced by McpcPCellProfileUeCfg::rsrpCritical. "+
                "Planned to be removed.";
            }
            reference
               "3GPP TS 38.331";
            yexte:takes-effect
              "Next usage.";
            tailf:info 'Takes effect: Next usage, Status Info: Since 22.Q1. Replaced by McpcPCellProfileUeCfg::rsrpCritical. Planned to be removed, Obsolete, RSRP measurement report criteria for detecting critical coverage.';
        }

        leaf rsrpCriticalEnabled {
            description
              "Whether RSRP measurement for detecting critical coverage is enabled.

              RSRP measurement criteria for detecting critical coverage is defined "+
              "by rsrpCritical attribute.";
            type boolean;
            yexte:disturbances
              "Changing this attribute to true can trigger release of NR resources "+
              "if UE measurement event condition defined by rsrpCritical attribute "+
              "is been fulfilled.";
            yexte:takes-effect
              "Next usage.";
            status obsolete {
                yexte:status-information
                "Since 22.Q1. Replaced by "+
                "McpcPCellProfileUeCfg::rsrpCriticalEnabled. Planned to be removed.";
            }
            tailf:info 'Status Info: Since 22.Q1. Replaced by McpcPCellProfileUeCfg::rsrpCriticalEnabled. Planned to be removed, Obsolete, Takes effect: Next usage, Traffic Disturbance: Changing this attribute to true can trigger release of NR resources if UE measurement event condition defined by rsrpCritical attribute is been fulfilled, Whether RSRP measurement for detecting critical coverage is enabled. RSRP measurement criteria for detecting critical coverage is defined by rsrpCritical attribute.';
        }

        leaf rsrpSearchTimeRestriction {
            description
              "Search time restriction when searching for PCell candidate using DL "+
              "RSRP measurements.

              If set to -1, no time restriction is applied.";
            type int32 {
                range "-1|10..12000";
            }
            units ms;
            yexte:takes-effect
              "Next usage.";
            status obsolete {
                yexte:status-information
                "Since 22.Q1. Replaced by "+
                "McpcPCellProfileUeCfg::rsrpSearchTimeRestriction. Planned to be "+
                "removed.";
            }
            tailf:info 'Status Info: Since 22.Q1. Replaced by McpcPCellProfileUeCfg::rsrpSearchTimeRestriction. Planned to be removed, Obsolete, Takes effect: Next usage, Search time restriction when searching for PCell candidate using DL RSRP measurements. If set to -1, no time restriction is applied.';
        }

        container rsrpSearchZone {
            description
              "RSRP measurement report criteria that define entering and leaving search zone.";
            uses ReportConfigA1A2RsrpObsolete {
                status obsolete;
            }
            status obsolete {
                yexte:status-information
                "Since 22.Q1. Replaced by McpcPCellProfileUeCfg::rsrpSearchZone. "+
                "Planned to be removed.";
            }
            reference
               "3GPP TS 38.331";
            yexte:takes-effect
              "Next usage.";
            tailf:info 'Takes effect: Next usage, Status Info: Since 22.Q1. Replaced by McpcPCellProfileUeCfg::rsrpSearchZone. Planned to be removed, Obsolete, RSRP measurement report criteria that define entering and leaving search zone.';
        }

        leaf ueConfGroupType {
            description
              "UE configuration Group Type.

              Defines which UE configuration group type that is applied in the "+
              "contained MO class McpcPCellProfileUeCfg.";
            type commontypes:UeConfGroupType;
            default UE_MOBILITY_GROUP;
            yexte:disturbances
              "Changing this attribute can cause loss of traffic.";
            yexte:takes-effect
              "Next usage.";
            tailf:info 'Takes effect: Next usage, Traffic Disturbance: Changing this attribute can cause loss of traffic, UE configuration Group Type. Defines which UE configuration group type that is applied in the contained MO class McpcPCellProfileUeCfg.';
        }
    }

    augment "/me3gpp:ManagedElement/gnbcucp3gpp:GNBCUCPFunction/mcpc:Mcpc" {

        list McpcPCellProfile {
            description
              "Mobility control at poor coverage (MCPC) for PCell.

              Applies to UEs which use the cell as PCell. Attributes are used "+
              "on cell level.

              MO instance McpcPCellProfile=Default is created automatically "+
              "when parent MO is created, unless created manually in the same "+
              "transaction as parent MO.

              MCPC for PCell is enabled per NRCellCU MO by setting "+
              "NRCellCU::mcpcPCellEnabled attribute.
              If NRCellCU::mcpcPCellProfileRef is non-empty, attributes from "+
              "referred MO instance are used.
              If NRCellCU::mcpcPCellProfileRef is empty, attribute default "+
              "values according to McpcPCellProfile and McpcPCellProfileUeCfg "+
              "MO class definitions are used.";
            yexte:precondition
              "McpcPCellProfile=Default MO instance can only be created in the "+
              "same transaction as parent MO and must not be deleted unless "+
              "parent MO is deleted. Other instances can be created and deleted "+
              "manually.";
            key id;
            uses top3gpp:Top_Grp;
            container attributes {
                uses McpcPCellProfileGrp;
                uses commontypes:UserLabelGrp;
            }
            tailf:info 'Precondition: McpcPCellProfile=Default MO instance can only be created in the same transaction as parent MO and must not be deleted unless parent MO is deleted. Other instances can be created and deleted manually, Mobility control at poor coverage (MCPC) for PCell. Applies to UEs which use the cell as PCell. Attributes are used on cell level. MO instance McpcPCellProfile=Default is created automatically when parent MO is created, unless created manually in the same transaction as parent MO. MCPC for PCell is enabled per NRCellCU MO by setting NRCellCU::mcpcPCellEnabled attribute. If NRCellCU::mcpcPCellProfileRef is non-empty, attributes from referred MO instance are used. If NRCellCU::mcpcPCellProfileRef is empty, attribute default values according to McpcPCellProfile and McpcPCellProfileUeCfg MO class definitions are used.';
        }
    }
}
