// Generated by eyang-preprocessor (1.22.0-48 2022-01-20 09:10:06 CET) on Jun 30, 2022, 8:31:44 AM
module ericsson-uemc-vcucp {
    yang-version 1.1;
    namespace "urn:rdns:com:ericsson:oammodel:ericsson-uemc-vcucp";
    prefix "uemcvcucp";

    import tailf-common {
        prefix tailf;
    }
    import _3gpp-common-managed-element {
        prefix "me3gpp";
    }
    import _3gpp-nr-nrm-gnbcucpfunction {
        prefix "gnbcucp3gpp";
    }
    import _3gpp-common-top {
        prefix "top3gpp";
    }
    import ericsson-yang-extensions {
        prefix "yexte";
    }
    import ericsson-common-types-vcucp {
        prefix "commontypes";
    }

    organization
      "Ericsson AB";
    contact
      "Ericsson first line support via email";
    description
      "The module defines the UeMC data model for the Ericsson vCU-CP.

       Copyright (c) 2021-2022 Ericsson AB. All rights reserved.";

    revision 2022-06-28 {
        description
            "Removed module-status preliminary.";
        yexte:version 1;
        yexte:release 2;
        yexte:correction 0;
        reference
            "RFC 7950: The YANG 1.1 Data Modeling Language";
    }

    revision 2022-03-14 {
        description
            "Updated the desciption for UeMC.
             Added the userLabel attribute.";
        yexte:version 1;
        yexte:release 1;
        yexte:correction 0;
        reference
            "RFC 7950: The YANG 1.1 Data Modeling Language";
    }

    revision 2021-11-17 {
        description
            "Marked freqSelAtBlindRwrToEutran and ueMCCellProfileEnabled as obsolete.
             Updated precondition for UeMC.";
        yexte:version 1;
        yexte:release 0;
        yexte:correction 0;
        reference
            "RFC 7950: The YANG 1.1 Data Modeling Language";
    }

    revision 2021-09-13 {
        description
            "Updated description and precondition for the UeMC list.";
        yexte:version 0;
        yexte:release 1;
        yexte:correction 2;
        reference
            "RFC 7950: The YANG 1.1 Data Modeling Language";
    }

    revision 2021-06-08 {
        description
            "Changed error message for a must statement.";
        yexte:version 0;
        yexte:release 1;
        yexte:correction 1;
        reference
            "RFC 7950: The YANG 1.1 Data Modeling Language";
    }

    revision 2021-04-16 {
        description
          "Initial version of the UeMC model.";
        yexte:version 0;
        yexte:release 1;
        yexte:correction 0;
        reference
          "RFC 7950: The YANG 1.1 Data Modeling Language";
    }

    typedef FreqSelAtBlindRwrToEutran {
        description
          "Which MO attribute that is used to select an E-UTRAN frequency for blind release with redirect.";

        type enumeration {
            enum CONNECTED_MODE_MOBILITY_PRIO {
                value 0;
                description
                  "Attribute EUtranFreqRelation::connectedModeMobilityPrio is used to select E-UTRAN frequency.";
            }

            enum BLIND_RWR_ALLOWED {
                value 1;
                description
                  "Attribute UeMCEUtranFreqRelProfile::blindRwrAllowed is used to select E-UTRAN frequency.";
            }
        }
    }

    grouping UeMCGrp {
        description
          "Represents the UeMC IOC.";

        leaf freqSelAtBlindRwrToEutran {
            description
              "Which MO attribute that is used to select an E-UTRAN frequency for "
            + "blind release with redirect.";
            type FreqSelAtBlindRwrToEutran;
            status obsolete {
                yexte:status-information
                    "Since 21.Q4. UeMCEUtranFreqRelProfile::blindRwrAllowed is now always used " +
                    "to select E-UTRAN frequency.";
            }
            tailf:info 'Status Info: Since 21.Q4. UeMCEUtranFreqRelProfile::blindRwrAllowed is now always used to select E-UTRAN frequency, Obsolete, Which MO attribute that is used to select an E-UTRAN frequency for blind release with redirect.';
        }

        leaf ueMCCellProfileEnabled {
            description
              "UeMCCellProfile MO class usage in relation to the deprecated MO "
            + "class UeMeasControl.

               If set to false attribute values from UeMCCellProfile MO class "
            + "instances are not used.
               Instead attribute values from deprecated UeMeasControl MO class "
            + "instances are used.

               If set to true attribute values from UeMCCellProfile MO class "
            + "instances are used.
               Attribute values from instances of deprecated MO class UeMeasControl "
            + "are not used.";
            type boolean;
            status obsolete {
                yexte:status-information
                    "Since 21.Q4. UeMCCellProfile MO class is now always used.";
            }
            tailf:info 'Status Info: Since 21.Q4. UeMCCellProfile MO class is now always used, Obsolete, UeMCCellProfile MO class usage in relation to the deprecated MO class UeMeasControl. If set to false attribute values from UeMCCellProfile MO class instances are not used. Instead attribute values from deprecated UeMeasControl MO class instances are used. If set to true attribute values from UeMCCellProfile MO class instances are used. Attribute values from instances of deprecated MO class UeMeasControl are not used.';
        }
    }
    augment "/me3gpp:ManagedElement/gnbcucp3gpp:GNBCUCPFunction" {
        list UeMC {
            description
                "Container class for UE mobility control attributes and UeMC "+
                "profile classes.

                MO instance UeMC=1 is created automatically when parent MO is "+
                "created, unless created manually in the same transaction as parent MO.

                The RDN of this MO must always be UeMC=1.";
            key id;
            max-elements 1;
            uses top3gpp:Top_Grp {
                refine id {
                    must '. = "1"' {
                        error-message
                          "The RDN of this MO must always be UeMC=1";
                    }
                }
            }
            container attributes {
                uses UeMCGrp;
                uses commontypes:UserLabelGrp;
            }
            yexte:precondition
                "UeMC=1 MO instance must not be deleted unless parent MO is deleted.";
            tailf:info 'Precondition: UeMC=1 MO instance must not be deleted unless parent MO is deleted, Container class for UE mobility control attributes and UeMC profile classes. MO instance UeMC=1 is created automatically when parent MO is created, unless created manually in the same transaction as parent MO. The RDN of this MO must always be UeMC=1.';
        }
    }
}
