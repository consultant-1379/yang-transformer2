// Generated by eyang-preprocessor (1.22.0-48 2022-01-20 09:10:06 CET) on Jun 30, 2022, 8:31:38 AM
module ericsson-local-ip-endpoint-vcucp {
    yang-version 1.1;
    namespace urn:rdns:com:ericsson:oammodel:ericsson-local-ip-endpoint-vcucp;
    prefix localipepvcucp;

    import tailf-common {
        prefix tailf;
    }
    import _3gpp-common-managed-element {
        prefix me3gpp;
    }
    import _3gpp-nr-nrm-gnbcucpfunction {
        prefix gnbcucp3gpp;
    }
    import _3gpp-common-top {
        prefix top3gpp;
    }
    import ericsson-endpoint-resource-vcucp {
        prefix epresource;
    }
    import ericsson-local-ip-endpoint-vcu {
        prefix localipep;
    }
    import ericsson-yang-extensions {
        prefix yexte;
    }

    organization
        "Ericsson AB";
    contact
        "Ericsson first line support via email";
    description
        "The module defines the LocalIpEndpoint data model for the Ericsson vCU-CP.

    Copyright (c) 2021-2022 Ericsson AB. All rights reserved.";

    revision 2022-06-28 {
        description
            "Removed module-status preliminary.";
        yexte:version 0;
        yexte:release 3;
        yexte:correction 0;
        reference
            "RFC 7950: The YANG 1.1 Data Modeling Language";
    }

    revision 2022-06-16 {
        description
            "Add takes-effect information to ipAddressIdList.";
        yexte:version 0;
        yexte:release 2;
        yexte:correction 3;
        reference
            "RFC 7950: The YANG 1.1 Data Modeling Language";
    }

    revision 2021-11-05 {
        description
            "Add must rule for ipAddressIdList uniqueness.";
        yexte:version 0;
        yexte:release 2;
        yexte:correction 2;
        reference
            "RFC 7950: The YANG 1.1 Data Modeling Language";
    }

    revision 2021-04-06 {
        description
            "Updated Ericsson MO description.";
        yexte:version 0;
        yexte:release 2;
        yexte:correction 1;
        reference
            "RFC 7950: The YANG 1.1 Data Modeling Language";
    }

    revision 2021-01-13 {
        description
            "Changed prefix and import to ericsson-local-ip-endpoint-vcu.";
        yexte:version 0;
        yexte:release 2;
        yexte:correction 0;
        reference
            "RFC 7950: The YANG 1.1 Data Modeling Language";
    }

    revision 2021-01-11 {
        description
            "Initial version of the LocalIpEndpoint model.";
        yexte:version 0;
        yexte:release 1;
        yexte:correction 0;
        reference
            "RFC 7950: The YANG 1.1 Data Modeling Language";
    }

    augment "/me3gpp:ManagedElement/gnbcucp3gpp:GNBCUCPFunction/epresource:EndpointResource" {

        list LocalIpEndpoint {
            description
                "Local transport network endpoint for user plane interface.

                E1 control plane uses TCP, hence this interface is also "+
                "configured by this class.";
            key id;
            uses top3gpp:Top_Grp;
            container attributes {
                uses localipep:LocalIpEndpointGrp {
                    refine interfaceList {
                        min-elements 1;
                        must '. = "E1"' {
                            error-message "Allowed values: E1";
                        }
                        must 'count(../../../localipepvcucp:LocalIpEndpoint/attributes/interfaceList[. = "E1"]) &lt; 2' {
                            error-message "An interface must be unique across LocalIpEndpoints under EndpointResource.";
                        }
                        yexte:takes-effect
                            "Node restart";
                        yexte:dependencies
                            "An interface must be unique across LocalIpEndpoints under EndpointResource.";
                        tailf:info 'Dependencies: An interface must be unique across LocalIpEndpoints under EndpointResource, Takes effect: Node restart.';
                    }
                    refine ipAddressIdList {
                        must 'count(../../../localipepvcucp:LocalIpEndpoint/attributes/ipAddressIdList[. = current()]) &lt; 2' {
                            error-message "An ipAddressId must be unique across LocalIpEndpoints under EndpointResource.";
                        }
                        yexte:takes-effect
                            "Node restart";
                        tailf:info 'Takes effect: Node restart.';
                    }
                }
            }
        }
    }
}
