// Generated by eyang-preprocessor (1.22.0-48 2022-01-20 09:10:06 CET) on Jun 30, 2022, 8:31:43 AM
module ericsson-nrfreqrelationtemplate-vcucp {
    yang-version 1.1;
    namespace urn:rdns:com:ericsson:oammodel:ericsson-nrfreqrelationtemplate-vcucp;
    prefix nrfreqrelationtemplate;

    import tailf-common {
        prefix tailf;
    }
    import _3gpp-common-managed-element {
        prefix me3gpp;
    }
    import _3gpp-nr-nrm-gnbcucpfunction {
        prefix gnbcucp3gpp;
    }
    import _3gpp-nr-nrm-nrcellcu {
        prefix nrcellcu3gpp;
    }
    import _3gpp-nr-nrm-nrfreqrelation {
        prefix nrfreqrel3gpp;
    }
    import _3gpp-common-top {
        prefix top3gpp;
    }
    import _3gpp-common-yang-types {
        prefix types3gpp;
    }
    import ericsson-nrnetwork-vcucp {
        prefix nrnetwork;
    }
    import ericsson-nrfrequency-vcucp {
        prefix nrfrequency;
    }
    import ericsson-yang-extensions {
        prefix yexte;
    }

    organization
        "Ericsson AB";
    contact
        "Ericsson first line support via email";
    description
        "The module defines the NRFreqRelationTemplate data model for the Ericsson vCU-CP.

         Copyright (c) 2022 Ericsson AB. All rights reserved.";

    revision 2022-06-28 {
        description
            "Removed module-status preliminary.";
        yexte:version 0;
        yexte:release 2;
        yexte:correction 0;
        reference
            "RFC 7950: The YANG 1.1 Data Modeling Language";
    }

    revision 2022-03-14 {
        description
            "Initial version of the NRFreqRelationTemplate model.";
        yexte:version 0;
        yexte:release 1;
        yexte:correction 0;
        reference
            "RFC 7950: The YANG 1.1 Data Modeling Language";
    }

    grouping NRFreqRelationTemplateGrp {
        description
          "Represents the NRFreqRelationTemplate IOC.";

        leaf arfcnValueNRDlHigh {
            description
                "Higher ARFCN value which is applicable for NR carrier frequency.

                 NRFreqRelation MO instances can be automatically created below this "+
                "value.

                 NRFreqRelationTemplate MO instances cannot have overlapping "+
                "nRFrequencyRange values under same NRCellCU.";
            mandatory true;
            type int32 {
                range "0..3279165";
            }
            yexte:dependencies
                "Must be greater than or equal to NRFrequency::arfcnValueNRDl "+
                "referred from NRFreqRelation::nRFrequencyRef referred from "+
                "defaultNRFreqRelationRef.

                 Must be greater than or equal to arfcnValueNRDlLow.";
            tailf:info 'Dependencies: Must be greater than or equal to NRFrequency::arfcnValueNRDl referred from NRFreqRelation::nRFrequencyRef referred from defaultNRFreqRelationRef.

                 Must be greater than or equal to arfcnValueNRDlLow, Higher ARFCN value which is applicable for NR carrier frequency. NRFreqRelation MO instances can be automatically created below this value. NRFreqRelationTemplate MO instances cannot have overlapping nRFrequencyRange values under same NRCellCU.';
        }

        leaf arfcnValueNRDlLow {
            description
                "Lower ARFCN value which is applicable for NR carrier frequency.

                 NRFreqRelation MO instances can be automatically created above this "+
                "value.

                 NRFreqRelationTemplate MO instances cannot have overlapping "+
                "nRFrequencyRange values under same NRCellCU.";
            mandatory true;
            type int32 {
                range "0..3279165";
            }
            yexte:dependencies
                "Must be less than or equal to NRFrequency::arfcnValueNRDl referred "+
                "from NRFreqRelation::nRFrequencyRef referred from "+
                "defaultNRFreqRelationRef.

                 Must be less than or equal to arfcnValueNRDlHigh.";
            tailf:info 'Dependencies: Must be less than or equal to NRFrequency::arfcnValueNRDl referred from NRFreqRelation::nRFrequencyRef referred from defaultNRFreqRelationRef.

                 Must be less than or equal to arfcnValueNRDlHigh, Lower ARFCN value which is applicable for NR carrier frequency. NRFreqRelation MO instances can be automatically created above this value. NRFreqRelationTemplate MO instances cannot have overlapping nRFrequencyRange values under same NRCellCU.';
        }

        leaf defaultNRFreqRelationRef {
            description
                "Reference to an instance of NRFreqRelation MO.";
            mandatory true;
            type types3gpp:DistinguishedName;
            yexte:dependencies
                "Referenced NRFreqRelation must be under same NRCellCU.";
            must "re-match(current(), 'ManagedElement=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,GNBCUCPFunction=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,NRCellCU=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?,NRFreqRelation=(\\\\( |#|\\\\|&gt;|&lt;|;|\"|\\+|,|[a-fA-F0-9]{2})|[^\\\\&gt;&lt;;\"+,# ])((\\\\( |#|\\\\|&gt;|&lt;|;|\"|\\+|,|[a-fA-F0-9]{2})|[^\\\\&gt;&lt;;\"+,])*(\\\\( |#|\\\\|&gt;|&lt;|;|\"|\\+|,|[a-fA-F0-9]{2})|[^\\\\&gt;&lt;;\"+, ]))?') and
                  re-match(current(), concat('ManagedElement=', ../../../../../me3gpp:id, ',.*')) and
                  re-match(current(), concat('.*GNBCUCPFunction=', ../../../../gnbcucp3gpp:id, ',.*')) and
                  re-match(current(), concat('.*NRCellCU=', ../../../nrcellcu3gpp:id, ',.*')) and
                  count(../../../nrfreqrel3gpp:NRFreqRelation[re-match(current(), concat('.*NRFreqRelation=', nrfreqrel3gpp:id))]) &gt; 0" {
                error-message
                    "defaultNRFreqRelationRef must refer to an NRFreqRelation under the same NRCellCU.";
            }
            tailf:info 'Dependencies: Referenced NRFreqRelation must be under same NRCellCU, Reference to an instance of NRFreqRelation MO.';
        }
    }

    augment "/me3gpp:ManagedElement/gnbcucp3gpp:GNBCUCPFunction/nrcellcu3gpp:NRCellCU" {

        list NRFreqRelationTemplate {
            description
                "Frequency range of automatically created or deleted "+
                "NRFreqRelation MO instances.

                Can be used, for example, for CBRS.

                Contains reference to default NRFreqRelation MO instance used as "+
                "template for automatically created NRFreqRelation instances "+
                "within this range.

                Note: Only NRFreqRelation MO instances within this range are "+
                "automatically deleted. Changing the range or deleting an "+
                "NRFreqRelationTemplate instance may require manual deletion of "+
                "NRFreqRelation MO instances.

                NRFreqRelationTemplate MO instances cannot have overlapping "+
                "nRFrequencyRange values under same NRCellCU.";
            key id;
            max-elements 4;
            uses top3gpp:Top_Grp;
            container attributes {
                uses NRFreqRelationTemplateGrp;
            }
            status current {
                yexte:preliminary;
            }

            must "attributes/arfcnValueNRDlHigh &gt;= attributes/arfcnValueNRDlLow" {
                error-message
                    "arfcnValueNRDlHigh must be greater than or equal to arfcnValueNRDlLow.";
            }

            must "count(../NRFreqRelationTemplate/attributes[
                            arfcnValueNRDlLow &lt;= current()/attributes/arfcnValueNRDlHigh and
                            arfcnValueNRDlHigh &gt;= current()/attributes/arfcnValueNRDlLow
                        ]) &lt;= 1" {
                error-message
                    "NRFreqRelationTemplate MO instances cannot have overlapping NR Frequency range values under same NRCellCU.";
            }

            must "count(../../nrnetwork:NRNetwork[
                      re-match(
                        current()/../nrfreqrel3gpp:NRFreqRelation[
                          nrfreqrel3gpp:id = substring-after(current()/attributes/defaultNRFreqRelationRef, 'NRFreqRelation=')
                        ]/nrfreqrel3gpp:attributes/nrfreqrel3gpp:nRFrequencyRef,
                        concat('.*NRNetwork=', nrnetwork:id, ',.*'))
                    ]/nrfrequency:NRFrequency[
                        nrfrequency:id = substring-after(current()/../nrfreqrel3gpp:NRFreqRelation[
                            nrfreqrel3gpp:id = substring-after(current()/attributes/defaultNRFreqRelationRef, 'NRFreqRelation=')
                          ]/nrfreqrel3gpp:attributes/nrfreqrel3gpp:nRFrequencyRef, 'NRFrequency=') and
                        nrfrequency:attributes/nrfrequency:arfcnValueNRDl &gt;= current()/attributes/arfcnValueNRDlLow and
                        nrfrequency:attributes/nrfrequency:arfcnValueNRDl &lt;= current()/attributes/arfcnValueNRDlHigh]
                  ) = 1" {
                error-message
                    "The value of NRFrequency::arfcnValueNRDl referenced by "+
                    "NRFreqRelation::nRFrequencyRef referenced by defaultNRFreqRelationRef "+
                    "must be between arfcnValueNRDlLow and arfcnValueNRDlHigh.";
            }
            tailf:info 'Preliminary, Frequency range of automatically created or deleted NRFreqRelation MO instances. Can be used, for example, for CBRS. Contains reference to default NRFreqRelation MO instance used as template for automatically created NRFreqRelation instances within this range. Note: Only NRFreqRelation MO instances within this range are automatically deleted. Changing the range or deleting an NRFreqRelationTemplate instance may require manual deletion of NRFreqRelation MO instances. NRFreqRelationTemplate MO instances cannot have overlapping nRFrequencyRange values under same NRCellCU.';
        }
    }
}
