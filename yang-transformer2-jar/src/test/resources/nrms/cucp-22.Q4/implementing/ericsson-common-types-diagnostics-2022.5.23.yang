// Generated by eyang-preprocessor (1.23.0-54 2022-02-22 23:30:06 CET) on Jun 9, 2022, 9:03:32 AM
module ericsson-common-types-diagnostics {
    yang-version 1.1;
    namespace urn:rdns:com:ericsson:oammodel:ericsson-common-types-diagnostics;
    prefix commontypesdiag;
    import tailf-common {
        prefix tailf;
    }
    import ericsson-yang-extensions {
        prefix yexte;
    }
    import ericsson-yang-types {
        prefix typese;
    }
    organization
      'Ericsson AB';
    contact
      'Ericsson first line support via email';
    description
      'Common types for diagnostics actions

       Copyright (c) 2022 Ericsson AB. All rights reserved';

    revision 2022-05-23 {
        description
        'Added grouping esi';
        yexte:version 1;
        yexte:release 1;
        yexte:correction 0;
    }

    revision 2022-05-16 {
        description
        'Administrative revision';
        yexte:version 1;
        yexte:release 0;
        yexte:correction 1;
    }

    revision 2022-01-31 {
        description
        'Initial revision';
        yexte:version 1;
        yexte:release 0;
        yexte:correction 0;
    }

    yexte:module-status preliminary;

    typedef full-banner {
        description '
        Warning text to be displayed to user
        at activation of diagnostics actions.
        ';

        type string;
    }

    typedef short-banner {
        description '
        Warning text to be displayed to user
        as part of the output from each action.
        ';

        type string;
    }

    grouping activation-action {
        action activate {
            description "activate diagnostics actions";
            output {
                leaf banner {
                    type full-banner;
                    mandatory true;
                }
            }
            tailf:actionpoint cpa-action;
        }
    }

    grouping output-format {
        description "definition of output format selector to be used in all actions";
        leaf output-format {
            description "result output format";
            default text;
            type enumeration {
                enum text {
                    description "plain text output (default)";
                }
                enum json {
                    description "json formatted output";
                }
            }
        }
    }

    grouping result {
        description "definition of result to be used in all actions";
        leaf banner {
            type short-banner;
            mandatory true;
        }
        list result {
            key instance;
            leaf instance {
                description '
            Identifier of the provider of this part of the result.
            When a hierarchy or other structure is traversed to retreive
            the result it is recommended to separate each level with "::".

            Example: "mediator::executor"
            ';
                type string;
            }
            leaf output {
                description '
            The actual result output from one instance performing the action.
            The format will depend on the selected output-format.
            ';
                type string;
            }
        }
    }

    grouping esi {
        container esi {
            action prepare {
                description "prepare esi for collection via ddc";
                output {
                    leaf prepare_esi_action_id {
                        type leafref {
                            path "../../progress-report/action-id";
                        }
                        mandatory true;
                        description
                "A reference to the progress-report list entry where
             information about the progress and the result of
             the esi preparation can be found.";
                    }
                }
                tailf:actionpoint cpa-action;
            }
            list progress-report {
                key "action-id";
                config false;
                description
            "Represents the progress report and final result of the
         ongoing (asynchronous) esi prepare action.
         Only one action can be executed at a time.";
                uses typese:async-action-progress;
            }
        }
    }
}
