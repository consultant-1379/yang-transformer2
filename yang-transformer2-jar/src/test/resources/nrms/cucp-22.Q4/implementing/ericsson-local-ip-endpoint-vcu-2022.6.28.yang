// Generated by eyang-preprocessor (1.24.0-23 2022-06-22 14:11:55 CEST) on Jun 28, 2022, 10:45:18 AM
module ericsson-local-ip-endpoint-vcu {
    yang-version 1.1;
    namespace urn:rdns:com:ericsson:oammodel:ericsson-local-ip-endpoint-vcu;
    prefix localipep;

    import ericsson-transport-types-vcu {
        prefix transtypes;
    }
    import ericsson-yang-extensions {
        prefix yexte;
    }

    organization
        "Ericsson AB";
    contact
        "Ericsson first line support via email";
    description
        "The module defines the abstract LocalIpEndpoint data model for the Ericsson vCU.

    Copyright (c) 2021-2022 Ericsson AB. All rights reserved.";

    revision 2022-06-28 {
        description
            "Removed module-status preliminary.";
        yexte:version 0;
        yexte:release 2;
        yexte:correction 0;
        reference
            "RFC 7950: The YANG 1.1 Data Modeling Language";
    }

    revision 2021-01-13 {
        description
            "Initial version of the abstract LocalIpEndpoint model.";
        yexte:version 0;
        yexte:release 1;
        yexte:correction 0;
        reference
            "RFC 7950: The YANG 1.1 Data Modeling Language";
    }

    grouping LocalIpEndpointGrp {
        description " Represents the LocalIpEndpoint IOC.";

        leaf-list ipAddressIdList {
            description
                "Reference to used IpAddress MO in the Transport Service.";
            min-elements 1;
            max-elements 1;
            type transtypes:ReferenceId;
        }

        leaf-list interfaceList {
            description
                "Contains all interface types using this endpoint.";
            type transtypes:InterfaceName;
        }
    }
}
