module simple-defaults-one {

    namespace "urn{test}simple-defaults-one";
    prefix this;

    revision "2021-10-30";
	
	container cont1 {

		leaf leaf11 {
			type boolean;
		}

		leaf leaf12 {
			type boolean;
			default true;
		}

		leaf leaf13 {
			type boolean;
			default FalSe;		// being lenient
		}

		leaf leaf14 {
			type boolean;
			default YES;		// invalid default value
		}

		leaf leaf17 {
			type empty;
		}
	}
	
	container cont2 {

		leaf leaf21 {
			type bits {
				bit ONE;
				bit TWO;
				bit THREE;
			}
			default "ONE";
		}

		leaf leaf22 {
			type bits {
				bit ONE;
				bit TWO;
				bit THREE;
			}
			default "  ONE   TWO   ";
		}

		leaf leaf23 {
			type bits {
				bit ONE;
				bit TWO;
				bit THREE;
			}
			default "	THREE  ONE	";	// ignoring extra whitespace, being lenient
		}

		leaf leaf24 {
			type bits {
				bit ONE;
				bit TWO;
				bit THREE;
			}
			default "  ";		// invalid default value
		}

		leaf leaf25 {
			type bits {
				bit ONE;
				bit TWO;
				bit THREE;
			}
			default "ONE ONE";		// duplicate default value, being lenient
		}

		leaf leaf26 {
			type bits {
				bit ONE;
				bit TWO;
				bit THREE;
			}
			default "ONE FOUR";		// invalid default value
		}
	}
	
	container cont3 {
	
		leaf leaf31 {
			type string;
			default "";
		}
	
		leaf leaf32 {
			type string;
			default "\t\t";
		}
	
		leaf leaf33 {
			type string;
			default " abc ";
		}

		leaf leaf34 {
			type string {
				length "0..4";
			}
			default "abcdef";		// illegal default value
		}
	}
	
	container cont4 {
	
		leaf leaf41 {
			type int8;
			default 10;
		}

		leaf leaf42 {
			type int16;
			default 1000;
		}

		leaf leaf43 {
			type int32;
			default 10000000;
		}

		leaf leaf44 {
			type int64;
			default 10000000000000000;
		}
	
		leaf leaf45 {
			type uint8;
			default 10;
		}

		leaf leaf46 {
			type uint16;
			default 1000;
		}

		leaf leaf47 {
			type uint32;
			default 10000000;
		}

		leaf leaf48 {
			type uint64;
			default 10000000000000000;
		}
	}

	container cont5 {
	
		leaf leaf51 {
			type int8;
			default 1000;		// invalid default value
		}

		leaf leaf52 {
			type int8;
			default "blurb";	// invalid default value
		}

		leaf leaf53 {
			type int8;
			default "-0x10";	// OK, hex representation = -16
		}

		leaf leaf54 {
			type int8 {
				range 0..5;
			}
			default 10;			// invalid default value
		}

		leaf leaf55 {
			type uint8;
			default 256;		// invalid default value
		}

		leaf leaf56 {
			type uint64;
			default 123456789012345678901234567890;		// invalid default value
		}
	}	

	container cont6 {
	
		leaf leaf61 {
			type decimal64 {
				fraction-digits 6;
			}
			default 10.12345;
		}

		leaf leaf62 {
			type decimal64 {
				fraction-digits 6;
			}
			default "blurb";		// invalid default value
		}

		leaf leaf63 {
			type decimal64 {
				fraction-digits 6;
				range "0.0 .. 5.0";
			}
			default 10.12345;		// invalid default value
		}
	}
	
	container cont7 {
	
		leaf leaf71 {
			type enumeration {
				enum RED;
				enum YELLOW;
				enum GREEN;
			}
			default "RED";
		}
	
		leaf leaf72 {
			type enumeration {
				enum RED;
				enum YELLOW;
				enum GREEN;
			}
			default "  YELLOW	";	// invalid default value
		}

		leaf leaf73 {
			type enumeration {
				enum RED;
				enum YELLOW;
				enum GREEN;
			}
			default "";			// invalid default value
		}
	
		leaf leaf74 {
			type enumeration {
				enum RED;
				enum YELLOW;
				enum GREEN;
			}
			default "BLUE";		// invalid default value
		}
	}
	
	identity identity1;
	
	identity identity2 {
		base identity1;
	}
	
	identity identity3 {
		base identity1;
	}

	identity identity99;

	container cont8 {
	
		leaf leaf81 {
			type identityref {
				base this:identity1;
			}
			default this:identity1;
		}

		leaf leaf82 {
			type identityref {
				base this:identity1;
			}
			default identity3;
		}

		leaf leaf83 {
			type identityref {
				base this:identity1;
			}
			default this:identity99;		// invalid default value
		}

		leaf leaf84 {
			type identityref {
				base this:identity1;
			}
			default this:unknown-identity;	// invalid default value
		}

		leaf leaf85 {
			type identityref {
				base this:identity1;
			}
			default unknown-prefix:unknown-identity;	// invalid default value
		}
	}
}
