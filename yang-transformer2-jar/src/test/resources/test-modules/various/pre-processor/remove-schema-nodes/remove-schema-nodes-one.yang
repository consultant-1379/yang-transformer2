module remove-schema-nodes-one {

    namespace "urn*test*remove-schema-nodes-one";
    prefix this;

    revision "2021-03-07";

	container cont1 {
	
		leaf leaf11 {				// will be removed
			type string;
		}

		leaf leaf12 {
			type string;
		}
		
		action action15 {
			input {
				leaf leaf16 {		// will be removed
					type string;
				}
			}
		}
		
		action action17;              // will be removed
	}

	list list2 {
		key leaf21;
	
		leaf leaf21 {
			type string;
		}
		
		choice choice24 {
			case case1 {
				leaf leaf26 {		// will be removed
					type string;
				}
			}
			case case2 {
				leaf leaf27 {		
					type string;
				}
			}
		}		
	}

	rpc rpc3;
}
