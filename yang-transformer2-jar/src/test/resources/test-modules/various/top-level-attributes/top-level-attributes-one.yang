module top-level-attributes-one {

    namespace "urn~test~top-level-attributes-one";
    prefix this;
	
    revision "2021-11-30";


	leaf leaf11 {
		type boolean;
	}

	leaf leaf12 {
		type enumeration {
			enum RED;
			enum YELLOW;
		}
	}

	leaf leaf13 {
		type int32;
	}

	leaf leaf14 {
		type leafref {
			path "../leaf13";
		}
	}

	leaf leaf15 {
		type identityref {
			base identity1;
		}
	}

	identity identity1;

	identity identity2 {
		base identity1;
	}
}
