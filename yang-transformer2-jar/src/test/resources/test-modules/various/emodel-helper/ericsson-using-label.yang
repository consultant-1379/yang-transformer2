module ericsson-using-label {

	namespace "urn:test:ericsson-using-label";
	prefix this;

	import o-ran-smo-teiv-common-yang-extensions {
		prefix or-teiv-ext;
	}

	revision 2024-01-30 {
		or-teiv-ext:label 5.7.3;
	}

	container cont11 {
		leaf leaf111 {
			type string;
		}
	}
}
