module data-type-compatibility {

    namespace "urn::test::data-type-compatibility";
    prefix this;
	
    revision "2021-04-21";

	container cont1 {

		leaf leaf11 {
			type string;
		}

		leaf leaf12 {
			type string;
		}

		leaf leaf13 {
			type uint32;
		}

		leaf leaf14 {
			type uint32;
		}
		
		leaf leaf15 {
			type enumeration {
				enum RED;
				enum YELLOW;
			}
		}
		leaf leaf16 {
			type enumeration {
				enum RED;
				enum YELLOW;
			}
		}
	}

}
