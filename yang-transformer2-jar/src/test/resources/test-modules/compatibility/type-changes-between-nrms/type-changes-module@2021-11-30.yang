module type-changes-module {

	namespace "urn:test:type-changes-module";
	prefix this;

	revision "2021-11-30";

	container cont1 {

		leaf leaf11 {
			type string;
		}

		leaf leaf12 {
			type boolean;
		}
	}
}
