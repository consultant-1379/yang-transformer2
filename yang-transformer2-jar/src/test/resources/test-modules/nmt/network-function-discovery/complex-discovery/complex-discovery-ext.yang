module complex-discovery-ext {

	namespace "urn:test:complex-discovery-ext";
	prefix this;

	revision "2022-07-01";

	import complex-discovery {
		prefix complex;
	}

	augment /complex:ManagedElement {
		container GNodeBDUFunction {
			presence "";
		}
		container GNodeBCUUPFunction {
			presence "";
		}
	}

	container ManagedElement {
		container GNodeBDUFunction {
			container NrCellDU {
				presence "";
			}
		}
	}

	container pgw-yy {
		leaf sgw-yy { type string; }
	}
}
